-- Imports declare

CENTEC DEFINITIONS ::= BEGIN

IMPORTS
      SnmpAdminString
      FROM SNMP-FRAMEWORK-MIB
      
      ifIndex
      FROM IF-MIB
      
      TimeTicks, Counter32, OBJECT-IDENTITY,
      mib-2, MODULE-IDENTITY, IpAddress, Counter64,
      Unsigned32, Integer32, Gauge32, OBJECT-TYPE,
      NOTIFICATION-TYPE
      FROM SNMPv2-SMI

      OwnerString
      FROM RMON-MIB
      
      NOTIFICATION-GROUP, MODULE-COMPLIANCE, OBJECT-GROUP
      FROM SNMPv2-CONF
      
      InetAddressPrefixLength, InetAddress, InetAddressType
      FROM INET-ADDRESS-MIB
      
      InterfaceIndex, InterfaceIndexOrZero, ifIndex
      FROM IF-MIB
      
      VrId
      FROM VRRP-MIB      
      
      TestAndIncr, TimeStamp, AutonomousType,
      PhysAddress, TEXTUAL-CONVENTION, TruthValue, DateAndTime,
      MacAddress, RowStatus
        FROM SNMPv2-TC
      
      enterprises
        FROM SNMPv2-SMI;
        
-- Child OID declare

centec MODULE-IDENTITY
	LAST-UPDATED "200806260000Z"        -- June 26, 2008 at 00:00 GMT
	ORGANIZATION
	   ""
	CONTACT-INFO
	   "
	   "
	DESCRIPTION
	       "The System Information of the switch"
	::= { enterprises 27975 }

------------------------------------------------------------------
--                      Centec Identifiers                      --
------------------------------------------------------------------

system                    OBJECT IDENTIFIER ::= { centec 1 }
syslog                    OBJECT IDENTIFIER ::= { centec 2 }
mirror                    OBJECT IDENTIFIER ::= { centec 3 }
portSecurity              OBJECT IDENTIFIER ::= { centec 4 }
stormControl              OBJECT IDENTIFIER ::= { centec 5 }
ntp                       OBJECT IDENTIFIER ::= { centec 6 }
acl                       OBJECT IDENTIFIER ::= { centec 7 }
qos                       OBJECT IDENTIFIER ::= { centec 8 }
igsp                      OBJECT IDENTIFIER ::= { centec 9 }
linkAgg                   OBJECT IDENTIFIER ::= { centec 10 }
qBridgeExt                OBJECT IDENTIFIER ::= { centec 11 }
dot1xExt                  OBJECT IDENTIFIER ::= { centec 12 }
timeRange                 OBJECT IDENTIFIER ::= { centec 13 }
stpExt                    OBJECT IDENTIFIER ::= { centec 14 }
igmpExt                   OBJECT IDENTIFIER ::= { centec 16 }
boardHealthyMonitor       OBJECT IDENTIFIER ::= { centec 17 }
arpInsp                   OBJECT IDENTIFIER ::= { centec 20 }
--pimsmExt                  OBJECT IDENTIFIER ::= { centec 21 }
--ospfExt                   OBJECT IDENTIFIER ::= { centec 22 }
user                      OBJECT IDENTIFIER ::= { centec 30 }
snmpExt                   OBJECT IDENTIFIER ::= { centec 32 }
stm                       OBJECT IDENTIFIER ::= { centec 33 }
dnsClient                 OBJECT IDENTIFIER ::= { centec 34 }
ssh                       OBJECT IDENTIFIER ::= { centec 35 }
dhcp                      OBJECT IDENTIFIER ::= { centec 36 }
lswdevMMib                OBJECT IDENTIFIER ::= { centec 37 }
lswTrapMib                OBJECT IDENTIFIER ::= { centec 39 }
ipSourceGuard             OBJECT IDENTIFIER ::= { centec 40 }
interface                 OBJECT IDENTIFIER ::= { centec 42 }
management                OBJECT IDENTIFIER ::= { centec 43 }
mvr                       OBJECT IDENTIFIER ::= { centec 44 }
erps                      OBJECT IDENTIFIER ::= { centec 45 }
prefixList                OBJECT IDENTIFIER ::= { centec 46 }
ipUnicast                 OBJECT IDENTIFIER ::= { centec 47 }
--vrf                       OBJECT IDENTIFIER ::= { centec 48 }
aaa                       OBJECT IDENTIFIER ::= { centec 49 }
evc                       OBJECT IDENTIFIER ::= { centec 51 }
qinq                      OBJECT IDENTIFIER ::= { centec 52 }
rmonExt                   OBJECT IDENTIFIER ::= { centec 53 }
--routeMap                  OBJECT IDENTIFIER ::= { centec 54 }
--ripExt                    OBJECT IDENTIFIER ::= { centec 57 }
ldpExt                    OBJECT IDENTIFIER ::= { centec 60 }
bgp                       OBJECT IDENTIFIER ::= { centec 68 }
mpls                      OBJECT IDENTIFIER ::= { centec 69 }
smartlink                 OBJECT IDENTIFIER ::= { centec 70 }
flowctrl                  OBJECT IDENTIFIER ::= { centec 71 }
cputraffic                OBJECT IDENTIFIER ::= { centec 72 }
portisolate               OBJECT IDENTIFIER ::= { centec 73 }
phyloopback               OBJECT IDENTIFIER ::= { centec 74 }
monitorlink               OBJECT IDENTIFIER ::= { centec 75 }
udld                      OBJECT IDENTIFIER ::= { centec 76 }
policyBasedRouting        OBJECT IDENTIFIER ::= { centec 77 }
ddos                      OBJECT IDENTIFIER ::= { centec 78 }
l2ping                    OBJECT IDENTIFIER ::= { centec 79 }
--ipg                       OBJECT IDENTIFIER ::= { centec 80 }
ssm                       OBJECT IDENTIFIER ::= { centec 81 }
arpConfig                 OBJECT IDENTIFIER ::= { centec 82 }
--cfm                       OBJECT IDENTIFIER ::= { centec 83 }
ptp                       OBJECT IDENTIFIER ::= { centec 85 }
pm                        OBJECT IDENTIFIER ::= { centec 90 }
alarm                     OBJECT IDENTIFIER ::= { centec 91 }
rsvpTe                    OBJECT IDENTIFIER ::= { centec 92 }
--g8031                     OBJECT IDENTIFIER ::= { centec 93 }
--g8032                     OBJECT IDENTIFIER ::= { centec 94 }
voiceVlan                 OBJECT IDENTIFIER ::= { centec 95 }
ivi                       OBJECT IDENTIFIER ::= { centec 96 }
product                   OBJECT IDENTIFIER ::= { centec 99 }
l2protocol                OBJECT IDENTIFIER ::= { centec 100 }
loopbackDetect            OBJECT IDENTIFIER ::= { centec 105 }




-- Module declares
-- Sub Module: product

	e3008TS OBJECT-IDENTITY
		STATUS	current
		DESCRIPTION
	        "E300,8TS."
	    ::= { product 3080 } 
	    
	e30016TX OBJECT-IDENTITY
		STATUS	current
		DESCRIPTION
	        "E300,16TX."
	    ::= { product 3160 }

	e3508T12X OBJECT-IDENTITY
		STATUS	current
		DESCRIPTION
	        "E350,8T12X."
	    ::= { product 3200 }
	    	
	e30024TS OBJECT-IDENTITY
		STATUS	current
		DESCRIPTION
	        "E300,24TS."
	    ::= { product 3240 }
	
	e30024ST OBJECT-IDENTITY
		STATUS	current
		DESCRIPTION
	        "E300,24ST."
	    ::= { product 3241 }
	
	e30048TS OBJECT-IDENTITY
		STATUS	current
		DESCRIPTION
	        "E300,48TS."
	    ::= { product 3480 }
	
	b30048T OBJECT-IDENTITY
		STATUS	current
		DESCRIPTION
	        "B300,48T."
	    ::= { product 3481 }
		
	e33048T OBJECT-IDENTITY
		STATUS	current
		DESCRIPTION
	        "E330,48T."
	    ::= { product 3485 }

	e33048SE OBJECT-IDENTITY
		STATUS	current
		DESCRIPTION
	        "E330,48SE."
	    ::= { product 3486 }

	e33048S OBJECT-IDENTITY
		STATUS	current
		DESCRIPTION
	        "E330,48S."
	    ::= { product 3487 }

	g24eu OBJECT-IDENTITY
		STATUS	current
		DESCRIPTION
	        "G24EU,24+4."
	    ::= { product 3488 }

	e35048T4X OBJECT-IDENTITY
		STATUS	current
		DESCRIPTION
	        "E350,48T4X."
	    ::= { product 3520 }
		
	e58024Q OBJECT-IDENTITY
		STATUS	current
		DESCRIPTION
	        "E580,24Q."
	    ::= { product 5801 }
		
	e58048X2Q4Z OBJECT-IDENTITY
		STATUS	current
		DESCRIPTION
	        "E580,48X2Q4Z."
	    ::= { product 5802 }
		
	e58048X6Q OBJECT-IDENTITY
		STATUS	current
		DESCRIPTION
	        "E580,48X6Q."
	    ::= { product 5803 }
		
	e58032X2Q OBJECT-IDENTITY
		STATUS	current
		DESCRIPTION
	        "E580,32X2Q."
	    ::= { product 5804 }
	    	    		
	e602 OBJECT-IDENTITY
		STATUS	current
		DESCRIPTION
	        "E600,2 slots."
	    ::= { product 6020 }  
	
	e606 OBJECT-IDENTITY
		STATUS	current
		DESCRIPTION
	        "E600,6 slots."
	    ::= { product 6060 }  
	
	e614 OBJECT-IDENTITY
		STATUS	current
		DESCRIPTION
	        "E600,14 slots."
	    ::= { product 6140 }  
	       
	e802 OBJECT-IDENTITY
		STATUS	current
		DESCRIPTION
	        "E800,2 slots"
	    ::= { product 8020 } 
	
	e806 OBJECT-IDENTITY
		STATUS	current
		DESCRIPTION
	        "E800,6 slots"
	    ::= { product 8060 } 
	
	e814 OBJECT-IDENTITY
		STATUS	current
		DESCRIPTION
	        "E800,14 slots"
	    ::= { product 8140 } 
	             



memory                    OBJECT IDENTIFIER ::= { system 1 }
systemStats               OBJECT IDENTIFIER ::= { system 2 }
operate                   OBJECT IDENTIFIER ::= { system 3 }
--sysImageTable             OBJECT IDENTIFIER ::= { system 4 }
sysImageTable         OBJECT-TYPE
    SYNTAX          SEQUENCE  OF SysImageEntry
    MAX-ACCESS      not-accessible
    STATUS          current
    DESCRIPTION
        "The system image management table."
    ::= { system 4 }
flash                     OBJECT IDENTIFIER ::= { system 5 }
cf                        OBJECT IDENTIFIER ::= { system 6 }
sysTrap                   OBJECT IDENTIFIER ::= { system 7 }
time                      OBJECT IDENTIFIER ::= { system 8 }


-- Sub Module:  SYSTEM

ErrorFlag    ::= TEXTUAL-CONVENTION
    STATUS          current
    DESCRIPTION
        "Represents a possible error condition."
    SYNTAX          INTEGER    { noError(0),  error(1) }
    
memIndex OBJECT-TYPE
    SYNTAX          Integer32
    MAX-ACCESS      	read-only
    STATUS          current
    DESCRIPTION  
        "Bogus Index.  This should always return the integer 0."
    ::= { memory 1 }   
    
memTotalReal          OBJECT-TYPE
    SYNTAX          Integer32
    UNITS             "kB"
    MAX-ACCESS      read-only
    STATUS          current
    DESCRIPTION
        "The total amount of real/physical memory installed on this host."
    ::= { memory 5 }

memTotalFree         OBJECT-TYPE
    SYNTAX          Integer32
    UNITS             "kB"
    MAX-ACCESS      read-only
    STATUS          current
    DESCRIPTION
        "The total amount of memory free or available for use on
        this host.This value typically covers both real memory
        and swap space or virtual memory."
    ::= { memory 11 }
    
   
-- systemStats OBJECT IDENTIFIER    ::= { system 2 }
    
ssIndex         OBJECT-TYPE
    SYNTAX          Integer32
    MAX-ACCESS      read-only
    STATUS          current
    DESCRIPTION
        "Bogus Index.This should always return the integer 1."
    ::= { systemStats 1 }
  
ssCpuIdle             OBJECT-TYPE
    SYNTAX          Integer32
    MAX-ACCESS      read-only
    STATUS          current
    DESCRIPTION
        "The percentage of processor time spent idle, calculated over the last
         minute."
    ::= { systemStats 11 }
    
-- The agent only implements those of the following counters that the
-- kernel supports! Don't expect all to be present.
    
-- sysProcessTable           OBJECT IDENTIFIER ::= { systemStats 100 }    
sysProcessTable         OBJECT-TYPE
    SYNTAX          SEQUENCE  OF SysProcessEntry
    MAX-ACCESS      not-accessible
    STATUS          current
    DESCRIPTION
        "The system precess table."
    ::= { systemStats 100 }

     
sysProcessEntry          OBJECT-TYPE
    SYNTAX          SysProcessEntry
    MAX-ACCESS      not-accessible
    STATUS          current
    DESCRIPTION
        "An entity process entry. Each entry consists of information of an process.
        The sysProcessIndex exclusively defines an process id."
    INDEX  { sysProcessIndex }
    ::= { sysProcessTable 1 }
    
    
SysProcessEntry  ::=
    SEQUENCE 
    {
        sysProcessIndex
            Integer32,
        sysProcessName
            OCTET STRING
     }
    
sysProcessIndex         OBJECT-TYPE
    SYNTAX          Integer32 (0..65536)
    MAX-ACCESS      not-accessible
    STATUS          current
    DESCRIPTION 
        "The pid of process."
    ::= { sysProcessEntry 1 }

    
sysProcessName          OBJECT-TYPE
    SYNTAX          OCTET STRING (SIZE(0..256))
    MAX-ACCESS      read-only
    STATUS          current
    DESCRIPTION
        "The name of the process."
    ::= { sysProcessEntry 2 }
 
-- operate OBJECT IDENTIFIER    ::= { system 3 }
    
configSave         OBJECT-TYPE
    SYNTAX          Integer32 (0..1)
    MAX-ACCESS      read-write
    STATUS          current
    DESCRIPTION
        "This should always write running-config to startup-config.And the 
        valid set value is 1. When get the configSave value, 1 means success, 0 means failure."
    ::= { operate 1 }
    
reload         OBJECT-TYPE
    SYNTAX          INTEGER
    {
        rebootWithoutSave(1),
        saveAndReboot(2)
    }
    MAX-ACCESS      read-write
    STATUS          current
    DESCRIPTION
	    "This should allow to reboot the switch.The valid input value is 1 and 2.
        Value 1 means the switch will reboot without savingcurrent configuration.
        Value 2 means the switch will savecurrent configuration before reboot the switch."
    ::= { operate 2 }

rebootAt         OBJECT-TYPE
    SYNTAX          OCTET STRING (SIZE(0..256))
    MAX-ACCESS      read-write
    STATUS          current
    DESCRIPTION
        "Specify auto reboot parameters at the special time. The format defined like 'HH:MM,YYYY/MM/DD'. 0 is mean clear."
    ::= { operate 3 }
        
rebootDelay         OBJECT-TYPE
    SYNTAX          OCTET STRING (SIZE(1..256))
    MAX-ACCESS      read-write
    STATUS          current
    DESCRIPTION
        "Specify auto reboot parameters reboot after delay some time. The value is [1, 720] minutes. 0 is mean clear."
    ::= { operate 4 }
        
version         OBJECT-TYPE
    SYNTAX          OCTET STRING (SIZE(0..256))
    MAX-ACCESS      read-only
    STATUS          current
    DESCRIPTION
    	"Description the current version "
    ::= { operate 5 }
    
serviceTelnet         OBJECT-TYPE
    SYNTAX          INTEGER 
    {
        enable(1),
        disable(2)
    }
    MAX-ACCESS      read-write
    STATUS          current
    DESCRIPTION
	        "Telnet service.1:enable 2:disable."
    ::= { operate 6 }

loginFail         OBJECT-TYPE
    SYNTAX          Integer32
    MAX-ACCESS      not-accessible
    STATUS          current
    DESCRIPTION
        "This node only for login fail for three time."
    ::= { operate 7 }    

lastCommand         OBJECT-TYPE
    SYNTAX          OCTET STRING (SIZE(0..512))
    MAX-ACCESS      read-only
    STATUS          current
    DESCRIPTION
    	"Save the last command line and time."
    ::= { operate 8 }

currentRunningImage OBJECT-TYPE
    SYNTAX			OCTET STRING (SIZE(0..512))
    MAX-ACCESS		read-only
    STATUS			current
    DESCRIPTION
    	"Show the current running image."
    ::= { operate 9 }

sysStartUpTime OBJECT-TYPE
    SYNTAX			TimeTicks
    MAX-ACCESS		read-only
    STATUS			current
    DESCRIPTION
    	"Show system startup time."
    ::= { operate 10 }
            
--sysImageTable         OBJECT-TYPE
--    SYNTAX          SEQUENCE  OF SysImageEntry
--    MAX-ACCESS      not-accessible
--    STATUS          current
--    DESCRIPTION
--        "The system image management table."
--    ::= { system 4 }
    
sysImageEntry          OBJECT-TYPE
    SYNTAX          SysImageEntry
    MAX-ACCESS      not-accessible
    STATUS          current
    DESCRIPTION
        "An entity image entry.Each entry consists of information of an entity image.
        The sysImageIndex exclusively defines an image file."
    INDEX  { sysImageIndex }
    ::= { sysImageTable 1 }
    
    
SysImageEntry    ::=
    SEQUENCE 
    {
        sysImageIndex
            Integer32,
        sysImageName
            OCTET STRING,
        sysImageCreateTime
            OCTET STRING,
        sysImageVersion
            OCTET STRING,
        sysImageSize
            OCTET STRING,
        sysImageDir
            OCTET STRING,
        sysImageIsBoot
            TruthValue
     }
    
sysImageIndex         OBJECT-TYPE
    SYNTAX          Integer32 (0..64)
    MAX-ACCESS      not-accessible
    STATUS          current
    DESCRIPTION 
        "The index of image."
    ::= { sysImageEntry 1 }

    
sysImageName          OBJECT-TYPE
    SYNTAX          OCTET STRING (SIZE(0..256))
    MAX-ACCESS      read-only
    STATUS          current
    DESCRIPTION
        "The file name of the image."
    ::= { sysImageEntry 2 }
    
sysImageCreateTime    OBJECT-TYPE
    SYNTAX          OCTET STRING (SIZE(0..256))
    MAX-ACCESS      read-only
    STATUS          current
    DESCRIPTION 
        "The create time of the image."
    ::= { sysImageEntry 3 }
    
sysImageVersion       OBJECT-TYPE
    SYNTAX          OCTET STRING (SIZE(0..256))
    MAX-ACCESS      read-only
    STATUS          current
    DESCRIPTION
        "The version of the image."
    ::= { sysImageEntry 4 }
        
sysImageSize          OBJECT-TYPE
    SYNTAX          OCTET STRING (SIZE(0..256))
    MAX-ACCESS      read-only
    STATUS          current
    DESCRIPTION 
        "The size of the image."
    ::= { sysImageEntry 5 }
    
sysImageDir           OBJECT-TYPE
    SYNTAX          OCTET STRING (SIZE(0..256))
    MAX-ACCESS      read-only
    STATUS          current
    DESCRIPTION
        "The dir of the image."
    ::= { sysImageEntry 6 }
        
sysImageIsBoot         OBJECT-TYPE
    SYNTAX          TruthValue
    MAX-ACCESS      read-write
    STATUS          current
    DESCRIPTION 
        "This image is the boot image (1),and is not the boot image (2). Only support enable(1)."
    ::= { sysImageEntry 7 }
      
--
-- System Traps
--    
                
                
     
--time OBJECT IDENTIFIER    ::= { system 8 }
    
timeSet OBJECT IDENTIFIER    ::= { time 1 }
timeSetClock          OBJECT-TYPE
    SYNTAX          OCTET STRING (SIZE(0..256))
    MAX-ACCESS      read-write
    STATUS          current
    DESCRIPTION
	        "current time. format HH:MM:SS."
    ::= { timeSet 1 }
    
timeSetMonth          OBJECT-TYPE
    SYNTAX          Integer32
    MAX-ACCESS      read-write
    STATUS          current
    DESCRIPTION
        "Month of the year. range is [1, 12]."
    ::= { timeSet 2 }
        
timeSetDay             OBJECT-TYPE
    SYNTAX          Integer32
    MAX-ACCESS      read-write
    STATUS          current
    DESCRIPTION
        "Day of the month. range is [1, 31]."
    ::= { timeSet 3 }
    
timeSetYear            OBJECT-TYPE
    SYNTAX          Integer32
    MAX-ACCESS      read-write
    STATUS          current
    DESCRIPTION
        "Year of the date. range is [2000, 2037]."
    ::= { timeSet 4 }
    
timezoneSetTable         OBJECT-TYPE
	SYNTAX          SEQUENCE OF TimezoneSetEntry
	MAX-ACCESS      not-accessible
    STATUS          current
    DESCRIPTION
        "The table of SummerTime."
    ::= { time 2 }
        
timezoneSetEntry         OBJECT-TYPE
    SYNTAX          TimezoneSetEntry
    MAX-ACCESS      not-accessible
    STATUS          current
    DESCRIPTION
        "The entry of timezone."
    INDEX        { timezoneSetZoneName }
    ::= { timezoneSetTable 1 }  
    
TimezoneSetEntry    ::=
    SEQUENCE 
    {
        timezoneSetZoneName
            OCTET STRING,
        timezoneSetType
            Integer32,
        timezoneSetHours
            Integer32,
        timezoneSetMinutes
            Integer32,
        timezoneSetSeconds
            Integer32,
        timezoneSetState
            RowStatus 
     }
    
timezoneSetZoneName   OBJECT-TYPE
    SYNTAX          OCTET STRING (SIZE (1..64))
    MAX-ACCESS      read-create
    STATUS          current
    DESCRIPTION
        "Zone name, must be less than 32 characters. only include [a-zA-Z_]. The begin and end character must be alphabet. Its length range is [3, 32)"
    ::= { timezoneSetEntry 1 }
    
timezoneSetType        OBJECT-TYPE
    SYNTAX          Integer32
    MAX-ACCESS      read-create
    STATUS          current
    DESCRIPTION
        "Positive/Negative time zone offset from UTC.
         0 means Negative
         1 means Positive"
    ::= { timezoneSetEntry 2 }
        
timezoneSetHours      OBJECT-TYPE
    SYNTAX          Integer32
    MAX-ACCESS      read-create
    STATUS          current
    DESCRIPTION
        "Hours offset from UTC, must be range 0~23."
    ::= { timezoneSetEntry 3 }
    
timezoneSetMinutes     OBJECT-TYPE
    SYNTAX          Integer32
    MAX-ACCESS      read-create
    STATUS          current
    DESCRIPTION
        "Minutes offset from UTC, must be range 0~59."
    ::= { timezoneSetEntry 4 }
    
timezoneSetSeconds     OBJECT-TYPE
    SYNTAX          Integer32
    MAX-ACCESS      read-create
    STATUS          current
    DESCRIPTION
        "Seconds offset from UTC, must be range 0~59."
    ::= { timezoneSetEntry 5 }
    
timezoneSetState         OBJECT-TYPE
    SYNTAX          RowStatus 
    MAX-ACCESS      read-create
    STATUS          current
    DESCRIPTION
        "The status of this conceptual row.Now only realize CreateAndGo and Destroy and Active.
        1 means Active
        4 means CreateAndGo
        6 means Destroy"
    ::= { timezoneSetEntry 6 }
        
recurrentSummerTimeTable         OBJECT-TYPE
    SYNTAX          SEQUENCE OF RecurrentSummerTimeEntry
    MAX-ACCESS      not-accessible
    STATUS          current
    DESCRIPTION
        "The table of SummerTime."
    ::= { time 3 }
        
recurrentSummerTimeEntry    OBJECT-TYPE
    SYNTAX          RecurrentSummerTimeEntry
    MAX-ACCESS      not-accessible
    STATUS          current
    DESCRIPTION
        "The entry of SummerTime."
    INDEX         { recurrentSummerTimeZoneName }
    ::= { recurrentSummerTimeTable 1 }  
    
RecurrentSummerTimeEntry    ::=
    SEQUENCE {
        recurrentSummerTimeZoneName
            OCTET STRING,
        recurrentSummerTimeStartMonth
            Integer32,
        recurrentSummerTimeStartDay
            Integer32,
        recurrentSummerTimeStartClock
            OCTET STRING,
        recurrentSummerTimeEndMonth
            Integer32,
        recurrentSummerTimeEndDay
            Integer32,
        recurrentSummerTimeEndClock
            OCTET STRING,
        recurrentSummerTimeOffset
            Integer32,
        recurrentSummerTimeState
            RowStatus 
     }
        
recurrentSummerTimeZoneName         OBJECT-TYPE
    SYNTAX          OCTET STRING (SIZE (1..64))
    MAX-ACCESS      read-create
    STATUS          current
    DESCRIPTION
        "Zone name, must be less than 32 characters. only include [a-zA-Z_]. The begin and end character must be alphabet. Its length range is [1, 32)"
    ::= { recurrentSummerTimeEntry 1 }
    
recurrentSummerTimeStartMonth         OBJECT-TYPE
    SYNTAX          Integer32
    MAX-ACCESS      read-create
    STATUS          current
    DESCRIPTION
        "Start month of the year. range is [1,12]"
    ::= { recurrentSummerTimeEntry 2 }

recurrentSummerTimeStartDay         OBJECT-TYPE
    SYNTAX          Integer32
    MAX-ACCESS      read-create
    STATUS          current
    DESCRIPTION
        "Day in month to start. range is [1, 31].        "
    ::= { recurrentSummerTimeEntry 3 }
    
recurrentSummerTimeStartClock         OBJECT-TYPE
    SYNTAX          OCTET STRING (SIZE (1..32))
    MAX-ACCESS      read-create
    STATUS          current
    DESCRIPTION
        "Time to start. format HH:MM:SS"
    ::= { recurrentSummerTimeEntry 4 }
    
recurrentSummerTimeEndMonth         OBJECT-TYPE
    SYNTAX          Integer32
    MAX-ACCESS      read-create
    STATUS          current
    DESCRIPTION
        "Month to end. range is [1, 12]."
    ::= { recurrentSummerTimeEntry 5 }

recurrentSummerTimeEndDay         OBJECT-TYPE
    SYNTAX          Integer32
    MAX-ACCESS      read-create
    STATUS          current
    DESCRIPTION
        "Day in month to end. range is [1, 31]."
    ::= { recurrentSummerTimeEntry 6 }
    
recurrentSummerTimeEndClock         OBJECT-TYPE
    SYNTAX          OCTET STRING (SIZE (1..32))
    MAX-ACCESS      read-create
    STATUS          current
    DESCRIPTION
	        "Time to end. format HH:MM:SS"
    ::= { recurrentSummerTimeEntry 7 }
    
recurrentSummerTimeOffset         OBJECT-TYPE
    SYNTAX          Integer32
    MAX-ACCESS      read-create
    STATUS          current
    DESCRIPTION
	        "Summer time offset, unit is minute.  range is [1, 1440]."
    ::= { recurrentSummerTimeEntry 8 }
    
recurrentSummerTimeState         OBJECT-TYPE
    SYNTAX          RowStatus 
    MAX-ACCESS      read-create
    STATUS          current
    DESCRIPTION
	        "The status of this conceptual row.Now only realize CreateAndGo and Destroy and Active.
      1 means Active
      4 means CreateAndGo
      6 means Destroy"
 
    ::= { recurrentSummerTimeEntry 9 }

summerTimeTable         OBJECT-TYPE
    SYNTAX          SEQUENCE OF SummerTimeEntry
    MAX-ACCESS      not-accessible
    STATUS          current
    DESCRIPTION
        "The table of SummerTime."
    ::= { time 4 }

summerTimeEntry         OBJECT-TYPE
    SYNTAX          SummerTimeEntry
    MAX-ACCESS      not-accessible
    STATUS          current
    DESCRIPTION
        "The entry of SummerTime."
	 	    INDEX      { summerTimeZoneName }
    ::= { summerTimeTable 1 }  

SummerTimeEntry    ::=
    SEQUENCE {
        summerTimeZoneName
            OCTET STRING,
        summerTimeStartMonth
            Integer32,
        summerTimeStartDay
            Integer32,
        summerTimeStartYear
            Integer32,
        summerTimeStartClock
            OCTET STRING,
        summerTimeEndMonth
            Integer32,
        summerTimeEndDay
            Integer32,
        summerTimeEndYear
            Integer32,
        summerTimeEndClock
            OCTET STRING,
        summerTimeOffset
            Integer32,
        summerTimeState
            RowStatus 
     }

summerTimeZoneName     OBJECT-TYPE
    SYNTAX          OCTET STRING (SIZE (1..32))
    MAX-ACCESS      read-create
    STATUS          current
    DESCRIPTION
        "Zone name, must be less than 32 characters.
 only include [a-zA-Z_]. The begin and end character must be alphabet. Its length range is [1, 32)"
    ::= { summerTimeEntry 1 }
summerTimeStartMonth         OBJECT-TYPE
    SYNTAX          Integer32
    MAX-ACCESS      read-create
    STATUS          current
    DESCRIPTION
        "Start month of the year. range is [1, 12]."
    ::= { summerTimeEntry 2 }
    
summerTimeStartDay     OBJECT-TYPE
    SYNTAX          Integer32
    MAX-ACCESS      read-create
    STATUS          current
    DESCRIPTION
	        "Start day of month. range is [1, 31]."
    ::= { summerTimeEntry 3 }

summerTimeStartYear    OBJECT-TYPE
    SYNTAX          Integer32
    MAX-ACCESS      read-create
    STATUS          current
    DESCRIPTION
        "Start year of summer-time. range is [2000, 2037]."
    ::= { summerTimeEntry 4 }
    
summerTimeStartClock   OBJECT-TYPE
    SYNTAX          OCTET STRING (SIZE (1..32))
    MAX-ACCESS      read-create
    STATUS          current
    DESCRIPTION
        "Start time. format HH:MM:SS."
    ::= { summerTimeEntry 5 }

summerTimeEndMonth     OBJECT-TYPE
    SYNTAX          Integer32
    MAX-ACCESS      read-create
    STATUS          current
    DESCRIPTION
        "End month of year. range is [1, 12]."
    ::= { summerTimeEntry 6 }
    
summerTimeEndDay       OBJECT-TYPE
    SYNTAX          Integer32
    MAX-ACCESS      read-create
    STATUS          current
    DESCRIPTION
        "End day of month. range is [1, 31]."
    ::= { summerTimeEntry 7 }

summerTimeEndYear      OBJECT-TYPE
    SYNTAX          Integer32
    MAX-ACCESS      read-create
    STATUS          current
    DESCRIPTION
        "End year of summer time. range is [2000, 2037]."
    ::= { summerTimeEntry 8 }
    
summerTimeEndClock     OBJECT-TYPE
    SYNTAX          OCTET STRING (SIZE (1..32))
    MAX-ACCESS      read-create
    STATUS          current
    DESCRIPTION
        "End time. format HH:MM:SS."
    ::= { summerTimeEntry 9 }
    
summerTimeOffset       OBJECT-TYPE
    SYNTAX          Integer32
    MAX-ACCESS      read-create
    STATUS          current
    DESCRIPTION
	        "Summer time offset, unit is minute. range is [1, 1440]."
    ::= { summerTimeEntry 10 }
    
summerTimeState         OBJECT-TYPE
    SYNTAX          RowStatus 
    MAX-ACCESS      read-create
    STATUS          current
    DESCRIPTION
	        "The status of this conceptual row.Now only realize CreateAndGo and Destroy and Active.
    1 means Active
    4 means CreateAndGo
    6 means Destroy"
    ::= { summerTimeEntry 11 }
        
-- Sub Module: FLASH

memTotalUsed         OBJECT-TYPE
    SYNTAX          Integer32
    UNITS             "kB"
    MAX-ACCESS      read-only
    STATUS          current
    DESCRIPTION
        "The total amount of memory used on this host.
        This value typically covers both real memory
        and swap space or virtual memory."
    ::= { memory 12 }

--
-- Textual conventions
--

FlashOperationStatus ::= TEXTUAL-CONVENTION
    STATUS          current
    DESCRIPTION
        "The status of the specified operation can be one of
        the following.
        opInProgress : the operation is in process.
        opSuccess :  the operation has been completed successfully.
        opInvalid : the command is invalid or command-protocol-device combination 
        is unsupported by the system.
        opInvalidProtocol :invalid protocol is specified
        opInvalidSourceName :invalid source file name is specified.
        opInvalidDestName :invalid target name is specified.
        opInvalidServerAddress :invalid server address is specified
        opDeviceBusy :the device is in use and locked by another process
        opDeviceOpenError :invalid device name is specified.
        opDeviceError : device read, write or erase error
        opDeviceNotProgrammable :device isread-only but a write or
        erase operation was specified.
        opDeviceFull :  device is filled to capacity
        opFileOpenError :invalid file name; file not found in partition
        opFileTransferError :file transfer was unsuccessful
        opFileChecksumError :file checksum in Flash is invalid
        opNoMemory :system is running in low on memory
        opUnknownFailure :failure which is  unknown
        opDeleteFileOpenError :file is in used by another process
        opDeleteInvalidDevice :invalid device name is specified
        opDeleteInvalidFunction :deleted operation is unsupported
        by the device.
        opDeleteOperationError :operation is in a low error
        opDeleteInvalidFileName :invalid file name is specified
        pDeleteDeviceBusy :the device is in use and locked
        by another process.
        opDeleteParaError :the parameters are invalid
        opDeleteInvalidPath :the file path is invalid."
    SYNTAX          INTEGER
    {
        opInProgress(1),
        opSuccess(2),
        opInvalid(3),
        opInvalidProtocol(4),
        opInvalidSourceName(5),
        opInvalidDestName(6),
        opInvalidServerAddress(7),
        opDeviceBusy(8),
        opDeviceOpenError(9),
        opDeviceError(10),
        opDeviceNotProgrammable(11),
        opDeviceFull(12),
        opFileOpenError(13),
        opFileTransferError(14),
        opFileChecksumError(15),
        opNoMemory(16),
        opAuthFail(17),
        opTimeout(18),
        opUnknownFailure(19),
        opDeleteFileOpenError(20),
        opDeleteInvalidDevice(21),
        opDeleteInvalidFunction(22),
        opDeleteOperationError(23),
        opDeleteInvalidFileName(24),
        opDeleteDeviceBusy(25),
        opDeleteParaError(26),
        opDeleteInvalidPath(27)
    }

--
-- Node definitions
--

-- Flash device management MIB object
flashManMIBObjects OBJECT IDENTIFIER    ::= { flash 1 }


-- The flash device information.
flashDevice OBJECT IDENTIFIER    ::= { flashManMIBObjects 1 }


flashTable         OBJECT-TYPE
    SYNTAX          SEQUENCE OF FlashEntry
    MAX-ACCESS      not-accessible
    STATUS          current
    DESCRIPTION
        "This table gives the properties of all the flashes on the system."
    ::= { flashDevice 1 }


flashEntry         OBJECT-TYPE
    SYNTAX          FlashEntry
    MAX-ACCESS      not-accessible
    STATUS          current
    DESCRIPTION
        "The entry of flashTable."
    INDEX      { flhIndex }
    ::= { flashTable 1 }


FlashEntry    ::=
    SEQUENCE {
        flhIndex
            Integer32,
        flhSize
            OCTET STRING,
        flhFree
            OCTET STRING,
        flhName
            OCTET STRING,
--      flhChipNum
--          Integer32,
        flhDescr
            OCTET STRING
--      flhInitTime
--          TimeStamp
--      flhRemovable
--          TruthValue,
--      flhPartitionBool
--          TruthValue,
--      flhMinPartitionSize
--          Integer32,
--      flhMaxPartitions
--          Integer32,
--      flhPartitionNum
--          Integer32
     }

flhIndex              OBJECT-TYPE
    SYNTAX          Integer32 (1..2147483647)
    MAX-ACCESS      not-accessible
    STATUS          current
    DESCRIPTION
        "The index of flashTable.It has a minimum value of 1, and  maximum value
         of the same as the value of flhSupportNum."
    ::= { flashEntry 1 }


flhSize         OBJECT-TYPE
    SYNTAX          OCTET STRING (SIZE(0..256))
    UNITS             "bytes"
    MAX-ACCESS      read-only
    STATUS          current
    DESCRIPTION
        "Specifies the total size of the flash device indexed by flhIndex.
        The value should be zero if the flash is removed for a removable device."
    ::= { flashEntry 2 }


flhFree         OBJECT-TYPE
    SYNTAX          OCTET STRING (SIZE(0..256)) 
    UNITS              "bytes"
    MAX-ACCESS      read-only
    STATUS          current
    DESCRIPTION
        "Specifies the free size of the flash device."
    ::= { flashEntry 3 }


flhName         OBJECT-TYPE
    SYNTAX          OCTET STRING (SIZE (0..255))
    MAX-ACCESS      read-only
    STATUS          current
    DESCRIPTION
        "The flash name within the system."
    ::= { flashEntry 4 }


--flhChipNum         OBJECT-TYPE
--    SYNTAX          Integer32 (1..64)
--    MAX-ACCESS      read-only
--    STATUS          current
--    DESCRIPTION
--        "The chip numbers in the flash."
--    ::= { flashEntry 5 }


flhDescr         OBJECT-TYPE
    SYNTAX          OCTET STRING  (SIZE (0..64))
    MAX-ACCESS      read-only
    STATUS          current
    DESCRIPTION
        "DESCRIPTION of the purpose of the flash in the system."
    ::= { flashEntry 6 }


--flhInitTime         OBJECT-TYPE
--    SYNTAX          TimeStamp
--    MAX-ACCESS      read-only
--    STATUS          current
--    DESCRIPTION
--        "
--            The initialization time for the flash component or partition,
--            recorded using the system time.This will be the boot time for
--            a fixed device.For a removable component or a partition,
--            it will be the initialization time.
--        "
--    ::= { flashEntry 8 }


--flhRemovable         OBJECT-TYPE
--    SYNTAX          TruthValue
--    MAX-ACCESS      read-only
--    STATUS          current
--    DESCRIPTION
--        "
--            The value indicates whether the flash indexed can be removed
--            or not.
--            The true(1) value indicates the flash device CAN be removed.
--        "
--    ::= { flashEntry 9 }
--
--
--flhPartitionBool         OBJECT-TYPE
--    SYNTAX          TruthValue
--    MAX-ACCESS      read-write
--    STATUS          current
--    DESCRIPTION
--        "
--            The value indicates whether the flash indexed can be partitioned
--            or not.
--            The true(1) value indicates the flash CAN be partitioned.
--        "
--    ::= { flashEntry 11 }
--
--
--flhMinPartitionSize         OBJECT-TYPE
--    SYNTAX          Integer32
--        UNITS         "bytes"
--    MAX-ACCESS      read-only
--    STATUS          current
--    DESCRIPTION
--        "
--            Minimum partition size supported.
--            If flhDevicePartitionBool is false, the value
--            of this object is the same as flhSize.
--        "
--    ::= { flashEntry 12 }
--
--
--flhMaxPartitions         OBJECT-TYPE
--    SYNTAX          Integer32 (1..8)
--    MAX-ACCESS      read-only
--    STATUS          current
--    DESCRIPTION
--        "
--            The maximum count of partitions which the system supports
--            for this flash.If flhPartitionBool is false,
--            the object value is 1.
--        "
--    ::= { flashEntry 13 }
--
--
--flhPartitionNum         OBJECT-TYPE
--    SYNTAX          Integer32
--    MAX-ACCESS      read-only
--    STATUS          current
--    DESCRIPTION
--        "
--            The actual number of partitions supported by the system for
--            this flash.If flhPartitionBool is false, this value is 1.
--        "
--    ::= { flashEntry 14 }


flhFiles OBJECT IDENTIFIER    ::= { flashDevice 2 }


flhFileTable        OBJECT-TYPE
    SYNTAX          SEQUENCE OF FlhFileEntry
    MAX-ACCESS      not-accessible
    STATUS          current
    DESCRIPTION
        "Table of file information."
    ::= { flhFiles 1 }


flhFileEntry         OBJECT-TYPE
    SYNTAX          FlhFileEntry
    MAX-ACCESS      not-accessible
    STATUS          current
    DESCRIPTION
        "An entry representing a file.Indexed using flash number, partition 
        number, and file number."
    INDEX {flhFileIndex }
    ::= { flhFileTable 1 }


FlhFileEntry    ::=
    SEQUENCE {
        flhFileIndex
            Integer32,
        flhFileName
             OCTET STRING,
        flhFileSize
            Integer32,
        flhFileTime
             OCTET STRING
--      flhFileChecksum
--           OCTET STRING
     }

flhFileIndex         OBJECT-TYPE
    SYNTAX          Integer32 (0..2147483647)
    MAX-ACCESS      not-accessible
    STATUS          current
    DESCRIPTION
        "Index of the table, whose range is from 1 to 2147483647."
    ::= { flhFileEntry 1 }


flhFileName         OBJECT-TYPE
    SYNTAX          OCTET STRING (SIZE (1..255))
    MAX-ACCESS      read-only
    STATUS          current
    DESCRIPTION
        "A valid file name supported by the file system."
    ::= { flhFileEntry 2 }


flhFileSize           OBJECT-TYPE
    SYNTAX          Integer32
    MAX-ACCESS      read-only
    STATUS          current
    DESCRIPTION
        "The file size in bytes excluding the file header of file system.
         The value should be greater than zero."
    ::= { flhFileEntry 3 }


flhFileTime           OBJECT-TYPE
    SYNTAX          OCTET STRING (SIZE (0..255))
    MAX-ACCESS      read-only
    STATUS          current
    DESCRIPTION
        "The time when this file is modified last time."
    ::= { flhFileEntry 4 }


--flhFileChecksum       OBJECT-TYPE
--    SYNTAX          OCTET STRING
--    MAX-ACCESS      read-only
--    STATUS          current
--    DESCRIPTION
--        "The file checksum in the header of file."
--    ::= { flhFileEntry 5 }


-- The operation on the flash.
flashOperate OBJECT IDENTIFIER    ::= { flashManMIBObjects 2 }


flhOpTable          OBJECT-TYPE
    SYNTAX          SEQUENCE OF FlhOpEntry
    MAX-ACCESS      not-accessible
    STATUS          current
    DESCRIPTION
        "Table used to operate flash."
    ::= { flashOperate 1 }


flhOpEntry         OBJECT-TYPE
    SYNTAX          FlhOpEntry
    MAX-ACCESS      not-accessible
    STATUS          current
    DESCRIPTION
        "Note an operation can not be stopped until it is finished.
        If notification is configured, NMS will receive a notification
        at the end of the operation.
        Entries in the table will be removed automatically in 5 minutes.
        It can also be deleted by NMS directly."
    INDEX    { flhOperIndex }
    ::= { flhOpTable 1 }


FlhOpEntry    ::=
    SEQUENCE {
        flhOperIndex
            Integer32,
        flhOperType
            INTEGER,
        flhOperProtocol
            INTEGER,
        flhOperServerAddress
            IpAddress,
        flhOperServerUser
             OCTET STRING,
        flhOperPassword
           OCTET STRING,
        flhOperSourceFile
             OCTET STRING,
        flhOperDestinationFile
             OCTET STRING,
        flhOperStatus 
             FlashOperationStatus ,
--      flhOperEndNotification
--          TruthValue,
--      flhOperProgress
--          TimeTicks,
        flhOperIsManagementIf 
            TruthValue,
        flhOperRowStatus 
            RowStatus 
     }

flhOperIndex          OBJECT-TYPE
    SYNTAX          Integer32 (1..2147483647)
    MAX-ACCESS      not-accessible
    STATUS          current
    DESCRIPTION
        " Specifies the index of an entry.It is a
        random value when creating an entry."
    ::= { flhOpEntry 1 }


flhOperType         OBJECT-TYPE
    SYNTAX          INTEGER
        {
        flash2Flash(1),
        net2Flash(2),
        flash2Net(3),
        delete(4),
        rename(5)
        }
    MAX-ACCESS      read-create
    STATUS          current
    DESCRIPTION
        "Specifies the operation to be executed.
        flash2Flash(1)  Copy a file from flash to flash.
        net2Flash(2)    Copy a file from net to flash; 
        flash2Net(3)    Copy a file from flash to net.
        delete(4)      Delete a file from flash, the file name is specified by flhOperSourceFile;
        rename(5)     Change a file's name."
    ::= { flhOpEntry 2 }


flhOperProtocol         OBJECT-TYPE
    SYNTAX          INTEGER
    {
        ftp(1),
        tftp(2)
--            clusterftp(3),
--            clustertftp(4)
    }
    MAX-ACCESS      read-create
    STATUS          current
    DESCRIPTION
        "Specifies the protocol used to transfer file.
        The default protocol is ftp.
        Both member switch and commander switch can use them if they
        support HGMP v2.
        1 FTP
        2 TFTP"
       -- DEFVAL { ftp }
    ::= { flhOpEntry 3 }


flhOperServerAddress         OBJECT-TYPE
    SYNTAX          IpAddress
    MAX-ACCESS      read-create
    STATUS          current
    DESCRIPTION
        "The address of remote host acting as server for operation.
        The default value is 0.0.0.0."
--		DEFVAL { 0.0.0.0 }
    ::= { flhOpEntry 4 }


flhOperServerUser      OBJECT-TYPE
    SYNTAX          OCTET STRING  (SIZE (1..255))
    MAX-ACCESS      read-create
    STATUS          current
    DESCRIPTION
        "When using ftp to transfer files, the user name must be
        specified through this node."
    ::= { flhOpEntry 5 }


flhOperPassword         OBJECT-TYPE
    SYNTAX          OCTET STRING (SIZE (1..255))
    MAX-ACCESS      read-create
    STATUS          current
    DESCRIPTION
        "Remote user password for copying via ftp protocol.Optionally,
        This object may be ignored for protocols other than ftp."
    ::= { flhOpEntry 6 }


flhOperSourceFile      OBJECT-TYPE
    SYNTAX          OCTET STRING (SIZE (1..255))
    MAX-ACCESS      read-create
    STATUS          current
    DESCRIPTION
        "Specifies the source file name to be transferred.
        It may be located on flash or remote server.
        It may include the file path if it is applicable.
        It must be specified."
    ::= { flhOpEntry 7 }


flhOperDestinationFile    OBJECT-TYPE
    SYNTAX          OCTET STRING (SIZE (1..255))
    MAX-ACCESS      read-create
    STATUS          current
    DESCRIPTION
        "Specifies the destination file name.
        It may be located on flash or remote server.
        It may include the file path if it is applicable.
        If it is not specified, the destination file name
        is the same as source file name for application."
    ::= { flhOpEntry 8 }


flhOperStatus         OBJECT-TYPE
    SYNTAX          FlashOperationStatus
    MAX-ACCESS      read-only
    STATUS          current
    DESCRIPTION
        "The status of the specified operation can be one of
        the following.
        opInProgress(1) : the operation is in process.
        opSuccess(2) :  the operation has been completed successfully.
        opInvalid(3) : the command is invalid or command-protocol-device combination is unsupported by the system.
        opInvalidProtocol(4) :invalid protocol is specified
        opInvalidSourceName(5) :invalid source file name is specified.
        opInvalidDestName(6) :invalid target name is specified.
        opInvalidServerAddress(7) :invalid server address is specified
        opDeviceBusy(8) :the device is in use and locked by another process
        opDeviceOpenError(9) :invalid device name is specified.
        opDeviceError(10) : device read, write or erase error
        opDeviceNotProgrammable(11) :device isread-only but a write or erase operation was specified.
        opDeviceFull(12) :  device is filled to capacity
        opFileOpenError(13) :invalid file name; file not found in partition
        opFileTransferError(14) :file transfer was unsuccessful
        opFileChecksumError(15) :file checksum in Flash is invalid
        opNoMemory(16) :system is running in low on memory
        opUnknownFailure(19) :failure which is  unknown
        opDeleteFileOpenError(20) :file is in used by another process
        opDeleteInvalidDevice(21) :invalid device name is specified
        opDeleteInvalidFunction(22) :deleted operation is unsupported by the device.
        opDeleteOperationError(23) :operation is in a low error
        opDeleteInvalidFileName(24) :invalid file name is specified
        pDeleteDeviceBusy(25) :the device is in use and locked by another process.
        opDeleteParaError(26) :the parameters are invalid
        opDeleteInvalidPath(27) :the file path is invalid."
    ::= { flhOpEntry 9 }


--flhOperEndNotification         OBJECT-TYPE
--    SYNTAX          TruthValue
--    MAX-ACCESS      read-only
--    STATUS          current
--    DESCRIPTION
--        "
--            If the value of it is specified 'true', a notification
--            will be generated at the end of the operation.
--            Else no notification will be generated.
--        "
--        DEFVAL { false }
--    ::= { flhOpEntry 10 }


--flhOperProgress       OBJECT-TYPE
--    SYNTAX          TimeTicks
--    MAX-ACCESS      read-only
--    STATUS          current
--    DESCRIPTION
--        "The progress described as the time taken for the operation.
--        "
--    ::= { flhOpEntry 11 }

flhOperIsManagementIf   OBJECT-TYPE
    SYNTAX          TruthValue
    MAX-ACCESS      read-create
    STATUS          current
    DESCRIPTION
        "If use management interface running SNMP or not, true(1):enable.false(2):disable"
      -- DEFVAL { true }    
    ::= { flhOpEntry 12 }
    
flhOperRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { flhOpEntry 13 }


--    flashNotification OBJECT IDENTIFIER    ::= { flashManMIBObjects 3 }
--
--
--    flhOperNotification NOTIFICATION-TYPE
--        OBJECTS { flhOperStatus }
--    STATUS          current
--    DESCRIPTION
--        "
--            A flhOperNotification is sent at the completion of a flash
--            copy operation if flhOperEndNotification is true.
--        "
--    ::= { flashNotification 1 }


-- Sub Module: CF

        

--
-- Textual conventions
--

CfOperationStatus ::= TEXTUAL-CONVENTION
    STATUS          current
    DESCRIPTION
        "The status of the specified operation can be one of the following.
        opInProgress : the operation is in process.
        opSuccess :  the operation has been completed successfully.
        opInvalid : the command is invalid or command-protocol-device combination is
         unsupported by the system.
        opInvalidProtocol :invalid protocol is specified
        opInvalidSourceName :invalid source file name is specified.
        opInvalidDestName :invalid target name is specified.
        opInvalidServerAddress :invalid server address is specified
        opDeviceBusy :the device is in use and locked by another process
        opDeviceOpenError :invalid device name is specified.
        opDeviceError : device read, write or erase error
        opDeviceNotProgrammable :device isread-only but a write or
        erase operation was specified
        opDeviceFull :  device is filled to capacity
        opFileOpenError :invalid file name; file not found in partition
        opFileTransferError :file transfer was unsuccessful
        opFileChecksumError :file checksum in Cf is invalid
        opNoMemory :system is running in low on memory
        opUnknownFailure :failure which is  unknown
        opDeleteFileOpenError :file is in used by another process
        opDeleteInvalidDevice :invalid device name is specified
        opDeleteInvalidFunction :deleted operation is unsupported
        by the device
        opDeleteOperationError :operation is in a low error
        opDeleteInvalidFileName :invalid file name is specified
        pDeleteDeviceBusy :the device is in use and locked
        by another process
        opDeleteParaError :the parameters are invalid
        opDeleteInvalidPath :the file path is invalid."
    SYNTAX          INTEGER
    {
        opInProgress(1),
        opSuccess(2),
        opInvalid(3),
        opInvalidProtocol(4),
        opInvalidSourceName(5),
        opInvalidDestName(6),
        opInvalidServerAddress(7),
        opDeviceBusy(8),
        opDeviceOpenError(9),
        opDeviceError(10),
        opDeviceNotProgrammable(11),
        opDeviceFull(12),
        opFileOpenError(13),
        opFileTransferError(14),
        opFileChecksumError(15),
        opNoMemory(16),
        opAuthFail(17),
        opTimeout(18),
        opUnknownFailure(19),
        opDeleteFileOpenError(20),
        opDeleteInvalidDevice(21),
        opDeleteInvalidFunction(22),
        opDeleteOperationError(23),
        opDeleteInvalidFileName(24),
        opDeleteDeviceBusy(25),
        opDeleteParaError(26),
        opDeleteInvalidPath(27)
    }

--
-- Node definitions
--

-- Cf device management MIB object
    cfManMIBObjects OBJECT IDENTIFIER    ::= { cf 1 }


-- The cf device information.
cfDevice OBJECT IDENTIFIER    ::= { cfManMIBObjects 1 }

cfTable                OBJECT-TYPE
    SYNTAX          SEQUENCE OF CfEntry
    MAX-ACCESS      not-accessible
    STATUS          current
    DESCRIPTION
        "This table gives the properties of all the cfes on the system."
    ::= { cfDevice 1 }


cfEntry         OBJECT-TYPE
    SYNTAX          CfEntry
    MAX-ACCESS      not-accessible
    STATUS          current
    DESCRIPTION
        "The entry of cfTable."
    INDEX         { cfIndex }
    ::= { cfTable 1 }


CfEntry    ::=
    SEQUENCE {
        cfIndex
            Integer32,
        cfSize
             OCTET STRING,
        cfFree
            OCTET STRING,
        cfName
            OCTET STRING,
--            cfChipNum
--                Integer32,
        cfDescr
            OCTET STRING 
--            cfInitTime
--                TimeStamp
--            cfRemovable
--                TruthValue,
--            cfPartitionBool
--                TruthValue,
--            cfMinPartitionSize
--                Integer32,
--            cfMaxPartitions
--                Integer32,
--            cfPartitionNum
--                Integer32
     }

cfIndex         OBJECT-TYPE
    SYNTAX          Integer32 (1..2147483647)
    MAX-ACCESS      read-only
    STATUS          current
    DESCRIPTION
        "The index of cfTable.It has a minimum value of 1, and
        maximum value of the same as the value of cfSupportNum."
    ::= { cfEntry 1 }


cfSize         OBJECT-TYPE
    SYNTAX          OCTET STRING (SIZE (0..255))
    UNITS             "bytes"
    MAX-ACCESS      read-only
    STATUS          current
    DESCRIPTION
        "
        Specifies the total size of the cf device indexed
        by cfIndex.The value should be zero if the cf is
        removed for a removable device. "
    ::= { cfEntry 2 }


cfFree         OBJECT-TYPE
    SYNTAX          OCTET STRING (SIZE (0..255))
    UNITS             "bytes"
    MAX-ACCESS      read-only
    STATUS          current
    DESCRIPTION
        "Specifies the free size of the cf device."
    ::= { cfEntry 3 }


cfName                 OBJECT-TYPE
    SYNTAX          OCTET STRING (SIZE (0..16))
    MAX-ACCESS      read-only
    STATUS          current
    DESCRIPTION
        "The cf name within the system."
    ::= { cfEntry 4 }


--cfChipNum             OBJECT-TYPE
--    SYNTAX          Integer32 (1..64)
--    MAX-ACCESS      read-only
--    STATUS          current
--    DESCRIPTION
--        "The chip numbers in the cf."
--    ::= { cfEntry 5 }


    cfDescr OBJECT-TYPE
    SYNTAX          OCTET STRING (SIZE (0..64))
        MAX-ACCESS      read-only
        STATUS          current
        DESCRIPTION
            "Description of the purpose of the cf in the system."
        ::= { cfEntry 6 }



    cfFiles OBJECT IDENTIFIER ::= { cfDevice 2 }


    cfFileTable OBJECT-TYPE
    SYNTAX          SEQUENCE OF CfFileEntry
        MAX-ACCESS      not-accessible
        STATUS          current
        DESCRIPTION
            "Table of file information."
        ::= { cfFiles 1 }


    cfFileEntry OBJECT-TYPE
    SYNTAX          CfFileEntry
        MAX-ACCESS      not-accessible
        STATUS          current
        DESCRIPTION
            "
            An entry representing a file. Indexed using cf number,
            partition number, and file number.
            "
        INDEX {cfFileIndex }
        ::= { cfFileTable 1 }


    CfFileEntry ::=
        SEQUENCE {
            cfFileIndex
                Integer32,
            cfFileName
                OCTET STRING,
            cfFileSize
                Integer32,
            cfFileTime
                OCTET STRING
--         cfFileChecksum
--                OCTET STRING
         }

    cfFileIndex OBJECT-TYPE
    SYNTAX          Integer32 (0..2147483647)
        MAX-ACCESS      not-accessible
        STATUS          current
        DESCRIPTION
            "Index of the table, whose range is from 1 to 2147483647"
        ::= { cfFileEntry 1 }


    cfFileName OBJECT-TYPE
    SYNTAX          OCTET STRING (SIZE (1..255))
        MAX-ACCESS      read-only
        STATUS          current
        DESCRIPTION
            "A valid file name supported by the file system."
        ::= { cfFileEntry 2 }


    cfFileSize OBJECT-TYPE
    SYNTAX          Integer32
        MAX-ACCESS      read-only
        STATUS          current
        DESCRIPTION
            "
            The file size in bytes excluding the file
            header of file system. The value should be greater than zero.
            "
        ::= { cfFileEntry 3 }


    cfFileTime OBJECT-TYPE
    SYNTAX          OCTET STRING (SIZE (1..255))
        MAX-ACCESS      read-only
        STATUS          current
        DESCRIPTION
            "
            The time when this file is modified last time.
            "
        ::= { cfFileEntry 4 }


-- The operation on the cf.
    cfOperate OBJECT IDENTIFIER ::= { cfManMIBObjects 2 }


cfOpTable OBJECT-TYPE
    SYNTAX          SEQUENCE OF CfOpEntry
    MAX-ACCESS      not-accessible
    STATUS          current
    DESCRIPTION
        "Table used to operate cf."
    ::= { cfOperate 1 }


cfOpEntry OBJECT-TYPE
    SYNTAX          CfOpEntry
    MAX-ACCESS      not-accessible
    STATUS          current
    DESCRIPTION
        "Note an operation can not be stopped until it is finished.
        If notification is configured, NMS will receive a notification
        at the end of the operation.
        Entries in the table will be removed automatically in 5 minutes.
        It can also be deleted by NMS directly."
    INDEX { cfOperIndex }
    ::= { cfOpTable 1 }


    CfOpEntry ::=
        SEQUENCE {
            cfOperIndex
                Integer32,
            cfOperType
                INTEGER,
            cfOperProtocol
                INTEGER,
            cfOperServerAddress
                IpAddress,
            cfOperServerUser
                OCTET STRING,
            cfOperPassword
                OCTET STRING,
            cfOperSourceFile
                OCTET STRING ,
            cfOperDestinationFile
                OCTET STRING,
            cfOperStatus
                CfOperationStatus,
--            cfOperEndNotification
--                TruthValue,
--            cfOperProgress
--                TimeTicks,
            cfOperIsManagementIf 
                TruthValue,
            cfOperRowStatus
                RowStatus
         }

cfOperIndex OBJECT-TYPE
    SYNTAX          Integer32 (1..2147483647)
        MAX-ACCESS      not-accessible
        STATUS          current
        DESCRIPTION
            "Specifies the index of an entry. It is a
            random value when creating an entry."
        ::= { cfOpEntry 1 }


cfOperType OBJECT-TYPE
    SYNTAX          INTEGER
    {
        cf2Cf(1),
        net2Cf(2),
        cf2Net(3),
        delete(4),
        rename(5)
    }
    MAX-ACCESS      read-create
    STATUS          current
    DESCRIPTION
        "Specifies the operation to be executed.
        net2CfWithErase  Copy a file to cf; erase cf beforehand.
        net2CfWithoutErase   Copy a file to cf; do not erase cf
        beforehand.
        cf2Net       Copy a file from cf.
        delete       Delete a file from cf, the file name is
        specified by cfOperSourceFile;
        rename          Change a file's name."
    ::= { cfOpEntry 2 }
cfOperProtocol         OBJECT-TYPE
    SYNTAX          INTEGER
    {
        ftp(1),
        tftp(2)
    }
    MAX-ACCESS      read-create
    STATUS          current
    DESCRIPTION
        "Specifies the protocol used to transfer file.The default protocol is ftp.
        when 'clusterftp' or 'clustertftp' is selected, the cfOperServerAddress needn't
        be set the server address can be acquired automatically, the value of
        cfOperServerAddress is uncertain during operation.Both member switch and
         commander switch can use them if they support HGMP v2."
--  DEFVAL { ftp }
    ::= { cfOpEntry 3 }


cfOperServerAddress         OBJECT-TYPE
    SYNTAX          IpAddress
    MAX-ACCESS      read-create
    STATUS          current
    DESCRIPTION
        "The address of remote host acting as server for operation.
        The default value is 255.255.255.255."
-- DEFVAL { 'FFFFFFFF'h }
    ::= { cfOpEntry 4 }


cfOperServerUser         OBJECT-TYPE
    SYNTAX          OCTET STRING (SIZE (1..255))
    MAX-ACCESS      read-create
    STATUS          current
    DESCRIPTION
        "When using ftp to transfer files, the user name must be specified through
         this node."
    ::= { cfOpEntry 5 }


cfOperPassword         OBJECT-TYPE
    SYNTAX          OCTET STRING (SIZE (1..255))
    MAX-ACCESS      read-create
    STATUS          current
    DESCRIPTION
        "Remote user password for copying via ftp protocol.Optionally.
        This object may be ignored for protocols other than ftp."
    ::= { cfOpEntry 6 }


cfOperSourceFile      OBJECT-TYPE
    SYNTAX          OCTET STRING  (SIZE (0..255))
    MAX-ACCESS      read-create
    STATUS          current
    DESCRIPTION
        "Specifies the source file name to be transferred.
        It may be located on cf or remote server.
        It may include the file path if it is applicable.
        It must be specified."
    ::= { cfOpEntry 7 }


cfOperDestinationFile  OBJECT-TYPE
    SYNTAX          OCTET STRING (SIZE (0..255))
    MAX-ACCESS      read-create
    STATUS          current
    DESCRIPTION
        "Specifies the destination file name.
        It may be located on cf or remote server.
        It may include the file path if it is applicable.
        If it is not specified, the destination file name
        is the same as source file name for application."
    ::= { cfOpEntry 8 }


cfOperStatus          OBJECT-TYPE
    SYNTAX          CfOperationStatus
    MAX-ACCESS      read-only
    STATUS          current
    DESCRIPTION
        "The status of operation."
    ::= { cfOpEntry 9 }


--cfOperEndNotification    OBJECT-TYPE
--    SYNTAX          TruthValue
--    MAX-ACCESS      read-create
--    STATUS          current
--    DESCRIPTION
--        "
--            If the value of it is specified 'true', a notification
--            will be generated at the end of the operation.
--            Else no notification will be generated.
--        "
--        DEFVAL { false }
--    ::= { cfOpEntry 10 }
--
--
--cfOperProgress        OBJECT-TYPE
--    SYNTAX          TimeTicks
--    MAX-ACCESS      read-only
--    STATUS          current
--    DESCRIPTION
--        "The progress described as the time taken for the operation."
--    ::= { cfOpEntry 11 }


cfOperIsManagementIf     OBJECT-TYPE
    SYNTAX          TruthValue
    MAX-ACCESS      read-write
    STATUS          current
    DESCRIPTION
        "If use management interface running SNMP or not."
-- DEFVAL { true }    
    ::= { cfOpEntry 12 }
    
cfOperRowStatus        OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { cfOpEntry 13 }

-- Sub Module: SYSLOG


--
-- Textual conventions
--
MessageLevelType    ::= TEXTUAL-CONVENTION
    STATUS          current
    DESCRIPTION
        "Specify severity level of message."
    SYNTAX          INTEGER
            {
            emergency(0),
            alert(1),
            critical(2),
            error(3),
            warning(4),
            notice(5),
            informational(6),
            debug(7)
            }

MessageTrapLevelType    ::= TEXTUAL-CONVENTION
    STATUS          current
    DESCRIPTION
        "Specify severity level of message."
    SYNTAX          INTEGER
            {
            high(0),
            middle(1),
            lower(2),
            minor(3)
            }

TimeStampFormatType    ::= TEXTUAL-CONVENTION
    STATUS          current
    DESCRIPTION
        "Specify operation types on time stamp of message.
        none: no time stamp information in message.
        date: the time stamp type of message is date.
        boot: the time stamp type of message is the time from uptime of system.
        dateWithoutYear: the time stamp type of message is date without year 
        information."
    SYNTAX          INTEGER
        {
            bsd(0),
            iso(1),
            full(2),
            null(3)
            }

FacilityType    ::= TEXTUAL-CONVENTION
    STATUS          current
    DESCRIPTION
        "Specify loghost facility which generates messages."
    SYNTAX          INTEGER
        {
            kernel(0),
            userLevel(1),
            mailSystem(2),
            systemDaemons(3),
            securityAuthorization(4),
            syslog(5),
            linePrinter(6),
            networkNews(7),
            uucp(8),
            cron(9),
            securityAuthorization2(10),
            ftpDaemon(11),
            ntp(12),
            logAudit(13),
            logAlert(14),
            clockDaemon2(15),
            local0(16),
            local1(17),
            local2(18),
            local3(19),
            local4(20),
            local5(21),
            local6(22),
            local7(23)
            }

--
--
-- Node definitions
--
syslogTimestamp         OBJECT-TYPE
    SYNTAX          TimeStampFormatType
    MAX-ACCESS      read-write
    STATUS          current
    DESCRIPTION
        "The log timestamp type.
        0 RBSD(RFC3164 or bsd).
        1 RISO(RFC3339 or iso).
        2 RFULL(date).
        3 NONE."
    ::= { syslog 1 }

syslogOperateLogEnable         OBJECT-TYPE
    SYNTAX          TruthValue
    MAX-ACCESS      read-write
    STATUS          current
    DESCRIPTION
        "The state of log operate true(1):enable.false(2):disable."
    ::= { syslog 2 }

syslogBuffer OBJECT IDENTIFIER    ::= { syslog 3 }
syslogBufferMaxSize          OBJECT-TYPE
    SYNTAX          INTEGER(10..1000)
    MAX-ACCESS      read-write
    STATUS          current
    DESCRIPTION
        "The maximum number of messages that can be storedin logbuffer.MaxSize range 10~1000."
    ::= { syslogBuffer 1 }

syslogbufferSeverity         OBJECT-TYPE
    SYNTAX          MessageLevelType
    MAX-ACCESS      read-write
    STATUS          current
    DESCRIPTION
        "The operations staff can selectively filter the messages
         with priority which consists of severity that generates
         the message and severity of the message.Range 0~7.
        "
 --   DEFVAL { 7 }
    ::= { syslogBuffer 2 }

syslogBuffercurrentMessages         OBJECT-TYPE
    SYNTAX          Unsigned32
    MAX-ACCESS      read-only
    STATUS          current
    DESCRIPTION
        "The number of log messages stored in logbuffer."
    ::= { syslogBuffer 3 }

syslogBufferDroppedMessages         OBJECT-TYPE
    SYNTAX          Counter32
    MAX-ACCESS      read-only
    STATUS          current
    DESCRIPTION
        "The number of log messages dropped in logbuffer."
    ::= { syslogBuffer 4 } 
--

syslogFile OBJECT IDENTIFIER    ::= { syslog 4 }

syslogFileEnable         OBJECT-TYPE
    SYNTAX          TruthValue
    MAX-ACCESS      read-write
    STATUS          current
    DESCRIPTION
        "The state of log merge true(1):enable.false(2):disable."
    ::= { syslogFile 1 }

syslogFileSeverity         OBJECT-TYPE
    SYNTAX          MessageLevelType
    MAX-ACCESS      read-write
    STATUS          current
    DESCRIPTION
        "The operations staff can selectively filter the messages with priority
         which consists of severity that generates the message and severity of 
         the message.Range 0~7."
    ::= { syslogFile 2 }


syslogServer OBJECT IDENTIFIER    ::= { syslog 5 } 

syslogServerEnable         OBJECT-TYPE
    SYNTAX          TruthValue
    MAX-ACCESS      read-write
    STATUS          current
    DESCRIPTION
        "The state of syslogtrap: true(1): enable.false(2): disable."
    ::= { syslogServer 1 }

syslogServerFacility         OBJECT-TYPE
    SYNTAX          FacilityType
    MAX-ACCESS      read-write
    STATUS          current
    DESCRIPTION
        "The operations staff can selectively filter the messages with priority
         which consists of facility that generates the message and severity of
          the message.Value range 0~11 or 16~23."
   -- DEFVAL { local7 }
    ::= { syslogServer 2 }

syslogServerSeverity         OBJECT-TYPE
    SYNTAX          MessageLevelType
    MAX-ACCESS      read-write
    STATUS          current
    DESCRIPTION
        "The operations staff can selectively filter the messages with priority 
        which consists of severity that generates the message and severity of 
        the message.Value range 0~7.default 4"
    ::= { syslogServer 3 }

syslogServerTable         OBJECT-TYPE
    SYNTAX          SEQUENCE OF SyslogServerEntry
    MAX-ACCESS      not-accessible
    STATUS          current
    DESCRIPTION
        "The table of loghost."
    ::= { syslogServer 4 }

syslogServerEntry         OBJECT-TYPE
    SYNTAX          SyslogServerEntry
    MAX-ACCESS      not-accessible
    STATUS          current
    DESCRIPTION
        "The loghost entry of syslog."
    INDEX    { syslogServerIpaddress, syslogServerMgmtIf }
    ::= { syslogServerTable 1 }

SyslogServerEntry    ::=
    SEQUENCE {
        syslogServerIpaddress
            IpAddress,
        syslogServerMgmtIf
            INTEGER,
        syslogServerRowStatus 
RowStatus 
    }

syslogServerIpaddress         OBJECT-TYPE
    SYNTAX          IpAddress
    MAX-ACCESS      read-only
    STATUS          current
    DESCRIPTION
        "The ip address of loghost."
    ::= { syslogServerEntry 1 }

syslogServerMgmtIf         OBJECT-TYPE
    SYNTAX          INTEGER
    {
        noUse(1),
        useMgmtIf(2)
    }
    MAX-ACCESS      read-only
    STATUS          current
    DESCRIPTION
        "The mgmt if of loghost.
        1  noUse.
        2  useMgmtIf."
    ::= { syslogServerEntry 2 }

syslogServerRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { syslogServerEntry 3 }

syslogTrap OBJECT IDENTIFIER    ::= { syslog 6 }

syslogTrapEnable         OBJECT-TYPE
    SYNTAX          TruthValue
    MAX-ACCESS      read-write
    STATUS          current
    DESCRIPTION
        "The state of syslog trap. true(1):enable.false(2):disable."
    ::= { syslogTrap 1 }

syslogTrapSeverity         OBJECT-TYPE
    SYNTAX          MessageTrapLevelType
    MAX-ACCESS      read-write
    STATUS          current
    DESCRIPTION
        "The operations staff can selectively filter the messages with priority
         which consists of severity that generates the message and severity of
          the message.
          0 high.
          1 middle.
          2 lower.
          3 minor."
    ::= { syslogTrap 2 }

syslogMerge OBJECT IDENTIFIER    ::= { syslog 7 }

syslogMergeEnable         OBJECT-TYPE
    SYNTAX          TruthValue
    MAX-ACCESS      read-write
    STATUS          current
    DESCRIPTION
        "The state of log merge true(1):enable.false(2):disable."
    ::= { syslogMerge 1 }

syslogMergeFifoSize         OBJECT-TYPE
    SYNTAX          INTEGER(100..10240)
    MAX-ACCESS      read-write
    STATUS          current
    DESCRIPTION
        "The logging merge fifo-size, specify the logging merge buffer."
    ::= { syslogMerge 2 }

syslogMergeTimeout         OBJECT-TYPE
    SYNTAX          INTEGER(1..300)
    MAX-ACCESS      read-write
    STATUS          current
    DESCRIPTION
        "The logging merge timeout value, specify the logging merge interval.default 10."
    ::= { syslogMerge 3 }

syslogSync        OBJECT-TYPE
    SYNTAX          INTEGER
    MAX-ACCESS      read-write
    STATUS          current
    DESCRIPTION
        "Specify sync parameter. true(1): sync the syslog and return value is always 0."
    ::= { syslog 8 }

syslogClearLogBuff        OBJECT-TYPE
    SYNTAX          INTEGER
    MAX-ACCESS      read-write
    STATUS          current
    DESCRIPTION
        "Clear logging buffer. true(1): clear the logging buffer and return value is always 0."
    ::= { syslog 9 }    

-- Sub Module: MIRROR


mSSrcIfTable         OBJECT-TYPE
    SYNTAX          SEQUENCE OF MSSrcIfEntry
    MAX-ACCESS      not-accessible
    STATUS          current
    DESCRIPTION
        "A list of mirror session source port entries."
    ::= { mirror 1 }

mSSrcIfEntry         OBJECT-TYPE
    SYNTAX          MSSrcIfEntry
    MAX-ACCESS      not-accessible
    STATUS          current
    DESCRIPTION
        "A list of parameters that describe a source port to be added to a mirror
         session."
    INDEX    
    {
        mSSrcIfID,
        mSSrcIfIndex
    }
    ::= { mSSrcIfTable 1 }

MSSrcIfEntry    ::=
    SEQUENCE
    {
        mSSrcIfID         
            Integer32,  
        mSSrcIfIndex       
            Integer32,
        mSSrcIfDirection   
            INTEGER,            
        mSSrcIfRowStatus 
RowStatus 
    }

mSSrcIfID         OBJECT-TYPE
    SYNTAX          Integer32 (1..3)
    MAX-ACCESS      not-accessible
    STATUS          current
    DESCRIPTION
        "An index that uniquely identifies an entry in the mirror session table."
    ::= { mSSrcIfEntry 1 }
    
mSSrcIfIndex         OBJECT-TYPE
    SYNTAX          Integer32 (1..65535)
    MAX-ACCESS      not-accessible
    STATUS          current
    DESCRIPTION
        "IfIndex of mirror group source port. including ethernet port and agg port"
    ::= { mSSrcIfEntry 2 }

mSSrcIfDirection         OBJECT-TYPE
    SYNTAX          INTEGER
                {
                    rx(1),
                    tx(2),
                    both(3)
                }
    MAX-ACCESS      read-create
    STATUS          current
    DESCRIPTION
        "Mirror direction of source port.if the direction first  configured 
        as rx, then configure tx, then the direction  will be both."
    ::= { mSSrcIfEntry 3 }

mSSrcIfRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { mSSrcIfEntry 4 }        


mSSrcVlanTable         OBJECT-TYPE
    SYNTAX          SEQUENCE OF MSSrcVlanEntry
    MAX-ACCESS      not-accessible
    STATUS          current
    DESCRIPTION
        "A list of mirror session source vlan entries."
    ::= { mirror 2 }

mSSrcVlanEntry         OBJECT-TYPE
    SYNTAX          MSSrcVlanEntry
    MAX-ACCESS      not-accessible
    STATUS          current
    DESCRIPTION
        "A list of parameters that describe a source vlan to be added to a mirror session."
    INDEX     
    {
        mSSrcVlanID,
        mSSrcVlanNum
    }
    ::= { mSSrcVlanTable 1 }

MSSrcVlanEntry    ::=
    SEQUENCE
    {
        mSSrcVlanID          
            Integer32,  
        mSSrcVlanNum         
            Integer32,
        mSSrcVlanDirection   
            INTEGER,            
        mSSrcVlanRowStatus 
RowStatus 
    }

mSSrcVlanID         OBJECT-TYPE
    SYNTAX          Integer32 (1..3)
    MAX-ACCESS      not-accessible
    STATUS          current
    DESCRIPTION
        "An index that uniquely identifies an entry in the mirror session table."
    ::= { mSSrcVlanEntry 1 }
    
mSSrcVlanNum         OBJECT-TYPE
    SYNTAX          Integer32 (1..4094)
    MAX-ACCESS      not-accessible
    STATUS          current
    DESCRIPTION
        "IfIndex of mirror group source vlan."
    ::= { mSSrcVlanEntry 2 }

mSSrcVlanDirection         OBJECT-TYPE
    SYNTAX          INTEGER
                {
                    rx(1),
                    tx(2),
                    both(3)
                }
    MAX-ACCESS      read-create
    STATUS          current
    DESCRIPTION
        "Mirror direction of source vlan.if the direction first configured as
         rx, then configure tx, then the direction will be both."
    ::= { mSSrcVlanEntry 3 }

mSSrcVlanRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { mSSrcVlanEntry 4 }

mSDestIfTable         OBJECT-TYPE
    SYNTAX          SEQUENCE OF MSDestIfEntry
    MAX-ACCESS      not-accessible
    STATUS          current
    DESCRIPTION
        "A list of mirror group dest port entries."
    ::= { mirror 3 }

mSDestIfEntry         OBJECT-TYPE
    SYNTAX          MSDestIfEntry
    MAX-ACCESS      not-accessible
    STATUS          current
    DESCRIPTION
        "A list of parameters that describe a dest port to be added to a mirror group."
    INDEX    
    {
        mSDestIfID
    }
    ::= { mSDestIfTable 1 }

MSDestIfEntry    ::=
    SEQUENCE
    {
        mSDestIfID          
            Integer32,
        mSDestIfIndex       
            Integer32,
        mSSessionType          
            INTEGER,  
        mSDestVlanID          
            Integer32,  
        mSDestIfRowStatus 
RowStatus 
    }
    
mSDestIfID         OBJECT-TYPE
    SYNTAX          Integer32 (1..3)
    MAX-ACCESS      not-accessible
    STATUS          current
    DESCRIPTION
        "An index that uniquely identifies an entry in the mirror session table."
    ::= { mSDestIfEntry 1 }

mSDestIfIndex         OBJECT-TYPE
    SYNTAX          Integer32 (1..1023)
    MAX-ACCESS      read-create
    STATUS          current
    DESCRIPTION
        "IfIndex of mirror group dest port. only ethernet port. "
    ::= { mSDestIfEntry 2 }

mSSessionType         OBJECT-TYPE
    SYNTAX          INTEGER
                {
                    local(1),
                    remote(2)
                }
    MAX-ACCESS      read-create
    STATUS          current
    DESCRIPTION
        "session type."
    ::= { mSDestIfEntry 3 }

mSDestVlanID         OBJECT-TYPE
    SYNTAX          Integer32 (2..4094)
    MAX-ACCESS      read-create
    STATUS          current
    DESCRIPTION
        "IfIndex of mirror group dest vlan."
    ::= { mSDestIfEntry 4 }
mSDestIfRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { mSDestIfEntry 5 }  
    
mSTable         OBJECT-TYPE
    SYNTAX          SEQUENCE OF MSEntry
    MAX-ACCESS      not-accessible
    STATUS          current
    DESCRIPTION
        "A list of mirror group entries."
    ::= { mirror 4 }

mSEntry                OBJECT-TYPE
    SYNTAX          MSEntry
    MAX-ACCESS      not-accessible
    STATUS          current
    DESCRIPTION
        "A list of parameters that describe a mirror group."
    INDEX    
    {
        mSID
    }
    ::= { mSTable 1 }

MSEntry    ::=
    SEQUENCE
    {
        mSID          
            Integer32,
        mSType        
            INTEGER,
        mSStatus 
            INTEGER,
        mSRowStatus 
RowStatus 
    }
    
mSID         OBJECT-TYPE
    SYNTAX          Integer32 (0..65535)
    MAX-ACCESS      not-accessible
    STATUS          current
    DESCRIPTION
        "An index that uniquely identifies an entry in the mirror session table."
    ::= { mSEntry 1 }

mSType         OBJECT-TYPE
    SYNTAX          INTEGER
                {
                    local(1)  ,
                    remote(2)                    
                }       
    MAX-ACCESS      read-only
    STATUS          current
    DESCRIPTION
        "The type of a mirror session.
        1 Local.
        2 remote."
    ::= { mSEntry 2 }
    
mSStatus         OBJECT-TYPE        
    SYNTAX          INTEGER
                {
                    active(1),
                    inactive(2)
                }
    MAX-ACCESS      read-only
    STATUS          current
    DESCRIPTION
        "The status of a mirror session.A mirror session will be active only when it has destination port.
        1 Active.
        2 Inactive."
    ::= { mSEntry 3 }

mSRowStatus            OBJECT-TYPE
    SYNTAX          RowStatus
    MAX-ACCESS      read-create
    STATUS          current
    DESCRIPTION
        "The status of this conceptual row.Now only realize Destroy and Active."
    ::= { mSEntry 4 } 
--
--mSEscapeMacTable
--

mSEscapeMacTable         OBJECT-TYPE
    SYNTAX          SEQUENCE OF MSEscapeMacEntry
    MAX-ACCESS      not-accessible
    STATUS          current
    DESCRIPTION
        "A list of mirror session escape mac entries."
    ::= { mirror 5 }

mSEscapeMacEntry         OBJECT-TYPE
    SYNTAX          MSEscapeMacEntry
    MAX-ACCESS      not-accessible
    STATUS          current
    DESCRIPTION
        "A list of parameters that describe a escape mac to be added to a mirror session."
    INDEX     
    {
        mSEscapeMacIndex
    }
    ::= { mSEscapeMacTable 1 }

MSEscapeMacEntry    ::=
    SEQUENCE
    {
        mSEscapeMacIndex          
            INTEGER,  
        mSEscapeMacAddress          
            OCTET STRING,  
        mSEscapeMacMask         
            OCTET STRING,
        mSEscapeMacRowStatus 
			RowStatus 
    }

mSEscapeMacIndex         OBJECT-TYPE        
    SYNTAX          INTEGER(1..2)
    MAX-ACCESS      not-accessible
    STATUS          current
    DESCRIPTION
        "The index of a escape mac.Range 1~2."
    ::= { mSEscapeMacEntry 1 }

mSEscapeMacAddress         OBJECT-TYPE
    SYNTAX          OCTET STRING(SIZE(1..15))
    MAX-ACCESS      read-create
    STATUS          current
    DESCRIPTION
        "Specify certain mac address as special and not mirror."
    ::= { mSEscapeMacEntry 2 }
    
mSEscapeMacMask         OBJECT-TYPE
    SYNTAX          OCTET STRING(SIZE(1..15))
    MAX-ACCESS      read-create
    STATUS          current
    DESCRIPTION
        "Mac mask of mirror Specify certain mac address."
    ::= { mSEscapeMacEntry 3 }

mSEscapeMacRowStatus         OBJECT-TYPE
    SYNTAX          RowStatus
    MAX-ACCESS      read-create
    STATUS          current
    DESCRIPTION
        "The status of this conceptual row.Now only realize CreateAndGo(4) and Destroy(6) and Active(1).
        1 means Active
        4 means CreateAndGo
        6 means Destroy"
    ::= { mSEscapeMacEntry 4 }


-- Sub Module: PORTSECURITY



--
-- Node definitions
--

portSecurityObject OBJECT IDENTIFIER    ::= { portSecurity 1 }

portSecurityPortTable         OBJECT-TYPE
    SYNTAX          SEQUENCE OF PortSecurityPortEntry
    MAX-ACCESS      not-accessible
    STATUS          current
    DESCRIPTION
        "This table defines the securityStatus of each secure port.
           Each port can have a number of authorised MAC addresses, and these are
            stored in the portSecurityStaticAddressTable and 
            portSecurityDynamicAddressTable."
    ::= { portSecurityObject 1 }

portSecurityPortEntry         OBJECT-TYPE
    SYNTAX          PortSecurityPortEntry
    MAX-ACCESS      not-accessible
    STATUS          current
    DESCRIPTION
        "There is a Rowin this table for each secure port and It is indexed
         using the object ifIndex in RFC1213-MIB."
    INDEX    
    {
        ifIndex
    }
    ::= { portSecurityPortTable 1 }

PortSecurityPortEntry    ::=
    SEQUENCE {
        portSecurityEnable
                INTEGER,
        portSecurityViolationMode
                INTEGER,
        portSecurityMaximumNumberOfMacAddresses
                Integer32,
                portSecurityCurrentNumberOfMacAddresses
                Integer32
    }

portSecurityEnable         OBJECT-TYPE
    SYNTAX          INTEGER {enabled(1),disabled(2)}
    MAX-ACCESS      read-write
    STATUS          current
    DESCRIPTION
        "This attribute controls the system wide operation of mac-authentication.
          The system-wide mac-authentication options become non-operational
           when this attribute is set to disabled."
    ::= { portSecurityPortEntry 1 }

portSecurityViolationMode         OBJECT-TYPE
    SYNTAX          INTEGER
    {
         protect(0),
         restrict(1),
         shutdown(2)
    }
    MAX-ACCESS      read-write
    STATUS          current
    DESCRIPTION
        "This attribute determines what action to be taken when a security violation is detected
        protect(0): discard packet silently
	   restrict(1): discard packet and print log
	   shutdown(2): discard packet, log and set the interface error-disabled."
    ::= { portSecurityPortEntry 2 }

portSecurityMaximumNumberOfMacAddresses         OBJECT-TYPE
    SYNTAX          Integer32
    MAX-ACCESS      read-write
    STATUS          current
    DESCRIPTION
        "This indicates the maximum value that mac addresses can be learned.
        Those objects are bound by the relationship: 
        staticNumberOfConfiguredMacAddresses
         <= totalNumberOfMacAddresses
         <= portSecurityMaximumMacAddresses."
    ::= { portSecurityPortEntry 3 }

    portSecurityCurrentNumberOfMacAddresses OBJECT-TYPE
    SYNTAX          Integer32
    MAX-ACCESS      read-only
    STATUS          current
    DESCRIPTION
        "This indicates thecurrent number of Mac Addresses."
    ::= { portSecurityPortEntry 4 }


portSecurityStaticAddressTable         OBJECT-TYPE
    SYNTAX          SEQUENCE OF PortSecurityStaticAddressEntry
    MAX-ACCESS      not-accessible
    STATUS          current
    DESCRIPTION
        "This table stores the static MAC addresses assigned to each port."
    ::= { portSecurityObject 2 }

portSecurityStaticAddressEntry         OBJECT-TYPE
    SYNTAX          PortSecurityStaticAddressEntry
    MAX-ACCESS      not-accessible
    STATUS          current
    DESCRIPTION
        "This table stores the static MAC addresses assigned to each port."
    INDEX  
    {
        ifIndex,
        portSecurityStaticMacAddress,
        portSecurityStaticVlanId
    }
    ::= { portSecurityStaticAddressTable 1 }

 PortSecurityStaticAddressEntry    ::=
    SEQUENCE {
            portSecurityStaticPortIndex
                Integer32,    
            portSecurityStaticVlanId
                Integer32,
            portSecurityStaticMacAddress
                Integer32,
            portSecurityStaticRowStatus 
                RowStatus 
        }

portSecurityStaticPortIndex         OBJECT-TYPE
    SYNTAX          Integer32
    MAX-ACCESS      not-accessible
    STATUS          current
    DESCRIPTION
        "The port index which port security is configured.
             This is the first index into the portSecurityStaticAddressTable."
    ::= { portSecurityStaticAddressEntry 1 }        

portSecurityStaticVlanId         OBJECT-TYPE
    SYNTAX          Integer32 
    MAX-ACCESS      not-accessible
    STATUS          current
    DESCRIPTION
        "The Vlan ID associate with the port and the MAC address.
             This is the second index into the portSecurityStaticAddressTable."
    ::= { portSecurityStaticAddressEntry 2 }

portSecurityStaticMacAddress         OBJECT-TYPE
    SYNTAX          Integer32
    MAX-ACCESS      not-accessible
    STATUS          current
    DESCRIPTION
        "The MAC address of a station assigned to this port. 
         The index format of mac address '01:02:0a:0b:ff:ff' should be '1.2.10.11.255.255'
            This is the third index into the portSecurityStaticAddressTable."
    ::= { portSecurityStaticAddressEntry 3 }

portSecurityStaticRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { portSecurityStaticAddressEntry 4 }

portSecurityDynamicAddressTable         OBJECT-TYPE
    SYNTAX          SEQUENCE OF PortSecurityDynamicAddressEntry
    MAX-ACCESS      not-accessible
    STATUS          current
    DESCRIPTION
        "This table stores the dynamic MAC addresses which
             are learned each port."
    ::= { portSecurityObject 3 }

portSecurityDynamicAddressEntry         OBJECT-TYPE
    SYNTAX          PortSecurityDynamicAddressEntry
    MAX-ACCESS      not-accessible
    STATUS          current
    DESCRIPTION
        "This table stores the dynamic MAC addresses which
             are learned each port."
    INDEX      
        {
            ifIndex,
            portSecurityDynamicMacAddress,
            portSecurityDynamicVlanId
        }
    ::= { portSecurityDynamicAddressTable 1 }

PortSecurityDynamicAddressEntry    ::=
    SEQUENCE {
            portSecurityDynamicVlanId
                    Integer32,
            portSecurityDynamicMacAddress
                    MacAddress,
            portSecurityDynamicPortName
                    OCTET STRING
        }

portSecurityDynamicVlanId         OBJECT-TYPE
    SYNTAX          Integer32 (0..65535)
    MAX-ACCESS      read-only
    STATUS          current
    DESCRIPTION
        "The Vlan ID associate with the port and the MAC address.
             This is the third index into the portSecurityDynamicAddressTable."
    ::= { portSecurityDynamicAddressEntry 1 }

portSecurityDynamicMacAddress         OBJECT-TYPE
    SYNTAX          MacAddress
    MAX-ACCESS      read-only
    STATUS          current
    DESCRIPTION
        "The MAC address of a station assigned to this port.This
             is the second index into the portSecurityDynamicAddressTable."
    ::= { portSecurityDynamicAddressEntry 2 }

portSecurityDynamicPortName         OBJECT-TYPE
    SYNTAX          OCTET STRING (SIZE(1..10))
    MAX-ACCESS      read-only
    STATUS          current
    DESCRIPTION
        "The port name which port security is configured."
    ::= { portSecurityDynamicAddressEntry 3 }

-- Sub Module:stormCONTROL


stormControlObject OBJECT IDENTIFIER    ::= {stormControl 1 }

stormControlUnicastTable OBJECT-TYPE
    SYNTAX          SEQUENCE OF StormControlUnicastEntry
    MAX-ACCESS      not-accessible
    STATUS          current
    DESCRIPTION
        "This table stores the port name and storm control 
        unicast mode,level and pps. "
    ::= { stormControlObject 1 }
   
stormControlUnicastEntry OBJECT-TYPE
    SYNTAX          StormControlUnicastEntry
    MAX-ACCESS      not-accessible
    STATUS          current
    DESCRIPTION
        "This table stores the port name and storm control  unicast mode and level. "
    INDEX
        {
            ifIndex
        }
            
    ::= { stormControlUnicastTable 1 }

StormControlUnicastEntry    ::=
    SEQUENCE {
        stormControlUnicastPortName
            OCTET STRING,
        stormControlUnicastMode
            INTEGER,
        stormControlUnicastLevel
            OCTET STRING ,
        stormControlUnicastPps
            Integer32,
        stormControlUnicastRowStatus 
            RowStatus 
        }
        
stormControlUnicastPortName         OBJECT-TYPE
    SYNTAX          OCTET STRING (SIZE(0..255))
    MAX-ACCESS      read-only
    STATUS          current
    DESCRIPTION
        "The name of interface which is configuredstorm 
             control."
    ::= {stormControlUnicastEntry 1 }

stormControlUnicastMode         OBJECT-TYPE
    SYNTAX          INTEGER
            {
                packetPerSecond(1),
                level(2)
            }
    MAX-ACCESS      read-create
    STATUS          current
    DESCRIPTION
        "This indicates which unicast mode is configured whenstorm control is used.
        1 PacketPerSecond.
        2 Level."
    ::= {stormControlUnicastEntry 2 }              

stormControlUnicastLevel         OBJECT-TYPE
    SYNTAX          OCTET STRING (SIZE(1..6))
    MAX-ACCESS      read-create
    STATUS          current
    DESCRIPTION
        "When unicast mode is configured Level,this 
                 indicates the percentage of bandwith.
                  The valid range is (0.00-100.00)."
    ::= {stormControlUnicastEntry 3 }  
    
stormControlUnicastPps         OBJECT-TYPE
    SYNTAX          Integer32 (0..1000000000)
    MAX-ACCESS      read-create
    STATUS          current
    DESCRIPTION
        "When unicast mode is configured PacketPerSecond, 
                 this indicates the number of packet per second."
    ::= {stormControlUnicastEntry 4 }
stormControlUnicastRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= {stormControlUnicastEntry 5 }      
                           
stormControlBroadcastTable OBJECT-TYPE
    SYNTAX          SEQUENCE OF StormControlBroadcastEntry
    MAX-ACCESS      not-accessible
    STATUS          current
    DESCRIPTION
        "This table stores the port name and storm control 
        broadcast mode,level and pps. "
    ::= { stormControlObject 2 }
                
stormControlBroadcastEntry         OBJECT-TYPE
    SYNTAX          StormControlBroadcastEntry
    MAX-ACCESS      not-accessible
    STATUS          current
    DESCRIPTION
        "This table stores the port name andstorm control broadcast mode and level."
    INDEX            
            {
                ifIndex
            }
    ::= {stormControlBroadcastTable 1 }

StormControlBroadcastEntry    ::=
    SEQUENCE {
        stormControlBroadcastPortName
            OCTET STRING ,
        stormControlBroadcastMode
            INTEGER,
        stormControlBroadcastLevel
            OCTET STRING ,
        stormControlBroadcastPps
            Integer32,
        stormControlBroadcastRowStatus 
            RowStatus 
            }
            
stormControlBroadcastPortName         OBJECT-TYPE
    SYNTAX          OCTET STRING (SIZE(0..255))
    MAX-ACCESS      read-only
    STATUS          current
    DESCRIPTION
        "The name of interface which is configuredstorm 
                 control."
    ::= {stormControlBroadcastEntry 1 }

stormControlBroadcastMode         OBJECT-TYPE
    SYNTAX          INTEGER
            {
                packetPerSecond(1),
                level(2)
            }
    MAX-ACCESS      read-create
    STATUS          current
    DESCRIPTION
        "This indicates which broadcast mode is configured whenstorm control is used.
        1 PacketPerSecond.
        2 Level."
    ::= {stormControlBroadcastEntry 2 }              

stormControlBroadcastLevel         OBJECT-TYPE
    SYNTAX          OCTET STRING (SIZE(1..6))
    MAX-ACCESS      read-create
    STATUS          current
    DESCRIPTION
        "When broadcast mode is configured Level,this 
                 indicates the percentage of bandwith.
                  The valid range is (0.00-100.00)."
    ::= {stormControlBroadcastEntry 3 }  
    
stormControlBroadcastPps         OBJECT-TYPE
    SYNTAX          Integer32 (0..1000000000)
    MAX-ACCESS      read-create
    STATUS          current
    DESCRIPTION
        "When broadcast mode is configured PacketPerSecond, 
                 this indicates the number of packet per second."
    ::= {stormControlBroadcastEntry 4 }
stormControlBroadcastRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= {stormControlBroadcastEntry 5 }    
                                     
stormControlMulticastTable         OBJECT-TYPE
    SYNTAX          SEQUENCE OF StormControlMulticastEntry
    MAX-ACCESS      not-accessible
    STATUS          current
    DESCRIPTION
        "This table stores the port name andstorm control 
                 multicast mode and level."
    ::= {stormControlObject 3 }
       
stormControlMulticastEntry         OBJECT-TYPE
    SYNTAX          StormControlMulticastEntry
    MAX-ACCESS      not-accessible
    STATUS          current
    DESCRIPTION
        "This table stores the port name andstorm control 
                 multicast,level and pps."
    INDEX            
            {
                ifIndex
            }
    ::= {stormControlMulticastTable 1 }

StormControlMulticastEntry    ::=
    SEQUENCE {
        stormControlMulticastPortName
            OCTET STRING ,
        stormControlMulticastMode
            INTEGER,
        stormControlMulticastLevel
            OCTET STRING ,
        stormControlMulticastPps
            Integer32,
        stormControlMulticastRowStatus 
             RowStatus 
            }

stormControlMulticastPortName         OBJECT-TYPE
    SYNTAX          OCTET STRING (SIZE(0..255))
    MAX-ACCESS      read-only
    STATUS          current
    DESCRIPTION
        "The name of interface which is configuredstorm control."
    ::= {stormControlMulticastEntry 1 }
            
stormControlMulticastMode         OBJECT-TYPE
    SYNTAX          INTEGER
            {
                packetPerSecond(1),
                level(2)
            }
    MAX-ACCESS      read-create
    STATUS          current
    DESCRIPTION
        "This indicates which multicast mode is configured whenstorm control is used.
        1 PacketPerSecond.
        2 Level."
    ::= {stormControlMulticastEntry 2 }              

stormControlMulticastLevel         OBJECT-TYPE
    SYNTAX          OCTET STRING (SIZE(1..6))
    MAX-ACCESS      read-create
    STATUS          current
    DESCRIPTION
        "When multicast mode is configured Level,this indicates the percentage
         of bandwith. The valid range is (0.00-100.00)."
    ::= {stormControlMulticastEntry 3 }  
    
stormControlMulticastPps         OBJECT-TYPE
    SYNTAX          Integer32 (0..1000000000)
    MAX-ACCESS      read-create
    STATUS          current
    DESCRIPTION
        "When multicast mode is configured PacketPerSecond, this indicates the 
        number of packet per second."
    ::= {stormControlMulticastEntry 4 }   
stormControlMulticastRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= {stormControlMulticastEntry 5 }    
                        
-- Sub Module: NTP



ntpObject OBJECT IDENTIFIER    ::= { ntp 1 }

ntpStratum         OBJECT-TYPE
    SYNTAX          OCTET STRING (SIZE (0..255))
    MAX-ACCESS      read-only
    STATUS          current
    DESCRIPTION
        "This is an eight-bit integer indicating the stratum level
            of the local clock, with values defined as follows:
            0, unspecified
            1, primary reference (e.g.,, radio clock)
            2-255, secondary reference (via NTP)        "
    ::= { ntpObject 1 }

ntpReferenceClockIp         OBJECT-TYPE
    SYNTAX          IpAddress
    MAX-ACCESS      read-only
    STATUS          current
    DESCRIPTION
        "The IP address of the reference clock ip address."
    ::= { ntpObject 2 }

ntpFrequency         OBJECT-TYPE
    SYNTAX          OCTET STRING (SIZE (0..255))
    MAX-ACCESS      read-only
    STATUS          current
    DESCRIPTION
        "The frequency of local clock relative to the primary
             reference source."
    ::= { ntpObject 3 }
        
ntpPrecision         OBJECT-TYPE
    SYNTAX          OCTET STRING (SIZE (0..255))
    MAX-ACCESS      read-only
    STATUS          current
    DESCRIPTION
        "Precision : This is a signed integer indicating the
            precision relative to the reference clock ip."
    ::= { ntpObject 4 }

ntpReferenceTime         OBJECT-TYPE
    SYNTAX          OCTET STRING (SIZE (0..255))
    MAX-ACCESS      read-only
    STATUS          current
    DESCRIPTION
        "This is the local time."
    ::= { ntpObject 5 }

ntpRootDelay         OBJECT-TYPE
    SYNTAX          OCTET STRING (SIZE (0..255))
    MAX-ACCESS      read-only
    STATUS          current
    DESCRIPTION
        "This is a signed fixed-point number indicating
            the total roundtrip delay to the primary reference source
            at the root of the synchronization subnet, in seconds."
    ::= { ntpObject 6 }   
        
ntpRootDispersion         OBJECT-TYPE
    SYNTAX          OCTET STRING (SIZE (0..255))
    MAX-ACCESS      read-only
    STATUS          current
    DESCRIPTION
        "Root Dispersion : This is a signed fixed-point number
            indicating the maximum error relative to the primary
            reference source at the root of the synchronization
            subnet, in seconds.Only positive values greater than
            zero are possible."
    ::= { ntpObject 7 }   

ntpPeerDispersion         OBJECT-TYPE
    SYNTAX          OCTET STRING (SIZE (0..255))
    MAX-ACCESS      read-only
    STATUS          current
    DESCRIPTION
        "This is a signed fixed-point number indicating
            the maximum error of the local clock relative to
            the primary reference source at the root of the
            synchronization subnet.Only positive values
            greater than zero are possible."
    ::= { ntpObject 8 }  
        
ntpClockOffset         OBJECT-TYPE
    SYNTAX          OCTET STRING (SIZE (0..255))
    MAX-ACCESS      read-only
    STATUS          current
    DESCRIPTION
        "This is a signed, fixed-point number indicating the offset
            of the local clock relative to the primary clock, in seconds."
    ::= { ntpObject 9 }

ntpStability         OBJECT-TYPE
    SYNTAX          OCTET STRING (SIZE (0..255))
    MAX-ACCESS      read-only
    STATUS          current
    DESCRIPTION
        "This is a signed, fixed-point number indicating the stability
            of the local clock relative to the primary clock, in seconds."
    ::= { ntpObject 10 }

ntpAssoTable         OBJECT-TYPE
    SYNTAX          SEQUENCE OF NtpAssoEntry
    MAX-ACCESS      not-accessible
    STATUS          current
    DESCRIPTION
        "This table provides information about the peers and servers
            with which the local NTP has associations."
    ::= { ntpObject 11 }
        
ntpAssoEntry         OBJECT-TYPE
    SYNTAX          NtpAssoEntry
    MAX-ACCESS      not-accessible
    STATUS          current
    DESCRIPTION
        "Each association entry provides NTP information retrieved
            from a particular initiative peer or server.Each peer or
            server is identified by a unique association identifier.
            Entries are automatically created when the user configures 
            the passive peer to unicast peer list or the passive server
            to unicast server list."
    INDEX     { ntpAssoRemoteIpAddress }
    ::= { ntpAssoTable 1 }

NtpAssoEntry    ::=
    SEQUENCE {
                ntpAssoRemoteIpAddress       IpAddress,
                ntpAssoRefId                 OCTET STRING,
                ntpAssoStratum               OCTET STRING,
                ntpAssoWhen                  OCTET STRING,             
                ntpAssoPoll                  OCTET STRING,
                ntpAssoReach                 OCTET STRING,
                ntpAssoDelay                 OCTET STRING,
                ntpAssoOffset                OCTET STRING,
                ntpAssoDispersion            OCTET STRING
            }

ntpAssoRemoteIpAddress         OBJECT-TYPE
    SYNTAX          IpAddress
    MAX-ACCESS      read-only
    STATUS          current
    DESCRIPTION
        "The IP address of the initiative peer or server."
    ::= { ntpAssoEntry 1 }
        
ntpAssoRefId         OBJECT-TYPE
    SYNTAX          OCTET STRING (SIZE (0..255))
    MAX-ACCESS      read-only
    STATUS          current
    DESCRIPTION
        "The reference identifier of the peer or server."
    ::= { ntpAssoEntry 2 }        

ntpAssoStratum         OBJECT-TYPE
    SYNTAX          OCTET STRING (SIZE (0..255))
    MAX-ACCESS      read-only
    STATUS          current
    DESCRIPTION
        "This is a integer indicating the stratum level
            of the peer of server clock."
    ::= { ntpAssoEntry 3 }

ntpAssoWhen         OBJECT-TYPE
    SYNTAX          OCTET STRING (SIZE (0..255))
    MAX-ACCESS      read-only
    STATUS          current
    DESCRIPTION
        "This is a round second clock whose value change
            from 1 to 60."
    ::= { ntpAssoEntry 4 }        
                
ntpAssoPoll         OBJECT-TYPE
    SYNTAX          OCTET STRING (SIZE (0..255))
    MAX-ACCESS      read-only
    STATUS          current
    DESCRIPTION
        "The interval at which the local host polls the peer."
    ::= { ntpAssoEntry 5 }        
        
ntpAssoReach         OBJECT-TYPE
    SYNTAX          OCTET STRING (SIZE (0..255))
    MAX-ACCESS      read-only
    STATUS          current
    DESCRIPTION
        "This is a shift register of NTP which is used to
            determine the reach abilityStatus of the peer."
    ::= { ntpAssoEntry 6 }        
        
ntpAssoDelay         OBJECT-TYPE
    SYNTAX          OCTET STRING (SIZE (0..255))
    MAX-ACCESS      read-only
    STATUS          current
    DESCRIPTION
        "This is a signed fixed-point number indicating
            the total roundtrip delay to the primary reference source
            at the root of the synchronization subnet, in seconds."
    ::= { ntpAssoEntry 7 }        

ntpAssoOffset         OBJECT-TYPE
    SYNTAX          OCTET STRING (SIZE (0..255))
    MAX-ACCESS      read-only
    STATUS          current
    DESCRIPTION
        "This is a signed, fixed-point number indicating the offset
            of the peer clock or server clock relative to the local 
            clock, in seconds."
    ::= { ntpAssoEntry 8 }        

ntpAssoDispersion         OBJECT-TYPE
    SYNTAX          OCTET STRING (SIZE (0..255))
    MAX-ACCESS      read-only
    STATUS          current
    DESCRIPTION
        "This is a signed fixed-point number indicating
            the maximum error of the peer or server clock 
            relative to the primary reference source."
    ::= { ntpAssoEntry 9 }

ntpUniPeerTable         OBJECT-TYPE
    SYNTAX          SEQUENCE OF NtpUniPeerEntry
    MAX-ACCESS      not-accessible
    STATUS          current
    DESCRIPTION
        "This table provides ipaddress about the peer
            with which the local NTP has associations.This
            Table support create and destroy association
            peer entry."
    ::= { ntpObject 12 }
        
ntpUniPeerEntry         OBJECT-TYPE
    SYNTAX          NtpUniPeerEntry
    MAX-ACCESS      not-accessible
    STATUS          current
    DESCRIPTION
        "This table provides ipaddress about the peer with which the local NTP
         has associations.This table support create and destroy association peer
          entry."
    INDEX     { ntpUnicastPeerIpAddress }
    ::= { ntpUniPeerTable 1 }

NtpUniPeerEntry    ::=
    SEQUENCE{
                ntpUnicastPeerIpAddress       
                    IpAddress,
                ntpUnicastPeerKey							
                    Integer32,
                ntpUnicastPeerVersion 				
                    Integer32,
                ntpUnicastPeerPrefer					
                    INTEGER,
                ntpUnicastPeerRowStatus       
                    RowStatus 
            }

ntpUnicastPeerIpAddress         OBJECT-TYPE
    SYNTAX          IpAddress
    MAX-ACCESS      read-only
    STATUS          current
    DESCRIPTION
        "The IP address of the initiative peer."
    ::= { ntpUniPeerEntry 1 }

ntpUnicastPeerKey         OBJECT-TYPE
    SYNTAX          Integer32
    MAX-ACCESS      read-write
    STATUS          current
    DESCRIPTION
        "The peer use which authentication key pair."
    ::= { ntpUniPeerEntry 2 }    
        
ntpUnicastPeerVersion         OBJECT-TYPE
    SYNTAX          Integer32
    MAX-ACCESS      read-write
    STATUS          current
    DESCRIPTION
        "The NTP verion of the peer."
    ::= { ntpUniPeerEntry 3 }     
        
ntpUnicastPeerPrefer         OBJECT-TYPE
    SYNTAX          INTEGER
        {
            prefer(1),
            noPrefer(2)
        }
    MAX-ACCESS      read-write
    STATUS          current
    DESCRIPTION
        "This indicates the NTP peer is a preferred peer."
    ::= { ntpUniPeerEntry 4 }     
            
ntpUnicastPeerRowStatus        OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { ntpUniPeerEntry 5 }

ntpUniServerTable         OBJECT-TYPE
    SYNTAX          SEQUENCE OF NtpUniServerEntry
    MAX-ACCESS      not-accessible
    STATUS          current
    DESCRIPTION
        "This table provides ipaddress about the server with which the local NTP
         has associations.This table support create and destroy association
         server entry."
    ::= { ntpObject 13 }
        
ntpUniServerEntry         OBJECT-TYPE
    SYNTAX          NtpUniServerEntry
    MAX-ACCESS      not-accessible
    STATUS          current
    DESCRIPTION
        "This table provides ipaddress about the server with which the local NTP
         has associations.This table support create and destroy association
         server entry."
    INDEX     { ntpUnicastServerIpAddress }
    ::= { ntpUniServerTable 1 }

NtpUniServerEntry    ::=
    SEQUENCE{
                ntpUnicastServerIpAddress       IpAddress,
                ntpUnicastServerKey							Integer32,
                ntpUnicastServerVersion 				Integer32,
                ntpUnicastServerPrefer					INTEGER,
                ntpUnicastServerRowStatus       RowStatus 
            }

ntpUnicastServerIpAddress         OBJECT-TYPE
    SYNTAX          IpAddress
    MAX-ACCESS      read-only
    STATUS          current
    DESCRIPTION
        "The IP address of the initiative server."
    ::= { ntpUniServerEntry 1 }

ntpUnicastServerKey         OBJECT-TYPE
    SYNTAX          Integer32
    MAX-ACCESS      read-write
    STATUS          current
    DESCRIPTION
        "The server use which authentication key pair."
    ::= { ntpUniServerEntry 2 }    
        
ntpUnicastServerVersion         OBJECT-TYPE
    SYNTAX          Integer32
    MAX-ACCESS      read-write
    STATUS          current
    DESCRIPTION
        "The NTP verion of the server."
    ::= { ntpUniServerEntry 3 }     
        
ntpUnicastServerPrefer         OBJECT-TYPE
    SYNTAX          INTEGER
        {
            prefer(1),
            noPrefer(2)
        }
    MAX-ACCESS      read-write
    STATUS          current
    DESCRIPTION
        "This indicates the NTP server is a preferred server."
    ::= { ntpUniServerEntry 4 }    
        
ntpUnicastServerRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { ntpUniServerEntry 5 }

ntpLocalRefClockStratum         OBJECT-TYPE
    SYNTAX          Integer32 (1..16)
    MAX-ACCESS      read-write
    STATUS          current
    DESCRIPTION
        "The stratum of local reference clock.If the value is 16, disable local reference clock."
    ::= { ntpObject 14 }

ntpSysAuthenticate         OBJECT-TYPE
    SYNTAX          INTEGER      
        {
                noAuthenticate(0),
                authenticate(1)
            }
    MAX-ACCESS      read-write
    STATUS          current
    DESCRIPTION
        "This is a integer indicating that system support authentication."
    ::= { ntpObject 15 }    
        
ntpBroadcastDelay         OBJECT-TYPE
    SYNTAX          Integer32 (1..10000)
    MAX-ACCESS      read-write
    STATUS          current
    DESCRIPTION
        "The broadcast delay of ntp broadcast mode."
    ::= { ntpObject 16 }           


--
-- NTP key
--         
ntpKeyTable         OBJECT-TYPE
    SYNTAX          SEQUENCE OF NtpKeyEntry
    MAX-ACCESS      not-accessible
    STATUS          current
    DESCRIPTION        "The table containing information of authentication key pair."
    ::= { ntpObject 17 }
                           
ntpKeyEntry         OBJECT-TYPE
    SYNTAX          NtpKeyEntry
    MAX-ACCESS      not-accessible
    STATUS          current
    DESCRIPTION        "An entry containing information of authentication key pair."
    INDEX     { ntpKeyID }
    ::= { ntpKeyTable 1 }

NtpKeyEntry    ::=
    SEQUENCE {
        ntpKeyID Integer32,
        ntpKeyPair    OCTET STRING,
        ntpKeyRowStatus  RowStatus 
        }

ntpKeyID         OBJECT-TYPE
    SYNTAX          Integer32 (1..64000)
    MAX-ACCESS      not-accessible
    STATUS          current
    DESCRIPTION        "NTP authentication key ID        "
    ::= { ntpKeyEntry 1 }

ntpKeyPair         OBJECT-TYPE
    SYNTAX          OCTET STRING (SIZE (0..256))
    MAX-ACCESS      read-write
    STATUS          current
    DESCRIPTION        "NTP authentication key pair."
    ::= { ntpKeyEntry 2 }

ntpKeyRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { ntpKeyEntry 3 }        
        

--
-- NTP trust key
--         
ntpTrustKeyTable       OBJECT-TYPE
    SYNTAX          SEQUENCE OF NtpTrustKeyEntry
    MAX-ACCESS      not-accessible
    STATUS          current
    DESCRIPTION        "The table containing information of authentication key pair that trusted."
    ::= { ntpObject 18 }
                           
ntpTrustKeyEntry         OBJECT-TYPE
    SYNTAX          NtpTrustKeyEntry
    MAX-ACCESS      not-accessible
    STATUS          current
    DESCRIPTION        "An entry containing information of authentication key pair that trusted."
    INDEX     { ntpKeyID }
    ::= { ntpTrustKeyTable 1 }

NtpTrustKeyEntry    ::=
    SEQUENCE {
        ntpTrustKeyID       Integer32,
        ntpTrustKeyTrust    Integer32
        }

ntpTrustKeyID          OBJECT-TYPE
    SYNTAX          Integer32(1..64000)
    MAX-ACCESS      not-accessible
    STATUS          current
    DESCRIPTION        "NTP authentication key ID        "
    ::= { ntpTrustKeyEntry 1 }

ntpTrustKeyTrust       OBJECT-TYPE
    SYNTAX          Integer32
    MAX-ACCESS      read-write
    STATUS          current
    DESCRIPTION        "NTP authentication key pair trust."
    ::= { ntpTrustKeyEntry 2 }
        
ntpInterfaceReload         OBJECT-TYPE
    SYNTAX          INTEGER      
        {
          reloadInterface(1)
        }
    MAX-ACCESS      read-write
    STATUS          current
    DESCRIPTION
        "Reload interfaces."
    ::= { ntpObject 19 }         

ntpTimeResetStatistic       OBJECT-TYPE
    SYNTAX          Integer32
    MAX-ACCESS      read-only
    STATUS          current
    DESCRIPTION        "NTP I/O statistics of time since reset."
    ::= { ntpObject 20 }

ntpRcvBufferStatistic       OBJECT-TYPE
    SYNTAX          Integer32
    MAX-ACCESS      read-only
    STATUS          current
    DESCRIPTION        "NTP I/O statistics of receive buffers."
    ::= { ntpObject 21 }

ntpFreeRcvBufferStatistic       OBJECT-TYPE
    SYNTAX          Integer32
    MAX-ACCESS      read-only
    STATUS          current
    DESCRIPTION        "NTP I/O statistics of free receive buffers."
    ::= { ntpObject 22 }

ntpUsedRcvBufferStatistic       OBJECT-TYPE
    SYNTAX          Integer32
    MAX-ACCESS      read-only
    STATUS          current
    DESCRIPTION        "NTP I/O statistics of used receive buffers."
    ::= { ntpObject 23 }

ntpLowWaterRefillStatistic       OBJECT-TYPE
    SYNTAX          Integer32
    MAX-ACCESS      read-only
    STATUS          current
    DESCRIPTION        "NTP I/O statistics of low water refills."
    ::= { ntpObject 24 }

ntpDroppedPktStatistic       OBJECT-TYPE
    SYNTAX          Integer32
    MAX-ACCESS      read-only
    STATUS          current
    DESCRIPTION        "NTP I/O statistics of dropped packets."
    ::= { ntpObject 25 }

ntpIgnoredPktStatistic       OBJECT-TYPE
    SYNTAX          Integer32
    MAX-ACCESS      read-only
    STATUS          current
    DESCRIPTION        "NTP I/O statistics of ignored packets."
    ::= { ntpObject 26 }

ntpReceivedPktStatistic       OBJECT-TYPE
    SYNTAX          Integer32
    MAX-ACCESS      read-only
    STATUS          current
    DESCRIPTION        "NTP I/O statistics of received packets."
    ::= { ntpObject 27 }

ntpPktSentStatistic       OBJECT-TYPE
    SYNTAX          Integer32
    MAX-ACCESS      read-only
    STATUS          current
    DESCRIPTION        "NTP I/O statistics of packets sent."
    ::= { ntpObject 28 }

ntpPktNotSentStatistic       OBJECT-TYPE
    SYNTAX          Integer32
    MAX-ACCESS      read-only
    STATUS          current
    DESCRIPTION        "NTP I/O statistics of packets not sent."
    ::= { ntpObject 29 }

ntpInterruptsHandledStatistic       OBJECT-TYPE
    SYNTAX          Integer32
    MAX-ACCESS      read-only
    STATUS          current
    DESCRIPTION        "NTP I/O statistics of interrupts handled."
    ::= { ntpObject 30 }

ntpReceivedByIntStatistic       OBJECT-TYPE
    SYNTAX          Integer32
    MAX-ACCESS      read-only
    STATUS          current
    DESCRIPTION        "NTP I/O statistics of received by int."
    ::= { ntpObject 31 }


--
-- NTP Access Control Entries(ACE) Table
--         
ntpAceTable       OBJECT-TYPE
    SYNTAX          SEQUENCE OF NtpAceEntry
    MAX-ACCESS      not-accessible
    STATUS          current
    DESCRIPTION        "The table create the Access Control Entries (ACE) of a NTP server/peer."
    ::= { ntpObject 32 }
                           
ntpAceEntry         OBJECT-TYPE
    SYNTAX          NtpAceEntry
    MAX-ACCESS      not-accessible
    STATUS          current
    DESCRIPTION        "An entry containing information of NTP ACE."
    INDEX     { ntpAceIndex }
    ::= { ntpAceTable 1 }

NtpAceEntry    ::=
    SEQUENCE {
        ntpAceIndex       Integer32,
        ntpAceAddress     OCTET STRING,
        ntpAceMask        OCTET STRING,
        ntpAceVersion       INTEGER,
        ntpAceKod           INTEGER,
        ntpAceIgnore        INTEGER,
        ntpAceNoquery       INTEGER,
        ntpAceNomodify      INTEGER,
        ntpAceNotrap        INTEGER,
        ntpAceNoserver      INTEGER,
        ntpAceNopeer        INTEGER,
        ntpAceNotrust       INTEGER,
        ntpAceLimited       INTEGER,
        ntpAceRowStatus     RowStatus
        }

ntpAceIndex          OBJECT-TYPE
    SYNTAX          Integer32
    MAX-ACCESS      not-accessible
    STATUS          current
    DESCRIPTION        "NTP ace list index."
    ::= { ntpAceEntry 1 }   

ntpAceAddress       OBJECT-TYPE
    SYNTAX          OCTET STRING (SIZE (1..63))
    MAX-ACCESS      read-create
    STATUS          current
    DESCRIPTION        "Ip address or hostname of NTP restrict peer."
    ::= { ntpAceEntry 2 }
      
ntpAceMask       OBJECT-TYPE
    SYNTAX          OCTET STRING (SIZE (7..15))
    MAX-ACCESS      read-create
    STATUS          current
    DESCRIPTION        "Mask of NTP restrict peer.
    Default value is 255.255.255.255"
    ::= { ntpAceEntry 3 }
         
ntpAceVersion         OBJECT-TYPE
    SYNTAX          INTEGER
        {
           enable(1),
           disable(2)
        }
    MAX-ACCESS      read-create
    STATUS          current
    DESCRIPTION
        "Ignore these hosts if not the current NTP version.enable(1),disable(2)."
    DEFVAL{ 2 }
    ::= { ntpAceEntry 4 }  
    
ntpAceKod         OBJECT-TYPE
    SYNTAX          INTEGER
        {
           enable(1),
           disable(2)
        }
    MAX-ACCESS      read-create
    STATUS          current
    DESCRIPTION
        "If access is denied, send a kiss-of-death packet."
    DEFVAL{ 2 }
    ::= { ntpAceEntry 5 }
          
ntpAceIgnore         OBJECT-TYPE
    SYNTAX          INTEGER
        {
           enable(1),
           disable(2)
        }
    MAX-ACCESS      read-create
    STATUS          current
    DESCRIPTION
        "Ignore all packets from host that match this entry."
    DEFVAL{ 2 }
    ::= { ntpAceEntry 6 }
      
ntpAceNoquery         OBJECT-TYPE
    SYNTAX          INTEGER
        {
           enable(1),
           disable(2)
        }
    MAX-ACCESS      read-create
    STATUS          current
    DESCRIPTION
        "Ignore all NTP mode 6 and 7 packets from the source.
         Time service is not affected."
    DEFVAL{ 2 }
    ::= { ntpAceEntry 7 } 
     
ntpAceNomodify         OBJECT-TYPE
    SYNTAX          INTEGER
        {
           enable(1),
           disable(2)
        }
    MAX-ACCESS      read-create
    STATUS          current
    DESCRIPTION
        "Ignore all NTP mode 6 and 7 packets
         which attempt to modify the stateof the server."
    DEFVAL{ 2 }
    ::= { ntpAceEntry 8 } 
    
ntpAceNotrap         OBJECT-TYPE
    SYNTAX          INTEGER
        {
           enable(1),
           disable(2)
        }
    MAX-ACCESS      read-create
    STATUS          current
    DESCRIPTION
        "Decline to provide mode 6 control message
         trap service to matching hosts."
    DEFVAL{ 2 }
    ::= { ntpAceEntry 9 }
       
ntpAceNoserver         OBJECT-TYPE
    SYNTAX          INTEGER
        {
           enable(1),
           disable(2)
        }
    MAX-ACCESS      read-create
    STATUS          current
    DESCRIPTION
        "Ignore NTP packets whose mode is other than 6 or 7."
    DEFVAL{ 2 }    
    ::= { ntpAceEntry 10 }
     
ntpAceNopeer          OBJECT-TYPE
    SYNTAX          INTEGER
        {
           enable(1),
           disable(2)
        }
    MAX-ACCESS      read-create
    STATUS          current
    DESCRIPTION
        "Provide stateless time service to polling hosts,
         but do not allocate peer memory resources."
    DEFVAL{ 2 }
    ::= { ntpAceEntry 11 }
      
ntpAceNotrust         OBJECT-TYPE
    SYNTAX          INTEGER
        {
           enable(1),
           disable(2)
        }
    MAX-ACCESS      read-create
    STATUS          current
    DESCRIPTION
        "Treat these hosts normally in other respects,
         but never use them as synchronization sources."
    DEFVAL{ 2 }
    ::= { ntpAceEntry 12 }
    
ntpAceLimited         OBJECT-TYPE
    SYNTAX          INTEGER
        {
           enable(1),
           disable(2)
        }
    MAX-ACCESS      read-create
    STATUS          current
    DESCRIPTION
        "These hosts are subject to limitation of
         number of clients from the same net."
    DEFVAL{ 2 }
    ::= { ntpAceEntry 13 }
         
ntpAceRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { ntpAceEntry 20 } 

--
-- NTP current restrict list
--         
ntpRestrictTable       OBJECT-TYPE
    SYNTAX          SEQUENCE OF NtpRestrictEntry
    MAX-ACCESS      not-accessible
    STATUS          current
    DESCRIPTION        "The table containing information of NTP current restrict list."
    ::= { ntpObject 33 }
                           
ntpRestrictEntry         OBJECT-TYPE
    SYNTAX          NtpRestrictEntry
    MAX-ACCESS      not-accessible
    STATUS          current
    DESCRIPTION        "An entry containing information of NTP restrict."
    INDEX     { ntpRestrictIndex }
    ::= { ntpRestrictTable 1 }

NtpRestrictEntry    ::=
    SEQUENCE {
        ntpRestrictIndex       Integer32,
        ntpRestrictAddress     OCTET STRING,
        ntpRestrictMask        OCTET STRING,
        ntpRestrictCount       Integer32,
        ntpRestrictFlag        OCTET STRING
        }

ntpRestrictIndex          OBJECT-TYPE
    SYNTAX          Integer32
    MAX-ACCESS      not-accessible
    STATUS          current
    DESCRIPTION        "NTP current restrict list index."
    ::= { ntpRestrictEntry 1 }

ntpRestrictAddress       OBJECT-TYPE
    SYNTAX          OCTET STRING (SIZE (0..16))
    MAX-ACCESS      read-only
    STATUS          current
    DESCRIPTION        "NTP current restrict address."
    ::= { ntpRestrictEntry 2 }

ntpRestrictMask       OBJECT-TYPE
    SYNTAX          OCTET STRING (SIZE (0..16))
    MAX-ACCESS      read-only
    STATUS          current
    DESCRIPTION        "NTP current restrict mask."
    ::= { ntpRestrictEntry 3 }

ntpRestrictCount       OBJECT-TYPE
    SYNTAX          Integer32
    MAX-ACCESS      read-only
    STATUS          current
    DESCRIPTION        "NTP current restrict count value."
    ::= { ntpRestrictEntry 4 }
        
ntpRestrictFlag       OBJECT-TYPE
    SYNTAX          OCTET STRING (SIZE (0..80))
    MAX-ACCESS      read-only
    STATUS          current
    DESCRIPTION        "NTP current restrict flags."
    ::= { ntpRestrictEntry 5 }
                
-- Sub Module: ACL


-- Rule action value
RuleAction    ::= TEXTUAL-CONVENTION
    STATUS          current
    DESCRIPTION
        "The value of rule's action.
             permit: The packet matching the rule will be permitted to forward.
             deny: The packet matching the rule will be denied.
        "
    SYNTAX          INTEGER
        {
            permit(1),
            deny(2)
        }

-- CounterClear value
    CounterClear    ::= TEXTUAL-CONVENTION
    STATUS          current
    DESCRIPTION
        "cleared: Reset the value of the rule's counter.
             nouse: 'nouse' will be returned when getting.
        "
    SYNTAX          INTEGER
        {
            cleared(1),
            nouse(2)
        }

-- PortOp value
    PortOp    ::= TEXTUAL-CONVENTION
    STATUS          current
    DESCRIPTION
        "The operation type of TCP and UDP.
             lt : Less than given port number.
             eq : Equal to given port number.
             gt : Greater than given port number.
--           neq : Not equal to given port number.
             range : Between two port numbers.
        "
    SYNTAX          INTEGER
        {
            eq(0),
--          neq(1),
            gt(2),
            lt(3),
            range(4),
            invalid(5)
        }

-- Precedence value
    PrecedenceValue    ::= TEXTUAL-CONVENTION
    STATUS          current
    DESCRIPTION
        "The value of IP-packet's precedence.
            <0-7>           Value of precedence
            routine         Specify routine precedence(0)
            priority        Specify priority precedence(1)
            immediate       Specify immediate precedence(2)
            flash           Specify flash precedence(3)
            flash-override  Specify flash-override precedence(4)
            critical        Specify critical precedence(5)
            internet        Specify internetwork control precedence(6)
            network         Specify network control precedence(7)        "
    SYNTAX          Integer32 (0..7|255)

-- DSCP value
    DSCPValue    ::= TEXTUAL-CONVENTION
    STATUS          current
    DESCRIPTION
        "The value of DSCP.
             <0-64>  Value of DSCP
             af11    Specify Assured Forwarding 11 service(10)
             af12    Specify Assured Forwarding 12 service(12)
             af13    Specify Assured Forwarding 13 service(14)
             af21    Specify Assured Forwarding 21 service(18)
             af22    Specify Assured Forwarding 22 service(20)
             af23    Specify Assured Forwarding 23 service(22)
             af31    Specify Assured Forwarding 31 service(26)
             af32    Specify Assured Forwarding 32 service(28)
             af33    Specify Assured Forwarding 33 service(30)
             af41    Specify Assured Forwarding 41 service(34)
             af42    Specify Assured Forwarding 42 service(36)
             af43    Specify Assured Forwarding 43 service(38)
             be      Specify Best Effort service(0)
             cs1     Specify Class Selector 1 service(8)
             cs2     Specify Class Selector 2 service(16)
             cs3     Specify Class Selector 3 service(24)
             cs4     Specify Class Selector 4 service(32)
             cs5     Specify Class Selector 5 service(40)
             cs6     Specify Class Selector 6 service(48)
             cs7     Specify Class Selector 7 service(56)
             ef      Specify Expedited Forwarding service(46)
             nouse   Do not use this filter(64)
        "
    SYNTAX          Integer32 (0..64)

--
-- nodes defined
--
        aclData OBJECT IDENTIFIER    ::= { acl 1 }

--
-- Node of aclGroupTable
--
aclGroupTable         OBJECT-TYPE
    SYNTAX          SEQUENCE OF AclGroupEntry
    MAX-ACCESS      not-accessible
    STATUS          current
    DESCRIPTION
        "Configure the match-order of number-acl group."
    ::= { aclData 1 }

aclGroupEntry         OBJECT-TYPE
    SYNTAX          AclGroupEntry
    MAX-ACCESS      not-accessible
    STATUS          current
    DESCRIPTION
        "Define the index of aclGroupTable."
    INDEX     { aclGroupIndex }
    ::= { aclGroupTable 1 }

AclGroupEntry    ::=
    SEQUENCE
        {
            aclGroupIndex
                Integer32,
            aclGroupName
                OCTET STRING,
            aclGroupRuleNum
                Unsigned32,
            aclGroupRowStatus 
                RowStatus,
            aclGroupDescription
                OCTET STRING
         }

aclGroupIndex         OBJECT-TYPE
    SYNTAX          Integer32 (10001..80000)
    MAX-ACCESS      not-accessible
    STATUS          current
    DESCRIPTION
        "The index of acl group.
            MAC type         :10001..20000
            IP Extend type   :20001..30000
            IP type          :30001..40000
            IPv6 type        :40001..50000
            IPv6 Extend type :50001..60000
            MLPS type        :60001..70000
            MPLS Extend type :70001..80000."
    ::= { aclGroupEntry 1 }

aclGroupName         OBJECT-TYPE
    SYNTAX          OCTET STRING (SIZE (0..20))
    MAX-ACCESS      read-create
    STATUS          current
    DESCRIPTION
        "The name of acl group. Range 0~20."
    ::= { aclGroupEntry 2 }

aclGroupRuleNum       OBJECT-TYPE
    SYNTAX          Unsigned32
    MAX-ACCESS      read-only
    STATUS          current
    DESCRIPTION
        "The count of rules in this acl group."
    ::= { aclGroupEntry 3 }

aclGroupRowStatus     OBJECT-TYPE
    SYNTAX          RowStatus
    MAX-ACCESS      read-create
    STATUS          current
    DESCRIPTION
        "The status of this row.Now only realize CreateAndGo and Destroy and Active.
        1 means Active
        4 means CreateAndGo
        6 means Destroy"
    ::= { aclGroupEntry 4 }
    
aclGroupDescription OBJECT-TYPE
    SYNTAX          OCTET STRING (SIZE(0..100))
    MAX-ACCESS      read-write
    STATUS          current
    DESCRIPTION
            "The description of this acl group.Up to 100 characters.Range 0~100."
    ::= { aclGroupEntry 5 }

--
-- Nodes of aclMacRuleTable
--
aclMacRuleTable       OBJECT-TYPE
    SYNTAX          SEQUENCE OF AclMacRuleEntry
    MAX-ACCESS      not-accessible
    STATUS          current
    DESCRIPTION
        "A table of MAC acl group.
             If some objects of this table are not supported by some products,
             these objects can't be created, changed and applied.
             Default value of these objects will be returned when they are read.
        "
    ::= { aclData 2 }

aclMacRuleEntry       OBJECT-TYPE
    SYNTAX          AclMacRuleEntry
    MAX-ACCESS      not-accessible
    STATUS          current
    DESCRIPTION
        "MAC acl group information."
    INDEX         { aclMacGroupIndex, aclMacRuleIndex }
    ::= { aclMacRuleTable 1 }

    AclMacRuleEntry    ::=
    SEQUENCE
        {
            aclMacGroupIndex
                Integer32,
            aclMacRuleIndex
                Integer32,
            aclMacAct
                RuleAction,
            aclMacSrcMac
                MacAddress ,
            aclMacSrcMacWild
                MacAddress ,
            aclMacDestMac
                MacAddress ,
            aclMacDestMacWild
                MacAddress ,
            aclMacProtocol
                OCTET STRING,
            aclMacProtocolWild
                OCTET STRING,
            aclMacType
                Integer32,
            aclMacVlanId
                Integer32,
            aclMacInnerVlanId
                Integer32,
            aclMacCos
                Integer32,
            aclMacInnerCos
                Integer32,
            aclMacTimeRangeName
                OCTET STRING,
            aclMacRowStatus
                RowStatus
         }

aclMacGroupIndex      OBJECT-TYPE
    SYNTAX          Integer32 (10001..30000|50001..60000)
    MAX-ACCESS      not-accessible
    STATUS          current
    DESCRIPTION
        "The index of MAC-based acl group.Range is 10001~30000 and 50001~60000."
    ::= { aclMacRuleEntry 1 }

aclMacRuleIndex       OBJECT-TYPE
    SYNTAX          Integer32 (1..131071)
    MAX-ACCESS      not-accessible
    STATUS          current
    DESCRIPTION
        "The rule index of MAC-based acl group. Range 1~131071."
    ::= { aclMacRuleEntry 2 }

aclMacAct             OBJECT-TYPE
    SYNTAX          RuleAction
    MAX-ACCESS      read-create
    STATUS          current
    DESCRIPTION
        "The action of MAC acl rule.
         (1) permit.
         (2) deny."
    ::= { aclMacRuleEntry 3 }

aclMacSrcMac          OBJECT-TYPE
    SYNTAX          MacAddress 
    MAX-ACCESS      read-create
    STATUS          current
    DESCRIPTION
        "Source MAC of MAC acl rule.
             If you do not want to use this filter,
             set this item with any valid value 
             and set aclMacSrcMacWild 'FFFF.FFFF.FFFF'."
    ::= { aclMacRuleEntry 4 }

aclMacSrcMacWild      OBJECT-TYPE
    SYNTAX          MacAddress 
    MAX-ACCESS      read-create
    STATUS          current
    DESCRIPTION
        "Source MAC wildcard of MAC acl rule.
        	   If you do not want to use this filter, 
        	   set aclMacSrcMac with any valid value 
        	   and set this item 'FFFF.FFFF.FFFF'."
    ::= { aclMacRuleEntry 5 }

aclMacDestMac         OBJECT-TYPE
    SYNTAX          MacAddress 
    MAX-ACCESS      read-create
    STATUS          current
    DESCRIPTION
        "Destination MAC of MAC acl rule.
             If you do not want to use this filter,
             set this item with any valid value 
             and set aclMacDestMacWild 'FFFF.FFFF.FFFF'."
    ::= { aclMacRuleEntry 6 }

aclMacDestMacWild     OBJECT-TYPE
    SYNTAX          MacAddress 
    MAX-ACCESS      read-create
    STATUS          current
    DESCRIPTION
        "Destination MAC wildcard of MAC acl rule. 
        	   If you do not want to use this filter, 
        	   set aclMacDestMac with any valid value 
        	   and set this item 'FFFF.FFFF.FFFF'."
    ::= { aclMacRuleEntry 7 }

aclMacProtocol         OBJECT-TYPE
    SYNTAX          OCTET STRING (SIZE(0..6))
    MAX-ACCESS      read-create
    STATUS          current
    DESCRIPTION
        "Ether type in decimal/hexadecimal, ranging in <0x0-0xffff>.
         (aclMacProtocol = 0, aclMacProtocolWild = 0xffff) means any protocols.
         "
    ::= { aclMacRuleEntry 8 }

aclMacProtocolWild         OBJECT-TYPE
    SYNTAX          OCTET STRING (SIZE(0..6))
    MAX-ACCESS      read-create
    STATUS          current
    DESCRIPTION
        "Ether type wildcard in decimal/hexadecimal, ranging in <0x0-0xffff>,
         reversely encoded.
         (aclMacProtocol = 0, aclMacProtocolWild = 0xffff) means any protocols.
         "
         ::= { aclMacRuleEntry 9 }

aclMacType         OBJECT-TYPE
    SYNTAX          Integer32 (0..3)
    MAX-ACCESS      read-create
    STATUS          obsolete
    DESCRIPTION
        "The type of protocol
              nouse(0)
              eth2(1)
              sap(2)
              snap(3)        "
    ::= { aclMacRuleEntry 10 }

aclMacVlanId         OBJECT-TYPE
    SYNTAX          Integer32 (0..4094)
    MAX-ACCESS      read-create
    STATUS          current
    DESCRIPTION
        "The vlan id of MAC acl rule.Range 0~4094.
             nouse(0)        "
    ::= { aclMacRuleEntry 11 }

aclMacInnerVlanId         OBJECT-TYPE
    SYNTAX          Integer32 (0..4094)
    MAX-ACCESS      read-create
    STATUS          current
    DESCRIPTION
        "The inner vlan id of MAC acl rule. Range 0~4094
             nouse(0)        "
    ::= { aclMacRuleEntry 12 }

aclMacCos         OBJECT-TYPE
    SYNTAX          Integer32 (0..8)
    MAX-ACCESS      read-create
    STATUS          current
    DESCRIPTION
        "Vlan priority of MAC acl rule.Range 0~8
         nouse(8)."
    ::= { aclMacRuleEntry 13 }

aclMacInnerCos         OBJECT-TYPE
    SYNTAX          Integer32 (0..8)
    MAX-ACCESS      read-create
    STATUS          current
    DESCRIPTION
        "Inner vlan priority of MAC acl rule.Range 0~8.
         nouse(8)."
    ::= { aclMacRuleEntry 14 }

aclMacTimeRangeName         OBJECT-TYPE
    SYNTAX          OCTET STRING (SIZE(0..20))
    MAX-ACCESS      read-create
    STATUS          current
    DESCRIPTION
        "The Time-range of MAC acl rule.Range 0~20."
    ::= { aclMacRuleEntry 15 }

aclMacRowStatus         OBJECT-TYPE
    SYNTAX          RowStatus
    MAX-ACCESS      read-create
    STATUS          current
    DESCRIPTION
        "The status of this row.Now only realize CreateAndGo and Destroy and Active.
        1 means Active
        4 means CreateAndGo
        6 means Destroy"
    ::= { aclMacRuleEntry 30 }

--
-- aclIpRuleTable
--
aclIpRuleTable         OBJECT-TYPE
    SYNTAX          SEQUENCE OF AclIpRuleEntry
    MAX-ACCESS      not-accessible
    STATUS          current
    DESCRIPTION
        "Configure the rule for ip acl group."
    ::= { aclData 3 }

aclIpRuleEntry         OBJECT-TYPE
    SYNTAX          AclIpRuleEntry
    MAX-ACCESS      not-accessible
    STATUS          current
    DESCRIPTION
        "Define the index of aclIpRuleTable."
    INDEX          { aclIpGroupIndex, aclIpRuleIndex }
    ::= { aclIpRuleTable 1 }

    AclIpRuleEntry    ::=
    SEQUENCE {
            aclIpGroupIndex
                Integer32,
            aclIpRuleIndex
                Integer32,
            aclIpAct
                RuleAction,
            aclIpProtocol
                Integer32,
            aclIpSrcIp
                IpAddress,
            aclIpSrcWild
                IpAddress,
            aclIpDestIp
                IpAddress,
            aclIpDestWild
                IpAddress,
            aclIpPrecedence
                Integer32,
            aclIpDscp
                DSCPValue,
            aclIpFragments
                TruthValue,
            aclIpRouted
                TruthValue,
            aclIpOptions
                TruthValue,
            aclIpTimeRangeName
                OCTET STRING,
            aclIpRowStatus 
                RowStatus 
         }

aclIpGroupIndex         OBJECT-TYPE
    SYNTAX          Integer32 (20001..40000)
    MAX-ACCESS      not-accessible
    STATUS          current
    DESCRIPTION
        "The index of ip acl group. Range 20001~40000."
    ::= { aclIpRuleEntry 1 }

aclIpRuleIndex         OBJECT-TYPE
    SYNTAX          Integer32 (1..131071)
    MAX-ACCESS      not-accessible
    STATUS          current
    DESCRIPTION
        "The rule index of ip acl rule.Range 1~131071."
    ::= { aclIpRuleEntry 2 }

aclIpAct         OBJECT-TYPE
    SYNTAX          RuleAction
    MAX-ACCESS      read-create
    STATUS          current
    DESCRIPTION
        "The action of ip acl rule.
         (1) permit.
         (2) deny."
    ::= { aclIpRuleEntry 3 }

aclIpProtocol         OBJECT-TYPE
    SYNTAX          Integer32 (0..256)
    MAX-ACCESS      read-create
    STATUS          current
    DESCRIPTION
        "The protocol-type of Ip acl group.
             <0-255>  Protocol number
              Icmp     Internet Control Message Protocol(1)
              igmp     Internet Group Management Protocol(2)
              ospf     OSPF routing protocol(89)
              tcp      Transmission Control Protocol (6)
              udp      User Datagram Protocol (17)
              nouse    Do not use this filter(256)        "
    ::= { aclIpRuleEntry 4 }

aclIpSrcIp         OBJECT-TYPE
    SYNTAX          IpAddress
    MAX-ACCESS      read-create
    STATUS          current
    DESCRIPTION
        "Source IP-address of ip acl group."
    ::= { aclIpRuleEntry 5 }

aclIpSrcWild         OBJECT-TYPE
    SYNTAX          IpAddress
    MAX-ACCESS      read-create
    STATUS          current
    DESCRIPTION
        "Source IP-address wild of ip acl group."
    ::= { aclIpRuleEntry 6 }

aclIpDestIp         OBJECT-TYPE
    SYNTAX          IpAddress
    MAX-ACCESS      read-create
    STATUS          current
    DESCRIPTION
        "Destination IP-address of ip acl group."
    ::= { aclIpRuleEntry 7 }

aclIpDestWild         OBJECT-TYPE
    SYNTAX          IpAddress
    MAX-ACCESS      read-create
    STATUS          current
    DESCRIPTION
        "Destination IP-address wild of ip acl group."
    ::= { aclIpRuleEntry 8 }

aclIpPrecedence         OBJECT-TYPE
    SYNTAX          Integer32 (0..8)
    MAX-ACCESS      read-create
    STATUS          current
    DESCRIPTION
        "The value of Precedence.8 means do not use this filter.Range 0~8.
         DSCP and Precedence both use IP TOS segment.This node can not be setted for aclIpDscp is setted."
    ::= { aclIpRuleEntry 9 }

aclIpDscp         OBJECT-TYPE
    SYNTAX          DSCPValue
    MAX-ACCESS      read-create
    STATUS          current
    DESCRIPTION
        "The value of DSCP.64 means do not use this filter.
         DSCP and Precedence both use IP TOS segment.This node can not be setted for aclIpPrecedence is setted."
    ::= { aclIpRuleEntry 10 }

aclIpFragments         OBJECT-TYPE
    SYNTAX          TruthValue
    MAX-ACCESS      read-create
    STATUS          current
    DESCRIPTION
        "The flag of matching fragmented packet. True(1),False(2)."
    ::= { aclIpRuleEntry 11 }

aclIpRouted         OBJECT-TYPE
    SYNTAX          TruthValue
    MAX-ACCESS      read-create
    STATUS          current
    DESCRIPTION
        "The flag of matching routed packet. True(1),False(2)."
    ::= { aclIpRuleEntry 12 }

aclIpOptions         OBJECT-TYPE
    SYNTAX          TruthValue
    MAX-ACCESS      read-create
    STATUS          current
    DESCRIPTION
        "The flag of matching packet with ip option. True(1),False(2)."
    ::= { aclIpRuleEntry 13 }

aclIpTimeRangeName         OBJECT-TYPE
    SYNTAX          OCTET STRING (SIZE (0..20))
    MAX-ACCESS      read-create
    STATUS          current
    DESCRIPTION
        "The Time-range of Ip acl rule.String length range 0~20."
    ::= { aclIpRuleEntry 14 }

aclIpRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { aclIpRuleEntry 16 }

--
-- aclTcpRuleTable
--
aclTcpRuleTable         OBJECT-TYPE
    SYNTAX          SEQUENCE OF AclTcpRuleEntry
    MAX-ACCESS      not-accessible
    STATUS          current
    DESCRIPTION
        "Configure the rule for tcp acl group."
    ::= { aclData 4 }

aclTcpRuleEntry         OBJECT-TYPE
    SYNTAX          AclTcpRuleEntry
    MAX-ACCESS      not-accessible
    STATUS          current
    DESCRIPTION
        "Define the index of hh3cAclTcpRuleTable."
    INDEX         { aclTcpGroupIndex, aclTcpRuleIndex }
    ::= { aclTcpRuleTable 1 }

    AclTcpRuleEntry    ::=
    SEQUENCE {
            aclTcpGroupIndex
                Integer32,
            aclTcpRuleIndex
                Integer32,
            aclTcpAct
                RuleAction,
            aclTcpSrcIp
                IpAddress,
            aclTcpSrcWild
                IpAddress,
            aclTcpDestIp
                IpAddress,
            aclTcpDestWild
                IpAddress,
            aclTcpPrecedence
                Integer32,
            aclTcpDscp
                DSCPValue,
            aclTcpFragments
                TruthValue,
            aclTcpRouted
                TruthValue,
            aclTcpOptions
                TruthValue,
            aclTcpSrcOp
                PortOp,
            aclTcpSrcPort1
                Integer32,
            aclTcpSrcPort2
                Integer32,
            aclTcpDestOp
                PortOp,
            aclTcpDestPort1
                Integer32,
            aclTcpDestPort2
                Integer32,
            aclTcpFlagOp
                INTEGER,
            aclTcpFlagUrg
                TruthValue,
            aclTcpFlagAck
                TruthValue,
            aclTcpFlagPsh
                TruthValue,
            aclTcpFlagRst
                TruthValue,
            aclTcpFlagSyn
                TruthValue,
            aclTcpFlagFin
                TruthValue,
            aclTcpTimeRangeName
                OCTET STRING,
            aclTcpRowStatus 
                RowStatus 
         }

aclTcpGroupIndex         OBJECT-TYPE
    SYNTAX          Integer32 (20001..40000)
    MAX-ACCESS      not-accessible
    STATUS          current
    DESCRIPTION
        "The index of tcp acl group. Range 20001~40000."
    ::= { aclTcpRuleEntry 1 }

aclTcpRuleIndex         OBJECT-TYPE
    SYNTAX          Integer32 (1..131071)
    MAX-ACCESS      not-accessible
    STATUS          current
    DESCRIPTION
        "The rule index of tcp acl group. Range 1~131071."
    ::= { aclTcpRuleEntry 2 }

aclTcpAct         OBJECT-TYPE
    SYNTAX          RuleAction
    MAX-ACCESS      read-create
    STATUS          current
    DESCRIPTION
        "The action of tcp acl rule.
         (1) permit.
         (2) deny."
    ::= { aclTcpRuleEntry 3 }

aclTcpSrcIp         OBJECT-TYPE
    SYNTAX          IpAddress
    MAX-ACCESS      read-create
    STATUS          current
    DESCRIPTION
        "Source IP-address of tcp acl group."
    ::= { aclTcpRuleEntry 4 }

aclTcpSrcWild         OBJECT-TYPE
    SYNTAX          IpAddress
    MAX-ACCESS      read-create
    STATUS          current
    DESCRIPTION
        "Source IP-address wild of tcp acl group."
    ::= { aclTcpRuleEntry 5 }

aclTcpDestIp         OBJECT-TYPE
    SYNTAX          IpAddress
    MAX-ACCESS      read-create
    STATUS          current
    DESCRIPTION
        "Destination IP-address of tcp acl group."
    ::= { aclTcpRuleEntry 6 }

aclTcpDestWild         OBJECT-TYPE
    SYNTAX          IpAddress
    MAX-ACCESS      read-create
    STATUS          current
    DESCRIPTION
        "Destination IP-address wild of tcp acl group."
    ::= { aclTcpRuleEntry 7 }

aclTcpPrecedence         OBJECT-TYPE
    SYNTAX          Integer32 (0..8)
    MAX-ACCESS      read-create
    STATUS          current
    DESCRIPTION
        "The value of Precedence.8 means do not use this filter.Range 0~8.
         DSCP and Precedence both use IP TOS segment.This node can not be setted for aclTcpDscp is setted."
    ::= { aclTcpRuleEntry 8 }

aclTcpDscp         OBJECT-TYPE
    SYNTAX          DSCPValue
    MAX-ACCESS      read-create
    STATUS          current
    DESCRIPTION
        "The value of DSCP.64 means do not use this filter.
         DSCP and Precedence both use IP TOS segment.This node can not be setted for aclTcpPrecedence is setted."
    ::= { aclTcpRuleEntry 9 }

aclTcpFragments         OBJECT-TYPE
    SYNTAX          TruthValue
    MAX-ACCESS      read-create
    STATUS          current
    DESCRIPTION
        "The flag of matching fragmented packet. True(1),False(2).
         This node can not be setted true for aclTcpSrcOp or aclTcpDestOp is setted."
    ::= { aclTcpRuleEntry 10 }

aclTcpRouted         OBJECT-TYPE
    SYNTAX          TruthValue
    MAX-ACCESS      read-create
    STATUS          current
    DESCRIPTION
        "The flag of matching routed packet. True(1),False(2)."
    ::= { aclTcpRuleEntry 11 }

aclTcpOptions         OBJECT-TYPE
    SYNTAX          TruthValue
    MAX-ACCESS      read-create
    STATUS          current
    DESCRIPTION
        "The flag of matching packet with ip option. True(1),False(2)."
    ::= { aclTcpRuleEntry 12 }

aclTcpSrcOp         OBJECT-TYPE
    SYNTAX          PortOp
    MAX-ACCESS      read-create
    STATUS          current
    DESCRIPTION
        "The source port's operator of tcp acl group.
            This node can not be setted if aclTcpFragments is true.
            eq(0),
            gt(2),
            lt(3),
            range(4),
            invalid(5)"
    ::= { aclTcpRuleEntry 13 }

aclTcpSrcPort1    OBJECT-TYPE
    SYNTAX          Integer32 (0..65535)
    MAX-ACCESS      read-create
    STATUS          current
    DESCRIPTION
        "The fourth layer source port1. Range 0~65535. "
    ::= { aclTcpRuleEntry 14 }

aclTcpSrcPort2    OBJECT-TYPE
    SYNTAX          Integer32 (0..65535)
    MAX-ACCESS      read-create
    STATUS          current
    DESCRIPTION
        "The fourth layer source port2. Range 0~65535."
    ::= { aclTcpRuleEntry 15 }

aclTcpDestOp         OBJECT-TYPE
    SYNTAX          PortOp
    MAX-ACCESS      read-create
    STATUS          current
    DESCRIPTION
        "The destination port's operator of tcp acl group.
         This node can not be setted if aclTcpFragments is true.
            eq(0),
            gt(2),
            lt(3),
            range(4),
            invalid(5)"
    ::= { aclTcpRuleEntry 16 }

aclTcpDestPort1    OBJECT-TYPE
    SYNTAX          Integer32 (0..65535)
    MAX-ACCESS      read-create
    STATUS          current
    DESCRIPTION
        "The fourth layer destination port1. Range 0~65535."
    ::= { aclTcpRuleEntry 17 }

aclTcpDestPort2    OBJECT-TYPE
    SYNTAX          Integer32 (0..65535)
    MAX-ACCESS      read-create
    STATUS          current
    DESCRIPTION
        "The fourth layer destination port2. Range 0~65535."
    ::= { aclTcpRuleEntry 18 }

aclTcpFlagOp         OBJECT-TYPE
    SYNTAX          INTEGER
        {
            matchAny(0),
            matchAll(1),
            invalid(2)
        }
    MAX-ACCESS      read-create
    STATUS          current
    DESCRIPTION
        "The tcp-flags' operator of tcp acl group.for example, established tcp packet with ack or rst flag setted, set this node matchAny(0) and set aclTcpFlagAck and aclTcpFlagRst can filter established tcp packet.
        matchAny(0),
        matchAll(1),
        invalid(2)."
    ::= { aclTcpRuleEntry 19 }

aclTcpFlagUrg         OBJECT-TYPE
    SYNTAX          TruthValue
    MAX-ACCESS      read-create
    STATUS          current
    DESCRIPTION
        "The tcp-urg flag of tcp acl group. True(1),False(2).
            TCP protocol URG Packet."
    ::= { aclTcpRuleEntry 20 }

aclTcpFlagAck         OBJECT-TYPE
    SYNTAX          TruthValue
    MAX-ACCESS      read-create
    STATUS          current
    DESCRIPTION
        "The tcp-ack flag of tcp acl group.
            TCP protocol ACK Packet. True(1),False(2)."
    ::= { aclTcpRuleEntry 21 }

aclTcpFlagPsh         OBJECT-TYPE
    SYNTAX          TruthValue
    MAX-ACCESS      read-create
    STATUS          current
    DESCRIPTION
        "The tcp-psh flag of tcp acl group. True(1),False(2).
            TCP protocol PSH Packet."
    ::= { aclTcpRuleEntry 22 }

aclTcpFlagRst         OBJECT-TYPE
    SYNTAX          TruthValue
    MAX-ACCESS      read-create
    STATUS          current
    DESCRIPTION
        "The tcp-rst flag of tcp acl group. True(1),False(2).
            TCP protocol RST Packet."
    ::= { aclTcpRuleEntry 23 }

aclTcpFlagSyn         OBJECT-TYPE
    SYNTAX          TruthValue
    MAX-ACCESS      read-create
    STATUS          current
    DESCRIPTION
        "The tcp-syn flag of tcp acl group. True(1),False(2).
            TCP protocol SYN Packet."
    ::= { aclTcpRuleEntry 24 }

aclTcpFlagFin         OBJECT-TYPE
    SYNTAX          TruthValue
    MAX-ACCESS      read-create
    STATUS          current
    DESCRIPTION
        "The tcp-fin flag of tcp acl group. True(1),False(2).
            TCP protocol FIN Packet."
    ::= { aclTcpRuleEntry 25 }

aclTcpTimeRangeName         OBJECT-TYPE
    SYNTAX          OCTET STRING (SIZE (0..20))
    MAX-ACCESS      read-create
    STATUS          current
    DESCRIPTION
        "The Time-range of tcp acl rule."
    ::= { aclTcpRuleEntry 26 }

aclTcpRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { aclTcpRuleEntry 28 }

--
-- aclUdpRuleTable
--
aclUdpRuleTable         OBJECT-TYPE
    SYNTAX          SEQUENCE OF AclUdpRuleEntry
    MAX-ACCESS      not-accessible
    STATUS          current
    DESCRIPTION
        "Configure the rule for udp acl group."
    ::= { aclData 5 }

aclUdpRuleEntry         OBJECT-TYPE
    SYNTAX          AclUdpRuleEntry
    MAX-ACCESS      not-accessible
    STATUS          current
    DESCRIPTION
        "Define the index of aclUdpRuleTable."
    INDEX         { aclUdpGroupIndex, aclUdpRuleIndex }
    ::= { aclUdpRuleTable 1 }

    AclUdpRuleEntry    ::=
    SEQUENCE {
            aclUdpGroupIndex
                Integer32,
            aclUdpRuleIndex
                Integer32,
            aclUdpAct
                RuleAction,
            aclUdpSrcIp
                IpAddress,
            aclUdpSrcWild
                IpAddress,
            aclUdpDestIp
                IpAddress,
            aclUdpDestWild
                IpAddress,
            aclUdpPrecedence
                Integer32,
            aclUdpDscp
                DSCPValue,
            aclUdpFragments
                TruthValue,
            aclUdpRouted
                TruthValue,
            aclUdpOptions
                TruthValue,
            aclUdpSrcOp
                PortOp,
            aclUdpSrcPort1
                Integer32,
            aclUdpSrcPort2
                Integer32,
            aclUdpDestOp
                PortOp,
            aclUdpDestPort1
                Integer32,
            aclUdpDestPort2
                Integer32,
            aclUdpTimeRangeName
                OCTET STRING,
            aclUdpRowStatus 
                RowStatus 
         }

aclUdpGroupIndex         OBJECT-TYPE
    SYNTAX          Integer32 (20001..40000)
    MAX-ACCESS      not-accessible
    STATUS          current
    DESCRIPTION
        "The index of udp acl group. Range 20001~40000."
    ::= { aclUdpRuleEntry 1 }

aclUdpRuleIndex         OBJECT-TYPE
    SYNTAX          Integer32 (1..131071)
    MAX-ACCESS      not-accessible
    STATUS          current
    DESCRIPTION
        "The rule index of udp acl group. Range 1~131071."
    ::= { aclUdpRuleEntry 2 }

aclUdpAct         OBJECT-TYPE
    SYNTAX          RuleAction
    MAX-ACCESS      read-create
    STATUS          current
    DESCRIPTION
        "The action of udp acl rule.
         (1) permit.
         (2) deny"
    ::= { aclUdpRuleEntry 3 }

aclUdpSrcIp         OBJECT-TYPE
    SYNTAX          IpAddress
    MAX-ACCESS      read-create
    STATUS          current
    DESCRIPTION
        "Source IP-address of udp acl group."
    ::= { aclUdpRuleEntry 4 }

aclUdpSrcWild         OBJECT-TYPE
    SYNTAX          IpAddress
    MAX-ACCESS      read-create
    STATUS          current
    DESCRIPTION
        "Source IP-address wild of udp acl group."
    ::= { aclUdpRuleEntry 5 }

aclUdpDestIp         OBJECT-TYPE
    SYNTAX          IpAddress
    MAX-ACCESS      read-create
    STATUS          current
    DESCRIPTION
        "Destination IP-address of udp acl group."
    ::= { aclUdpRuleEntry 6 }

aclUdpDestWild         OBJECT-TYPE
    SYNTAX          IpAddress
    MAX-ACCESS      read-create
    STATUS          current
    DESCRIPTION
        "Destination IP-address wild of udp acl group."
    ::= { aclUdpRuleEntry 7 }

aclUdpPrecedence         OBJECT-TYPE
    SYNTAX          Integer32 (0..8)
    MAX-ACCESS      read-create
    STATUS          current
    DESCRIPTION
        "The value of Precedence.8 means do not use this filter.Range 0~8.
         DSCP and Precedence both use IP TOS segment.This node can not be setted for aclUdpDscp is setted."
    ::= { aclUdpRuleEntry 8 }

aclUdpDscp         OBJECT-TYPE
    SYNTAX          DSCPValue
    MAX-ACCESS      read-create
    STATUS          current
    DESCRIPTION
        "The value of DSCP.64 means do not use this filter.
         DSCP and Precedence both use IP TOS segment.This node can not be setted for aclUdpPrecedence is setted."
    ::= { aclUdpRuleEntry 9 }

aclUdpFragments         OBJECT-TYPE
    SYNTAX          TruthValue
    MAX-ACCESS      read-create
    STATUS          current
    DESCRIPTION
        "The flag of matching fragmented packet. True(1),False(2).
         This node can not be setted true for aclUdpSrcOp or aclUdpDestOp is setted."
    ::= { aclUdpRuleEntry 10 }

aclUdpRouted         OBJECT-TYPE
    SYNTAX          TruthValue
    MAX-ACCESS      read-create
    STATUS          current
    DESCRIPTION
        "The flag of matching routed packet. True(1),False(2)."
    ::= { aclUdpRuleEntry 11 }

aclUdpOptions         OBJECT-TYPE
    SYNTAX          TruthValue
    MAX-ACCESS      read-create
    STATUS          current
    DESCRIPTION
        "The flag of matching packet with ip option. True(1),False(2)."
    ::= { aclUdpRuleEntry 12 }

aclUdpSrcOp         OBJECT-TYPE
    SYNTAX          PortOp
    MAX-ACCESS      read-create
    STATUS          current
    DESCRIPTION
        "The source port's operator of udp acl group.
            This node can not be setted if aclUdpFragments is true.
            eq(0),
            gt(2),
            lt(3),
            range(4),
            invalid(5)"
    ::= { aclUdpRuleEntry 13 }

aclUdpSrcPort1    OBJECT-TYPE
    SYNTAX          Integer32 (0..65535)
    MAX-ACCESS      read-create
    STATUS          current
    DESCRIPTION
        "The fourth layer source port1. Range 0~65535."
    ::= { aclUdpRuleEntry 14 }

aclUdpSrcPort2    OBJECT-TYPE
    SYNTAX          Integer32 (0..65535)
    MAX-ACCESS      read-create
    STATUS          current
    DESCRIPTION
        "The fourth layer source port2. Range 0~65535."
    ::= { aclUdpRuleEntry 15 }

aclUdpDestOp         OBJECT-TYPE
    SYNTAX          PortOp
    MAX-ACCESS      read-create
    STATUS          current
    DESCRIPTION
        "The destination port's operator of udp acl group.
         This node can not be setted if aclUdpFragments is true.
            eq(0),
            gt(2),
            lt(3),
            range(4),
            invalid(5)"
    ::= { aclUdpRuleEntry 16 }

aclUdpDestPort1    OBJECT-TYPE
    SYNTAX          Integer32 (0..65535)
    MAX-ACCESS      read-create
    STATUS          current
    DESCRIPTION
        "The fourth layer destination port1. Range 0~65535."
    ::= { aclUdpRuleEntry 17 }

aclUdpDestPort2    OBJECT-TYPE
    SYNTAX          Integer32 (0..65535)
    MAX-ACCESS      read-create
    STATUS          current
    DESCRIPTION
        "The fourth layer destination port2. Range 0~65535."
    ::= { aclUdpRuleEntry 18 }

aclUdpTimeRangeName         OBJECT-TYPE
    SYNTAX          OCTET STRING (SIZE (0..20))
    MAX-ACCESS      read-create
    STATUS          current
    DESCRIPTION
        "The Time-range of udp acl rule. Range 0~20."
    ::= { aclUdpRuleEntry 19 }

aclUdpRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { aclUdpRuleEntry 21 }

--
-- aclIcmpRuleTable
--
aclIcmpRuleTable         OBJECT-TYPE
    SYNTAX          SEQUENCE OF AclIcmpRuleEntry
    MAX-ACCESS      not-accessible
    STATUS          current
    DESCRIPTION
        "Configure the rule for icmp acl group."
    ::= { aclData 6 }
    
aclIcmpRuleEntry         OBJECT-TYPE
    SYNTAX          AclIcmpRuleEntry
    MAX-ACCESS      not-accessible
    STATUS          current
    DESCRIPTION
        "Define the index of aclIcmpRuleTable."
     INDEX        { aclIcmpGroupIndex, aclIcmpRuleIndex }
    ::= { aclIcmpRuleTable 1 }

    AclIcmpRuleEntry    ::=
    SEQUENCE {
            aclIcmpGroupIndex
                Integer32,
            aclIcmpRuleIndex
                Integer32,
            aclIcmpAct
                RuleAction,
            aclIcmpSrcIp
                IpAddress,
            aclIcmpSrcWild
                IpAddress,
            aclIcmpDestIp
                IpAddress,
            aclIcmpDestWild
                IpAddress,
            aclIcmpPrecedence
                Integer32,
            aclIcmpDscp
                DSCPValue,
            aclIcmpFragments
                TruthValue,
            aclIcmpRouted
                TruthValue,
            aclIcmpOptions
                TruthValue,
            aclIcmpType
                Integer32,
            aclIcmpCode
                Integer32,
            aclIcmpTimeRangeName
                OCTET STRING,
            aclIcmpRowStatus 
                RowStatus 
         }

aclIcmpGroupIndex         OBJECT-TYPE
    SYNTAX          Integer32 (20001..40000)
    MAX-ACCESS      not-accessible
    STATUS          current
    DESCRIPTION
        "The index of icmp acl group. Range 20001~40000."
    ::= { aclIcmpRuleEntry 1 }

aclIcmpRuleIndex         OBJECT-TYPE
    SYNTAX          Integer32 (1..131071)
    MAX-ACCESS      not-accessible
    STATUS          current
    DESCRIPTION
        "The rule index of icmp acl group. Range 1~131071."
    ::= { aclIcmpRuleEntry 2 }

aclIcmpAct         OBJECT-TYPE
    SYNTAX          RuleAction
    MAX-ACCESS      read-create
    STATUS          current
    DESCRIPTION
        "The action of icmp acl rule.
         (1) permit.
         (2) deny"
    ::= { aclIcmpRuleEntry 3 }

aclIcmpSrcIp         OBJECT-TYPE
    SYNTAX          IpAddress
    MAX-ACCESS      read-create
    STATUS          current
    DESCRIPTION
        "Source IP-address of icmp acl group."
    ::= { aclIcmpRuleEntry 4 }

aclIcmpSrcWild         OBJECT-TYPE
    SYNTAX          IpAddress
    MAX-ACCESS      read-create
    STATUS          current
    DESCRIPTION
        "Source IP-address wild of icmp acl group."
    ::= { aclIcmpRuleEntry 5 }

aclIcmpDestIp         OBJECT-TYPE
    SYNTAX          IpAddress
    MAX-ACCESS      read-create
    STATUS          current
    DESCRIPTION
        "Destination IP-address of icmp acl group."
    ::= { aclIcmpRuleEntry 6 }

aclIcmpDestWild         OBJECT-TYPE
    SYNTAX          IpAddress
    MAX-ACCESS      read-create
    STATUS          current
    DESCRIPTION
        "Destination IP-address wild of icmp acl group."
    ::= { aclIcmpRuleEntry 7 }

aclIcmpPrecedence         OBJECT-TYPE
    SYNTAX          Integer32 (0..8)
    MAX-ACCESS      read-create
    STATUS          current
    DESCRIPTION
        "The value of Precedence.8 means do not use this filter.Range 0~8.
         DSCP and Precedence both use IP TOS segment.This node can not be setted for aclIcmpDscp is setted."
    ::= { aclIcmpRuleEntry 8 }

aclIcmpDscp         OBJECT-TYPE
    SYNTAX          DSCPValue
    MAX-ACCESS      read-create
    STATUS          current
    DESCRIPTION
        "The value of DSCP.64 means do not use this filter.
         DSCP and Precedence both use IP TOS segment.This node can not be setted for aclIcmpPrecedence is setted."
    ::= { aclIcmpRuleEntry 9 }
    
aclIcmpFragments         OBJECT-TYPE
    SYNTAX          TruthValue
    MAX-ACCESS      read-create
    STATUS          current
    DESCRIPTION
        "The flag of matching fragmented packet.
            This node can not be setted true if aclIcmpType is setted. True(1),False(2)."
    ::= { aclIcmpRuleEntry 10 }

aclIcmpRouted         OBJECT-TYPE
    SYNTAX          TruthValue
    MAX-ACCESS      read-create
    STATUS          current
    DESCRIPTION
        "The flag of matching routed packet. True(1),False(2)."
    ::= { aclIcmpRuleEntry 11 }

aclIcmpOptions         OBJECT-TYPE
    SYNTAX          TruthValue
    MAX-ACCESS      read-create
    STATUS          current
    DESCRIPTION
        "The flag of matching packet with ip option. True(1),False(2)."
    ::= { aclIcmpRuleEntry 12 }

aclIcmpType         OBJECT-TYPE
    SYNTAX          Integer32 (0..256)
    MAX-ACCESS      read-create
    STATUS          current
    DESCRIPTION
        "The type of ICMP packet.
            INTEGER<0-256>        ICMP type
            echo                  Type=8, Code=0
            echo-reply            Type=0, Code=0
            fragmentneed-DFset    Type=3, Code=4
            host-redirect         Type=5, Code=1
            host-tos-redirect     Type=5, Code=3
            host-unreachable      Type=3, Code=1
            information-reply     Type=16, Code=0
            information-request   Type=15, Code=0
            net-redirect          Type=5, Code=0
            net-tos-redirect      Type=5, Code=2
            net-unreachable       Type=3, Code=0
            parameter-problem     Type=12, Code=0
            port-unreachable      Type=3, Code=3
            protocol-unreachable  Type=3, Code=2
            reassembly-timeout    Type=11, Code=1
            source-quench         Type=4, Code=0
            source-route-failed   Type=3, Code=5
            timestamp-reply       Type=14, Code=0
            timestamp-request     Type=13, Code=0
            ttl-exceeded          Type=11, Code=0
            nouse                 256
            This node can not be setted if aclIcmpFragments is true."
    ::= { aclIcmpRuleEntry 13 }

aclIcmpCode         OBJECT-TYPE
    SYNTAX          Integer32 (0..256)
    MAX-ACCESS      read-create
    STATUS          current
    DESCRIPTION
        "The code of ICMP packet.INTEGER<0-256>
            echo                  Type=8, Code=0
            echo-reply            Type=0, Code=0
            fragmentneed-DFset    Type=3, Code=4
            host-redirect         Type=5, Code=1
            host-tos-redirect     Type=5, Code=3
            host-unreachable      Type=3, Code=1
            information-reply     Type=16, Code=0
            information-request   Type=15, Code=0
            net-redirect          Type=5, Code=0
            net-tos-redirect      Type=5, Code=2
            net-unreachable       Type=3, Code=0
            parameter-problem     Type=12, Code=0
            port-unreachable      Type=3, Code=3
            protocol-unreachable  Type=3, Code=2
            reassembly-timeout    Type=11, Code=1
            source-quench         Type=4, Code=0
            source-route-failed   Type=3, Code=5
            timestamp-reply       Type=14, Code=0
            timestamp-request     Type=13, Code=0
            ttl-exceeded          Type=11, Code=0
            nouse                 256        
            This node can not be setted if aclIcmpType is not setted."
    ::= { aclIcmpRuleEntry 14 }

aclIcmpTimeRangeName         OBJECT-TYPE
    SYNTAX          OCTET STRING (SIZE (0..20))
    MAX-ACCESS      read-create
    STATUS          current
    DESCRIPTION
        "The Time-range of icmp acl rule. Range 0~20."
    ::= { aclIcmpRuleEntry 15 }

aclIcmpRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { aclIcmpRuleEntry 17 }
        

--
-- aclIgmpRuleTable
--
aclIgmpRuleTable         OBJECT-TYPE
    SYNTAX          SEQUENCE OF AclIgmpRuleEntry
    MAX-ACCESS      not-accessible
    STATUS          current
    DESCRIPTION
        "Configure the rule for igmp acl group."
    ::= { aclData 7 }

aclIgmpRuleEntry         OBJECT-TYPE
    SYNTAX          AclIgmpRuleEntry
    MAX-ACCESS      not-accessible
    STATUS          current
    DESCRIPTION
        "Define the index of aclIgmpRuleTable."
    INDEX         { aclIgmpGroupIndex, aclIgmpRuleIndex }
    ::= { aclIgmpRuleTable 1 }

    AclIgmpRuleEntry    ::=
    SEQUENCE {
            aclIgmpGroupIndex
                Integer32,
            aclIgmpRuleIndex
                Integer32,
            aclIgmpAct
                RuleAction,
            aclIgmpSrcIp
                IpAddress,
            aclIgmpSrcWild
                IpAddress,
            aclIgmpDestIp
                IpAddress,
            aclIgmpDestWild
                IpAddress,
            aclIgmpPrecedence
                Integer32,
            aclIgmpDscp
                DSCPValue,
            aclIgmpFragments
                TruthValue,
            aclIgmpRouted
                TruthValue,
            aclIgmpOptions
                TruthValue,
            aclIgmpType
                INTEGER,
            aclIgmpTimeRangeName
                OCTET STRING,
            aclIgmpRowStatus 
                RowStatus 
         }

aclIgmpGroupIndex         OBJECT-TYPE
    SYNTAX          Integer32 (20001..40000)
    MAX-ACCESS      not-accessible
    STATUS          current
    DESCRIPTION
        "The index of igmp acl group. Range 20001~40000."
    ::= { aclIgmpRuleEntry 1 }

aclIgmpRuleIndex         OBJECT-TYPE
    SYNTAX          Integer32 (1..131071)
    MAX-ACCESS      not-accessible
    STATUS          current
    DESCRIPTION
        "The rule index of igmp acl group.Range 1~131071."
    ::= { aclIgmpRuleEntry 2 }

aclIgmpAct         OBJECT-TYPE
    SYNTAX          RuleAction
    MAX-ACCESS      read-create
    STATUS          current
    DESCRIPTION
        "The action of igmp acl rule.
         (1) permit.
         (2) deny"
    ::= { aclIgmpRuleEntry 3 }

aclIgmpSrcIp         OBJECT-TYPE
    SYNTAX          IpAddress
    MAX-ACCESS      read-create
    STATUS          current
    DESCRIPTION
        "Source IP-address of igmp acl group."
    ::= { aclIgmpRuleEntry 4 }

aclIgmpSrcWild         OBJECT-TYPE
    SYNTAX          IpAddress
    MAX-ACCESS      read-create
    STATUS          current
    DESCRIPTION
        "Source IP-address wild of igmp acl group."
    ::= { aclIgmpRuleEntry 5 }

aclIgmpDestIp         OBJECT-TYPE
    SYNTAX          IpAddress
    MAX-ACCESS      read-create
    STATUS          current
    DESCRIPTION
        "Destination IP-address of igmp acl group."
    ::= { aclIgmpRuleEntry 6 }

aclIgmpDestWild         OBJECT-TYPE
    SYNTAX          IpAddress
    MAX-ACCESS      read-create
    STATUS          current
    DESCRIPTION
        "Destination IP-address wild of igmp acl group."
    ::= { aclIgmpRuleEntry 7 }

aclIgmpPrecedence         OBJECT-TYPE
    SYNTAX          Integer32 (0..8)
    MAX-ACCESS      read-create
    STATUS          current
    DESCRIPTION
        "The value of Precedence.8 means do not use this filter.Range 0~8.
         DSCP and Precedence both use IP TOS segment.This node can not be setted for aclIgmpDscp is setted."
    ::= { aclIgmpRuleEntry 8 }

aclIgmpDscp         OBJECT-TYPE
    SYNTAX          DSCPValue
    MAX-ACCESS      read-create
    STATUS          current
    DESCRIPTION
        "The value of DSCP.64 means do not use this filter.
         DSCP and Precedence both use IP TOS segment.This node can not be setted for aclIgmpPrecedence is setted."
    ::= { aclIgmpRuleEntry 9 }

aclIgmpFragments         OBJECT-TYPE
    SYNTAX          TruthValue
    MAX-ACCESS      read-create
    STATUS          current
    DESCRIPTION
        "The flag of matching fragmented packet.
         This node can not be setted true if aclIgmpType is setted. True(1),False(2)."
    ::= { aclIgmpRuleEntry 10 }

aclIgmpRouted         OBJECT-TYPE
    SYNTAX          TruthValue
    MAX-ACCESS      read-create
    STATUS          current
    DESCRIPTION
        "The flag of matching routed packet. True(1),False(2)."
    ::= { aclIgmpRuleEntry 11 }

aclIgmpOptions         OBJECT-TYPE
    SYNTAX          TruthValue
    MAX-ACCESS      read-create
    STATUS          current
    DESCRIPTION
        "The flag of matching packet with ip option.True(1),False(2)."
    ::= { aclIgmpRuleEntry 12 }

aclIgmpType         OBJECT-TYPE
    SYNTAX          INTEGER
        {
            precedence(0),
            hostQuery(17),
            hostReport(18),
            dvmrp(19),
            pim(20),
            trace(21),
            v2Report(22),
            v2Leave(23),
            mtraceResponse(30),
            mtrace(31),
            v3Report(34),
            invalid(256)
        }
    MAX-ACCESS      read-create
    STATUS          current
    DESCRIPTION
        "The type of ICMP packet.
               0         precedence
               17        host query
               18        host report
               19        dvmrp
               20        pim
               21        trace
               22        v2 report
               23        v2 leave
               30        mtrace response
               31        mtrace
               34        v3 report
               256       nouse
           This node can not be setted if aclIgmpFragments is true."
    ::= { aclIgmpRuleEntry 13 }

aclIgmpTimeRangeName         OBJECT-TYPE
    SYNTAX          OCTET STRING (SIZE (0..20))
    MAX-ACCESS      read-create
    STATUS          current
    DESCRIPTION
        "The Time-range of igmp acl rule.Range 0~20."
    ::= { aclIgmpRuleEntry 14 }

aclIgmpRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { aclIgmpRuleEntry 16 }

--
-- Nodes of aclMplsMacRuleTable
--
aclMplsMacRuleTable       OBJECT-TYPE
    SYNTAX          SEQUENCE OF AclMplsMacRuleEntry
    MAX-ACCESS      not-accessible
    STATUS          current
    DESCRIPTION
        "A table of MPLS MAC acl group.
             If some objects of this table are not supported by some products,
             these objects can't be created, changed and applied.
             Default value of these objects will be returned when they are read.
        "
    ::= { aclData 8 }

aclMplsMacRuleEntry       OBJECT-TYPE
    SYNTAX          AclMplsMacRuleEntry
    MAX-ACCESS      not-accessible
    STATUS          current
    DESCRIPTION
        "MPLS MAC acl group information."
    INDEX         { aclMplsMacGroupIndex, aclMplsMacRuleIndex }
    ::= { aclMplsMacRuleTable 1 }

    AclMplsMacRuleEntry    ::=
    SEQUENCE
        {
            aclMplsMacGroupIndex
                Integer32,
            aclMplsMacRuleIndex
                Integer32,
            aclMplsMacAct
                RuleAction,
            aclMplsMacSrcMac
                MacAddress ,
            aclMplsMacSrcMacWild
                MacAddress ,
            aclMplsMacDestMac
                MacAddress ,
            aclMplsMacDestMacWild
                MacAddress ,
            aclMplsMacType
                Integer32,
            aclMplsMacVlanId
                Integer32,
            aclMplsMacInnerVlanId
                Integer32,
            aclMplsMacCos
                Integer32,
            aclMplsMacInnerCos
                Integer32,
            aclMplsMacTimeRangeName
                OCTET STRING,
            aclMplsMacRowStatus
                RowStatus
         }

aclMplsMacGroupIndex      OBJECT-TYPE
    SYNTAX          Integer32 (70001..80000)
    MAX-ACCESS      not-accessible
    STATUS          current
    DESCRIPTION
        "The index of MPLS MAC-based acl group. Range 70001 ~ 80000."
    ::= { aclMplsMacRuleEntry 1 }

aclMplsMacRuleIndex       OBJECT-TYPE
    SYNTAX          Integer32 (1..131071)
    MAX-ACCESS      not-accessible
    STATUS          current
    DESCRIPTION
        "The rule index of MPLS MAC-based acl group. Range 1~131071."
    ::= { aclMplsMacRuleEntry 2 }

aclMplsMacAct             OBJECT-TYPE
    SYNTAX          RuleAction
    MAX-ACCESS      read-create
    STATUS          current
    DESCRIPTION
        "The action of MPLS MAC acl rule.
         (1) permit.
         (2) deny."
    ::= { aclMplsMacRuleEntry 3 }

aclMplsMacSrcMac          OBJECT-TYPE
    SYNTAX          MacAddress
    MAX-ACCESS      read-create
    STATUS          current
    DESCRIPTION
        "Source MAC of MPLS MAC acl rule."
    ::= { aclMplsMacRuleEntry 4 }

aclMplsMacSrcMacWild      OBJECT-TYPE
    SYNTAX          MacAddress
    MAX-ACCESS      read-create
    STATUS          current
    DESCRIPTION
        "Source MAC wildcard of MPLS MAC acl rule."
    ::= { aclMplsMacRuleEntry 5 }

aclMplsMacDestMac         OBJECT-TYPE
    SYNTAX          MacAddress
    MAX-ACCESS      read-create
    STATUS          current
    DESCRIPTION
        "Destination MAC of MAC acl rule.
             If you do not want to use this filter,
             set this item and aclMacDestMacWild 'FF:FF:FF:FF:FF:FF'."
    ::= { aclMplsMacRuleEntry 6 }

aclMplsMacDestMacWild     OBJECT-TYPE
    SYNTAX          MacAddress
    MAX-ACCESS      read-create
    STATUS          current
    DESCRIPTION
        "Destination MAC wildcard of MAC acl rule. If you do not want to use
        this filter, set this item and aclMacDestMac 'FF:FF:FF:FF:FF:FF'."
    ::= { aclMplsMacRuleEntry 7 }


aclMplsMacType         OBJECT-TYPE
    SYNTAX          Integer32 (0..3)
    MAX-ACCESS      read-create
    STATUS          current
    DESCRIPTION
        "The type of protocol
              nouse(0)
              eth2(1)
              sap(2)
              snap(3)        "
    ::= { aclMplsMacRuleEntry 8 }

aclMplsMacVlanId         OBJECT-TYPE
    SYNTAX          Integer32 (0..4094)
    MAX-ACCESS      read-create
    STATUS          current
    DESCRIPTION
        "The vlan id of MAC acl rule.Range 0~4094.
             nouse(0)        "
    ::= { aclMplsMacRuleEntry 9 }

aclMplsMacInnerVlanId         OBJECT-TYPE
    SYNTAX          Integer32 (0..4094)
    MAX-ACCESS      read-create
    STATUS          current
    DESCRIPTION
        "The inner vlan id of MAC acl rule.
             nouse(0)        "
    ::= { aclMplsMacRuleEntry 10 }

aclMplsMacCos         OBJECT-TYPE
    SYNTAX          Integer32 (0..8)
    MAX-ACCESS      read-create
    STATUS          current
    DESCRIPTION
        "Vlan priority of MAC acl rule.Range 0~8
         nouse(8)."
    ::= { aclMplsMacRuleEntry 11 }

aclMplsMacInnerCos         OBJECT-TYPE
    SYNTAX          Integer32 (0..8)
    MAX-ACCESS      read-create
    STATUS          current
    DESCRIPTION
        "Inner vlan priority of MAC acl rule.
         nouse(8)."
    ::= { aclMplsMacRuleEntry 12 }

aclMplsMacTimeRangeName         OBJECT-TYPE
    SYNTAX          OCTET STRING (SIZE(0..20))
    MAX-ACCESS      read-create
    STATUS          current
    DESCRIPTION
        "The Time-range of MAC acl rule."
    ::= { aclMplsMacRuleEntry 13 }

aclMplsMacRowStatus         OBJECT-TYPE
    SYNTAX          RowStatus
    MAX-ACCESS      read-create
    STATUS          current
    DESCRIPTION
        "The status of this row.Now only realize CreateAndGo and Destroy and Active."
    ::= { aclMplsMacRuleEntry 20 }



--
-- aclMplsLabelRuleTable
--
aclMplsLabelRuleTable         OBJECT-TYPE
    SYNTAX          SEQUENCE OF AclMplsLabelRuleEntry
    MAX-ACCESS      not-accessible
    STATUS          current
    DESCRIPTION
        "Configure the rule for Mpls Label acl group."
    ::= { aclData 9 }

aclMplsLabelRuleEntry         OBJECT-TYPE
    SYNTAX          AclMplsLabelRuleEntry
    MAX-ACCESS      not-accessible
    STATUS          current
    DESCRIPTION
        "Define the index of acl Mpls Label RuleTable."
    INDEX          { aclMplsLabelGroupIndex, aclMplsLabelRuleIndex }
    ::= { aclMplsLabelRuleTable 1 }

    AclMplsLabelRuleEntry    ::=
    SEQUENCE {
            aclMplsLabelGroupIndex
                Integer32,
            aclMplsLabelRuleIndex
                Integer32,
            aclMplsLabelAct
                RuleAction,
            aclMplsLabelLayer
                Integer32,
            aclMplsLabel1Value
                Integer32,
            aclMplsLabel1Wild
                OCTET STRING,
            aclMplsLabel1Exp
                Integer32,
            aclMplsLabel1Ttl
                Integer32,
            aclMplsLabel2Value
                Integer32,
            aclMplsLabel2Wild
                OCTET STRING,
            aclMplsLabel2Exp
                Integer32,
            aclMplsLabel2Ttl
                Integer32,
            aclMplsLabel3Value
                Integer32,
            aclMplsLabel3Wild
                OCTET STRING,
            aclMplsLabel3Exp
                Integer32,
            aclMplsLabel3Ttl
                Integer32,
            aclMplsLabel4Value
                Integer32,
            aclMplsLabel4Wild
                OCTET STRING,
            aclMplsLabel4Exp
                Integer32,
            aclMplsLabel4Ttl
                Integer32,
            aclMplsLabelSkBottom
                TruthValue,
            aclMplsLabelTimeRangeName
                OCTET STRING,
            aclMplsLabelRowStatus
                RowStatus
         }

aclMplsLabelGroupIndex         OBJECT-TYPE
    SYNTAX          Integer32 (60001..80000)
    MAX-ACCESS      not-accessible
    STATUS          current
    DESCRIPTION
        "The index of MplsLabel acl group. Range 60001~80000."
    ::= { aclMplsLabelRuleEntry 1 }

aclMplsLabelRuleIndex         OBJECT-TYPE
    SYNTAX          Integer32 (1..131071)
    MAX-ACCESS      not-accessible
    STATUS          current
    DESCRIPTION
        "The rule index of MplsLabel acl rule.Range 1~131071."
    ::= { aclMplsLabelRuleEntry 2 }

aclMplsLabelAct         OBJECT-TYPE
    SYNTAX          RuleAction
    MAX-ACCESS      read-create
    STATUS          current
    DESCRIPTION
        "The action of MplsLabel acl rule.
         (1) permit.
         (2) deny."
    ::= { aclMplsLabelRuleEntry 3 }

aclMplsLabelLayer          OBJECT-TYPE
    SYNTAX          Integer32 (1..4)
    MAX-ACCESS      read-create
    STATUS          current
    DESCRIPTION
        "The layer number of MPLS labels.Range is <1-4>.
         Set 1 means match MPLS packets with more than
         (or equal to) one layer MPLS label.
         Set 2 means match MPLS packets with more than
         (or equal to) two layer MPLS label.
         Set 3 means match MPLS packets with more than
         (or equal to) three layer MPLS label.
         Set 4 means match MPLS packets with more than
         (or equal to) four layer MPLS label."
    ::= { aclMplsLabelRuleEntry 4 }


aclMplsLabel1Value         OBJECT-TYPE
    SYNTAX          Integer32 (0..1048575)
    MAX-ACCESS      read-create
    STATUS          current
    DESCRIPTION
        "The mpls label1 value in in decimal system.
         Range is 0~1048575.Default value is 0."
    ::= { aclMplsLabelRuleEntry 5 }

aclMplsLabel1Wild        OBJECT-TYPE
    SYNTAX          OCTET STRING (SIZE(0..5))
    MAX-ACCESS      read-create
    STATUS          current
    DESCRIPTION
        "MPLS label wildcard in hexadecimal system.
         Range is string 0~fffff.
         Default wild value is fffff, means any."
    ::= { aclMplsLabelRuleEntry 6 }

aclMplsLabel1Exp         OBJECT-TYPE
    SYNTAX          Integer32 (0..8)
    MAX-ACCESS      read-create
    STATUS          current
    DESCRIPTION
        "The exp value of the MPLS label.Range of exp is <0-7>.
         8 means do not use.Default value is 8."
    ::= { aclMplsLabelRuleEntry 7 }

aclMplsLabel1Ttl         OBJECT-TYPE
    SYNTAX          Integer32 (0..256)
    MAX-ACCESS      read-create
    STATUS          current
    DESCRIPTION
        "The ttl value of the MPLS label.Range of ttl is <0-255>.
         256 means do not use.Default value is 256."
    ::= { aclMplsLabelRuleEntry 8 }

aclMplsLabel2Value         OBJECT-TYPE
    SYNTAX          Integer32 (0..1048575)
    MAX-ACCESS      read-create
    STATUS          current
    DESCRIPTION
        "The mpls label value in in decimal system.
         Range is 0~1048575.Default value is 0."
    ::= { aclMplsLabelRuleEntry 9 }

aclMplsLabel2Wild        OBJECT-TYPE
    SYNTAX          OCTET STRING (SIZE(0..5))
    MAX-ACCESS      read-create
    STATUS          current
    DESCRIPTION
        "MPLS label wildcard in hexadecimal system.
         Range is string 0~fffff.
         Defalut wild value is fffff, means any."
    ::= { aclMplsLabelRuleEntry 10 }

aclMplsLabel2Exp         OBJECT-TYPE
    SYNTAX          Integer32 (0..8)
    MAX-ACCESS      read-create
    STATUS          current
    DESCRIPTION
        "The exp value of the MPLS label.Range of exp is <0-7>.
         8 means do not use.Default value is 8."
    ::= { aclMplsLabelRuleEntry 11 }

aclMplsLabel2Ttl         OBJECT-TYPE
    SYNTAX          Integer32 (0..256)
    MAX-ACCESS      read-create
    STATUS          current
    DESCRIPTION
        "The ttl value of the MPLS label.Range of ttl is <0-255>.
         256 means do not use.Default value is 256."
    ::= { aclMplsLabelRuleEntry 12 }

aclMplsLabel3Value         OBJECT-TYPE
    SYNTAX          Integer32 (0..1048575)
    MAX-ACCESS      read-create
    STATUS          current
    DESCRIPTION
        "The mpls label value in in decimal system.
         Range is 0~1048575.Default value is 0."
    ::= { aclMplsLabelRuleEntry 13 }

aclMplsLabel3Wild        OBJECT-TYPE
    SYNTAX          OCTET STRING (SIZE(0..5))
    MAX-ACCESS      read-create
    STATUS          current
    DESCRIPTION
        "MPLS label wildcard in hexadecimal system.
         Range is string 0~fffff.
         Default wild value is fffff, means any."
    ::= { aclMplsLabelRuleEntry 14 }

aclMplsLabel3Exp         OBJECT-TYPE
    SYNTAX          Integer32 (0..8)
    MAX-ACCESS      read-create
    STATUS          current
    DESCRIPTION
        "The exp value of the MPLS label.Range of exp is <0-7>.
         8 means do not use.Default value is 8."
    ::= { aclMplsLabelRuleEntry 15 }

aclMplsLabel3Ttl         OBJECT-TYPE
    SYNTAX          Integer32 (0..256)
    MAX-ACCESS      read-create
    STATUS          current
    DESCRIPTION
        "The ttl value of the MPLS label.Range of ttl is <0-255>.
         256 means do not use.Default value is 256."
    ::= { aclMplsLabelRuleEntry 16 }

aclMplsLabel4Value         OBJECT-TYPE
    SYNTAX          Integer32 (0..1048575)
    MAX-ACCESS      read-create
    STATUS          current
    DESCRIPTION
        "The mpls label value in in decimal system.
         Range is 0~1048575.Default value is 0."
    ::= { aclMplsLabelRuleEntry 17 }

aclMplsLabel4Wild        OBJECT-TYPE
    SYNTAX          OCTET STRING (SIZE(0..5))
    MAX-ACCESS      read-create
    STATUS          current
    DESCRIPTION
        "MPLS label wildcard in hexadecimal system.
         Range is string 0~fffff.
         Default wild value is fffff, means any."
    ::= { aclMplsLabelRuleEntry 18 }

aclMplsLabel4Exp         OBJECT-TYPE
    SYNTAX          Integer32 (0..8)
    MAX-ACCESS      read-create
    STATUS          current
    DESCRIPTION
        "The exp value of the MPLS label.Range of exp is <0-7>.
         8 means do not use.Default value is 8."
    ::= { aclMplsLabelRuleEntry 19 }

aclMplsLabel4Ttl         OBJECT-TYPE
    SYNTAX          Integer32 (0..256)
    MAX-ACCESS      read-create
    STATUS          current
    DESCRIPTION
        "The ttl value of the MPLS label.Range of ttl is <0-255>.
         256 means do not use.Default value is 256."
    ::= { aclMplsLabelRuleEntry 20 }

aclMplsLabelSkBottom         OBJECT-TYPE
    SYNTAX          TruthValue
    MAX-ACCESS      read-create
    STATUS          current
    DESCRIPTION
        "Set whether the topmost label as bottom of label stack.
         True(1), means matching MPLS packets with
                  label layer num equal to aclMplsLabelLayer.
         False(2), means matching MPLS packets with
                   label layer num more than aclMplsLabelLayer.
         Default value is False."
    ::= { aclMplsLabelRuleEntry 21 }

aclMplsLabelTimeRangeName         OBJECT-TYPE
    SYNTAX          OCTET STRING (SIZE (0..20))
    MAX-ACCESS      read-create
    STATUS          current
    DESCRIPTION
        "The Time-range of used by the MPLS filter rule."
    ::= { aclMplsLabelRuleEntry 22 }

aclMplsLabelRowStatus         OBJECT-TYPE
    SYNTAX          RowStatus
    MAX-ACCESS      read-create
    STATUS          current
    DESCRIPTION
        "The status of this conceptual row.Now only realize CreateAndGo and Destroy and Active."
    ::= { aclMplsLabelRuleEntry 25 }


--
-- aclIpv6RuleTable
--
aclIpv6RuleTable         OBJECT-TYPE
    SYNTAX          SEQUENCE OF AclIpv6RuleEntry
    MAX-ACCESS      not-accessible
    STATUS          current
    DESCRIPTION
        "Configure the rule for ipv6 acl group."
    ::= { aclData 10 }

aclIpv6RuleEntry         OBJECT-TYPE
    SYNTAX          AclIpv6RuleEntry
    MAX-ACCESS      not-accessible
    STATUS          current
    DESCRIPTION
        "Define the index of aclIpv6RuleTable."
    INDEX          { aclIpv6GroupIndex, aclIpv6RuleIndex }
    ::= { aclIpv6RuleTable 1 }

    AclIpv6RuleEntry    ::=
    SEQUENCE {
            aclIpv6GroupIndex
                Integer32,
            aclIpv6RuleIndex
                Integer32,
            aclIpv6Act
                RuleAction,
            aclIpv6Protocol
                Integer32,
            aclIpv6SrcIpv6
                OCTET STRING,
            aclIpv6SrcPrefixLen
                Integer32,
            aclIpv6DestIpv6
                OCTET STRING,
            aclIpv6DestPrefixLen
                Integer32,
            aclIpv6FlowLabel
                Integer32,
            aclIpv6Dscp
                DSCPValue,
            aclIpv6Fragments
                TruthValue,
            aclIpv6Routed
                TruthValue,
            aclIpv6Options
                TruthValue,
            aclIpv6TimeRangeName
                OCTET STRING,
            aclIpv6RowStatus
                RowStatus
         }

aclIpv6GroupIndex         OBJECT-TYPE
    SYNTAX          Integer32 (40001..60000)
    MAX-ACCESS      not-accessible
    STATUS          current
    DESCRIPTION
        "The index of ipv6 acl group. Range 40001~60000."
    ::= { aclIpv6RuleEntry 1 }

aclIpv6RuleIndex         OBJECT-TYPE
    SYNTAX          Integer32 (1..131071)
    MAX-ACCESS      not-accessible
    STATUS          current
    DESCRIPTION
        "The rule index of ipv6 acl rule.Range 1~131071."
    ::= { aclIpv6RuleEntry 2 }

aclIpv6Act         OBJECT-TYPE
    SYNTAX          RuleAction
    MAX-ACCESS      read-create
    STATUS          current
    DESCRIPTION
        "The action of ipv6 acl rule.
         (1) permit.
         (2) deny."
    ::= { aclIpv6RuleEntry 3 }

aclIpv6Protocol         OBJECT-TYPE
    SYNTAX          Integer32 (0..256)
    MAX-ACCESS      read-create
    STATUS          current
    DESCRIPTION
        "The protocol-type of Ipv6 acl group.
             <0-255>  Protocol number
              Icmpv6     Internet Control Message Protocol(58)
              ospf     OSPF routing protocol(89)
              tcp      Transmission Control Protocol (6)
              udp      User Datagram Protocol (17)
              nouse    Do not use this filter(256)"
    ::= { aclIpv6RuleEntry 4 }

aclIpv6SrcIpv6         OBJECT-TYPE
    SYNTAX          OCTET STRING (SIZE (0..46))
    MAX-ACCESS      read-create
    STATUS          current
    DESCRIPTION
        "Source IPv6-address of ipv6 acl group."
    ::= { aclIpv6RuleEntry 5 }

aclIpv6SrcPrefixLen         OBJECT-TYPE
    SYNTAX          Integer32 (0..128)
    MAX-ACCESS      read-create
    STATUS          current
    DESCRIPTION
        "Source IPv6-address prefix length of ipv6 acl group.Range 0~128"
    ::= { aclIpv6RuleEntry 6 }

aclIpv6DestIpv6         OBJECT-TYPE
    SYNTAX          OCTET STRING (SIZE (0..46))
    MAX-ACCESS      read-create
    STATUS          current
    DESCRIPTION
        "Destination IPv6-address of ipv6 acl group."
    ::= { aclIpv6RuleEntry 7 }

aclIpv6DestPrefixLen         OBJECT-TYPE
    SYNTAX          Integer32 (0..128)
    MAX-ACCESS      read-create
    STATUS          current
    DESCRIPTION
        "Destination IPv6-address prefix length of ipv6 acl group.Range 0~128"
    ::= { aclIpv6RuleEntry 8 }

aclIpv6FlowLabel         OBJECT-TYPE
    SYNTAX          Integer32 (0..1048576)
    MAX-ACCESS      read-create
    STATUS          current
    DESCRIPTION
        "The value of FlowLabel.1048576 means do not use this filter.Range 0~1048576."
    ::= { aclIpv6RuleEntry 9 }

aclIpv6Dscp         OBJECT-TYPE
    SYNTAX          DSCPValue
    MAX-ACCESS      read-create
    STATUS          current
    DESCRIPTION
        "The value of DSCP.64 means do not use this filter.Range 0~64."
    ::= { aclIpv6RuleEntry 10 }

aclIpv6Fragments         OBJECT-TYPE
    SYNTAX          TruthValue
    MAX-ACCESS      read-create
    STATUS          current
    DESCRIPTION
        "The flag of matching fragmented packet. True(1),False(2)."
    ::= { aclIpv6RuleEntry 11 }

aclIpv6Routed         OBJECT-TYPE
    SYNTAX          TruthValue
    MAX-ACCESS      read-create
    STATUS          current
    DESCRIPTION
        "The flag of matching routed packet. True(1),False(2)."
    ::= { aclIpv6RuleEntry 12 }

aclIpv6Options         OBJECT-TYPE
    SYNTAX          TruthValue
    MAX-ACCESS      read-create
    STATUS          obsolete
    DESCRIPTION
        "The flag of matching packet with ipv6 option. True(1),False(2)."
    ::= { aclIpv6RuleEntry 13 }

aclIpv6TimeRangeName         OBJECT-TYPE
    SYNTAX          OCTET STRING (SIZE (0..20))
    MAX-ACCESS      read-create
    STATUS          current
    DESCRIPTION
        "The Time-range of Ipv6 acl rule.String length range 0~20."
    ::= { aclIpv6RuleEntry 14 }

aclIpv6RowStatus         OBJECT-TYPE
    SYNTAX          RowStatus
    MAX-ACCESS      read-create
    STATUS          current
    DESCRIPTION
        "The status of this conceptual row.Now only realize CreateAndGo and Destroy and Active."
    ::= { aclIpv6RuleEntry 16 }

--
-- aclTcp6RuleTable
--
aclTcp6RuleTable         OBJECT-TYPE
    SYNTAX          SEQUENCE OF AclTcp6RuleEntry
    MAX-ACCESS      not-accessible
    STATUS          current
    DESCRIPTION
        "Configure the rule for tcp6 acl group."
    ::= { aclData 11 }

aclTcp6RuleEntry         OBJECT-TYPE
    SYNTAX          AclTcp6RuleEntry
    MAX-ACCESS      not-accessible
    STATUS          current
    DESCRIPTION
        "Define the index of aclTcp6RuleTable."
    INDEX         { aclTcp6GroupIndex, aclTcp6RuleIndex }
    ::= { aclTcp6RuleTable 1 }

    AclTcp6RuleEntry    ::=
    SEQUENCE {
            aclTcp6GroupIndex
                Integer32,
            aclTcp6RuleIndex
                Integer32,
            aclTcp6Act
                RuleAction,
            aclTcp6SrcIpv6
                OCTET STRING,
            aclTcp6SrcPrefixLen
                Integer32,
            aclTcp6DestIpv6
                OCTET STRING,
            aclTcp6DestPrefixLen
                Integer32,
            aclTcp6FlowLabel
                Integer32,
            aclTcp6Dscp
                DSCPValue,
            aclTcp6Fragments
                TruthValue,
            aclTcp6Routed
                TruthValue,
            aclTcp6Options
                TruthValue,
            aclTcp6SrcOp
                PortOp,
            aclTcp6SrcPort1
                Integer32,
            aclTcp6SrcPort2
                Integer32,
            aclTcp6DestOp
                PortOp,
            aclTcp6DestPort1
                Integer32,
            aclTcp6DestPort2
                Integer32,
            aclTcp6FlagOp
                INTEGER,
            aclTcp6FlagUrg
                TruthValue,
            aclTcp6FlagAck
                TruthValue,
            aclTcp6FlagPsh
                TruthValue,
            aclTcp6FlagRst
                TruthValue,
            aclTcp6FlagSyn
                TruthValue,
            aclTcp6FlagFin
                TruthValue,
            aclTcp6TimeRangeName
                OCTET STRING,
            aclTcp6RowStatus
                RowStatus
         }

aclTcp6GroupIndex         OBJECT-TYPE
    SYNTAX          Integer32 (40001..60000)
    MAX-ACCESS      not-accessible
    STATUS          current
    DESCRIPTION
        "The index of tcp6 acl group. Range 40001~60000."
    ::= { aclTcp6RuleEntry 1 }

aclTcp6RuleIndex         OBJECT-TYPE
    SYNTAX          Integer32 (1..131071)
    MAX-ACCESS      not-accessible
    STATUS          current
    DESCRIPTION
        "The rule index of tcp6 acl group. Range 1~131071."
    ::= { aclTcp6RuleEntry 2 }

aclTcp6Act         OBJECT-TYPE
    SYNTAX          RuleAction
    MAX-ACCESS      read-create
    STATUS          current
    DESCRIPTION
        "The action of tcp6 acl rule.
         (1) permit.
         (2) deny."
    ::= { aclTcp6RuleEntry 3 }

aclTcp6SrcIpv6         OBJECT-TYPE
    SYNTAX          OCTET STRING (SIZE (0..46))
    MAX-ACCESS      read-create
    STATUS          current
    DESCRIPTION
        "Source IPv6-address of tcp6 acl group."
    ::= { aclTcp6RuleEntry 4 }

aclTcp6SrcPrefixLen         OBJECT-TYPE
    SYNTAX          Integer32 (0..128)
    MAX-ACCESS      read-create
    STATUS          current
    DESCRIPTION
        "Source IPv6-address prefix length of tcp6 acl group.Range 0~128"
    ::= { aclTcp6RuleEntry 5 }

aclTcp6DestIpv6         OBJECT-TYPE
    SYNTAX          OCTET STRING (SIZE (0..46))
    MAX-ACCESS      read-create
    STATUS          current
    DESCRIPTION
        "Destination IPv6-address of tcp6 acl group."
    ::= { aclTcp6RuleEntry 6 }

aclTcp6DestPrefixLen         OBJECT-TYPE
    SYNTAX          Integer32 (0..128)
    MAX-ACCESS      read-create
    STATUS          current
    DESCRIPTION
        "Destination IPv6-address prefix length of tcp6 acl group.Range 0~128"
    ::= { aclTcp6RuleEntry 7 }

aclTcp6FlowLabel         OBJECT-TYPE
    SYNTAX          Integer32 (0..1048576)
    MAX-ACCESS      read-create
    STATUS          current
    DESCRIPTION
        "The value of FlowLabel.1048576 means do not use this filter.Range 0~1048576."
    ::= { aclTcp6RuleEntry 8 }

aclTcp6Dscp         OBJECT-TYPE
    SYNTAX          DSCPValue
    MAX-ACCESS      read-create
    STATUS          current
    DESCRIPTION
        "The value of DSCP.64 means do not use this filter.Range 0~64."
    ::= { aclTcp6RuleEntry 9 }

aclTcp6Fragments         OBJECT-TYPE
    SYNTAX          TruthValue
    MAX-ACCESS      read-create
    STATUS          current
    DESCRIPTION
        "The flag of matching fragmented packet. True(1),False(2).
         This node can not be setted true for aclTcp6SrcOp or aclTcp6DestOp is setted."
    ::= { aclTcp6RuleEntry 10 }

aclTcp6Routed         OBJECT-TYPE
    SYNTAX          TruthValue
    MAX-ACCESS      read-create
    STATUS          current
    DESCRIPTION
        "The flag of matching routed packet. True(1),False(2)."
    ::= { aclTcp6RuleEntry 11 }

aclTcp6Options         OBJECT-TYPE
    SYNTAX          TruthValue
    MAX-ACCESS      read-create
    STATUS          obsolete
    DESCRIPTION
        "The flag of matching packet with ipv6 option. True(1),False(2)."
    ::= { aclTcp6RuleEntry 12 }

aclTcp6SrcOp         OBJECT-TYPE
    SYNTAX          PortOp
    MAX-ACCESS      read-create
    STATUS          current
    DESCRIPTION
        "The source port's operator of tcp6 acl group.
            This node can not be setted if aclTcp6Fragments is true.
            eq(0),
            gt(2),
            lt(3),
            range(4),
            invalid(5)"
    ::= { aclTcp6RuleEntry 13 }

aclTcp6SrcPort1    OBJECT-TYPE
    SYNTAX          Integer32 (0..65535)
    MAX-ACCESS      read-create
    STATUS          current
    DESCRIPTION
        "The fourth layer source port1. Range 0~65535. "
    ::= { aclTcp6RuleEntry 14 }

aclTcp6SrcPort2    OBJECT-TYPE
    SYNTAX          Integer32 (0..65535)
    MAX-ACCESS      read-create
    STATUS          current
    DESCRIPTION
        "The fourth layer source port2. Range 0~65535."
    ::= { aclTcp6RuleEntry 15 }

aclTcp6DestOp         OBJECT-TYPE
    SYNTAX          PortOp
    MAX-ACCESS      read-write
    STATUS          current
    DESCRIPTION
        "The destination port's operator of tcp6 acl group.
         This node can not be setted if aclTcp6Fragments is true.
            eq(0),
            gt(2),
            lt(3),
            range(4),
            invalid(5)"
    ::= { aclTcp6RuleEntry 16 }

aclTcp6DestPort1    OBJECT-TYPE
    SYNTAX          Integer32 (0..65535)
    MAX-ACCESS      read-create
    STATUS          current
    DESCRIPTION
        "The fourth layer destination port1. Range 0~65535."
    ::= { aclTcp6RuleEntry 17 }

aclTcp6DestPort2    OBJECT-TYPE
    SYNTAX          Integer32 (0..65535)
    MAX-ACCESS      read-create
    STATUS          current
    DESCRIPTION
        "The fourth layer destination port2. Range 0~65535."
    ::= { aclTcp6RuleEntry 18 }

aclTcp6FlagOp         OBJECT-TYPE
    SYNTAX          INTEGER
        {
            matchAny(0),
            matchAll(1),
            invalid(2)
        }
    MAX-ACCESS      read-create
    STATUS          current
    DESCRIPTION
        "The tcp-flags' operator of tcp6 acl group.
        for example, established tcp packet with ack or rst flag setted,
        set this node matchAny(0) and set aclTcp6FlagAck and aclTcp6FlagRst
        can filter established tcp packet.
            matchAny(0),
            matchAll(1),
            invalid(2)."
    ::= { aclTcp6RuleEntry 19 }

aclTcp6FlagUrg         OBJECT-TYPE
    SYNTAX          TruthValue
    MAX-ACCESS      read-create
    STATUS          current
    DESCRIPTION
        "The tcp-urg flag of tcp6 acl group. True(1),False(2).
            TCP protocol URG Packet."
    ::= { aclTcp6RuleEntry 20 }

aclTcp6FlagAck         OBJECT-TYPE
    SYNTAX          TruthValue
    MAX-ACCESS      read-create
    STATUS          current
    DESCRIPTION
        "The tcp-ack flag of tcp6 acl group.
            TCP protocol ACK Packet. True(1),False(2)."
    ::= { aclTcp6RuleEntry 21 }

aclTcp6FlagPsh         OBJECT-TYPE
    SYNTAX          TruthValue
    MAX-ACCESS      read-create
    STATUS          current
    DESCRIPTION
        "The tcp-psh flag of tcp6 acl group. True(1),False(2).
            TCP protocol PSH Packet."
    ::= { aclTcp6RuleEntry 22 }

aclTcp6FlagRst         OBJECT-TYPE
    SYNTAX          TruthValue
    MAX-ACCESS      read-create
    STATUS          current
    DESCRIPTION
        "The tcp-rst flag of tcp6 acl group. True(1),False(2).
            TCP protocol RST Packet."
    ::= { aclTcp6RuleEntry 23 }

aclTcp6FlagSyn         OBJECT-TYPE
    SYNTAX          TruthValue
    MAX-ACCESS      read-create
    STATUS          current
    DESCRIPTION
        "The tcp-syn flag of tcp6 acl group. True(1),False(2).
            TCP protocol SYN Packet."
    ::= { aclTcp6RuleEntry 24 }

aclTcp6FlagFin         OBJECT-TYPE
    SYNTAX          TruthValue
    MAX-ACCESS      read-create
    STATUS          current
    DESCRIPTION
        "The tcp-fin flag of tcp6 acl group. True(1),False(2).
            TCP protocol FIN Packet."
    ::= { aclTcp6RuleEntry 25 }

aclTcp6TimeRangeName         OBJECT-TYPE
    SYNTAX          OCTET STRING (SIZE (0..20))
    MAX-ACCESS      read-create
    STATUS          current
    DESCRIPTION
        "The Time-range of tcp6 acl rule."
    ::= { aclTcp6RuleEntry 26 }

aclTcp6RowStatus         OBJECT-TYPE
    SYNTAX          RowStatus
    MAX-ACCESS      read-create
    STATUS          current
    DESCRIPTION
        "The status of this conceptual row.Now only realize CreateAndGo and Destroy and Active."
    ::= { aclTcp6RuleEntry 28 }

--
-- aclUdp6RuleTable
--
aclUdp6RuleTable         OBJECT-TYPE
    SYNTAX          SEQUENCE OF AclUdp6RuleEntry
    MAX-ACCESS      not-accessible
    STATUS          current
    DESCRIPTION
        "Configure the rule for udp6 acl group."
    ::= { aclData 12 }

aclUdp6RuleEntry         OBJECT-TYPE
    SYNTAX          AclUdp6RuleEntry
    MAX-ACCESS      not-accessible
    STATUS          current
    DESCRIPTION
        "Define the index of aclUdp6RuleTable."
    INDEX         { aclUdp6GroupIndex, aclUdp6RuleIndex }
    ::= { aclUdp6RuleTable 1 }

    AclUdp6RuleEntry    ::=
    SEQUENCE {
            aclUdp6GroupIndex
                Integer32,
            aclUdp6RuleIndex
                Integer32,
            aclUdp6Act
                RuleAction,
            aclUdp6SrcIpv6
                OCTET STRING,
            aclUdp6SrcPrefixLen
                Integer32,
            aclUdp6DestIpv6
                OCTET STRING,
            aclUdp6DestPrefixLen
                Integer32,
            aclUdp6FlowLabel
                Integer32,
            aclUdp6Dscp
                DSCPValue,
            aclUdp6Fragments
                TruthValue,
            aclUdp6Routed
                TruthValue,
            aclUdp6Options
                TruthValue,
            aclUdp6SrcOp
                PortOp,
            aclUdp6SrcPort1
                Integer32,
            aclUdp6SrcPort2
                Integer32,
            aclUdp6DestOp
                PortOp,
            aclUdp6DestPort1
                Integer32,
            aclUdp6DestPort2
                Integer32,
            aclUdp6TimeRangeName
                OCTET STRING,
            aclUdp6RowStatus
                RowStatus
         }

aclUdp6GroupIndex         OBJECT-TYPE
    SYNTAX          Integer32 (40001..60000)
    MAX-ACCESS      not-accessible
    STATUS          current
    DESCRIPTION
        "The index of udp6 acl group. Range 40001~60000."
    ::= { aclUdp6RuleEntry 1 }

aclUdp6RuleIndex         OBJECT-TYPE
    SYNTAX          Integer32 (1..131071)
    MAX-ACCESS      not-accessible
    STATUS          current
    DESCRIPTION
        "The rule index of udp6 acl group. Range 1~131071."
    ::= { aclUdp6RuleEntry 2 }

aclUdp6Act         OBJECT-TYPE
    SYNTAX          RuleAction
    MAX-ACCESS      read-create
    STATUS          current
    DESCRIPTION
        "The action of udp6 acl rule.
         (1) permit.
         (2) deny"
    ::= { aclUdp6RuleEntry 3 }

aclUdp6SrcIpv6         OBJECT-TYPE
    SYNTAX          OCTET STRING (SIZE (0..46))
    MAX-ACCESS      read-create
    STATUS          current
    DESCRIPTION
        "Source IPv6-address of udp6 acl group."
    ::= { aclUdp6RuleEntry 4 }

aclUdp6SrcPrefixLen         OBJECT-TYPE
    SYNTAX          Integer32 (0..128)
    MAX-ACCESS      read-create
    STATUS          current
    DESCRIPTION
        "Source IPv6-address prefix length of udp6 acl group.Range 0~128"
    ::= { aclUdp6RuleEntry 5 }

aclUdp6DestIpv6         OBJECT-TYPE
    SYNTAX          OCTET STRING (SIZE (0..46))
    MAX-ACCESS      read-create
    STATUS          current
    DESCRIPTION
        "Destination IPv6-address of udp6 acl group."
    ::= { aclUdp6RuleEntry 6 }

aclUdp6DestPrefixLen         OBJECT-TYPE
    SYNTAX          Integer32 (0..128)
    MAX-ACCESS      read-create
    STATUS          current
    DESCRIPTION
        "Destination IPv6-address prefix length of udp6 acl group.Range 0~128"
    ::= { aclUdp6RuleEntry 7 }

aclUdp6FlowLabel         OBJECT-TYPE
    SYNTAX          Integer32 (0..1048576)
    MAX-ACCESS      read-create
    STATUS          current
    DESCRIPTION
        "The value of FlowLabel.1048576 means do not use this filter.Range 0~1048576."
    ::= { aclUdp6RuleEntry 8 }

aclUdp6Dscp         OBJECT-TYPE
    SYNTAX          DSCPValue
    MAX-ACCESS      read-create
    STATUS          current
    DESCRIPTION
        "The value of DSCP.64 means do not use this filter.Range 0~64."
    ::= { aclUdp6RuleEntry 9 }

aclUdp6Fragments         OBJECT-TYPE
    SYNTAX          TruthValue
    MAX-ACCESS      read-create
    STATUS          current
    DESCRIPTION
        "The flag of matching fragmented packet. True(1),False(2).
         This node can not be setted true for aclUdp6SrcOp or aclUdp6DestOp is setted."
    ::= { aclUdp6RuleEntry 10 }

aclUdp6Routed         OBJECT-TYPE
    SYNTAX          TruthValue
    MAX-ACCESS      read-create
    STATUS          current
    DESCRIPTION
        "The flag of matching routed packet. True(1),False(2)."
    ::= { aclUdp6RuleEntry 11 }

aclUdp6Options         OBJECT-TYPE
    SYNTAX          TruthValue
    MAX-ACCESS      read-create
    STATUS          obsolete
    DESCRIPTION
        "The flag of matching packet with ipv6 option. True(1),False(2)."
    ::= { aclUdp6RuleEntry 12 }

aclUdp6SrcOp         OBJECT-TYPE
    SYNTAX          PortOp
    MAX-ACCESS      read-create
    STATUS          current
    DESCRIPTION
        "The source port's operator of udp6 acl group.
            This node can not be setted if aclUdp6Fragments is true.
            eq(0),
            gt(2),
            lt(3),
            range(4),
            invalid(5)"
    ::= { aclUdp6RuleEntry 13 }

aclUdp6SrcPort1    OBJECT-TYPE
    SYNTAX          Integer32 (0..65535)
    MAX-ACCESS      read-create
    STATUS          current
    DESCRIPTION
        "The fourth layer source port1. Range 0~65535."
    ::= { aclUdp6RuleEntry 14 }

aclUdp6SrcPort2    OBJECT-TYPE
    SYNTAX          Integer32 (0..65535)
    MAX-ACCESS      read-create
    STATUS          current
    DESCRIPTION
        "The fourth layer source port2. Range 0~65535."
    ::= { aclUdp6RuleEntry 15 }

aclUdp6DestOp         OBJECT-TYPE
    SYNTAX          PortOp
    MAX-ACCESS      read-create
    STATUS          current
    DESCRIPTION
        "The destination port's operator of udp6 acl group.
         This node can not be setted if aclUdp6Fragments is true.
            eq(0),
            gt(2),
            lt(3),
            range(4),
            invalid(5)"
    ::= { aclUdp6RuleEntry 16 }

aclUdp6DestPort1    OBJECT-TYPE
    SYNTAX          Integer32 (0..65535)
    MAX-ACCESS      read-create
    STATUS          current
    DESCRIPTION
        "The fourth layer destination port1. Range 0~65535."
    ::= { aclUdp6RuleEntry 17 }

aclUdp6DestPort2    OBJECT-TYPE
    SYNTAX          Integer32 (0..65535)
    MAX-ACCESS      read-create
    STATUS          current
    DESCRIPTION
        "The fourth layer destination port2. Range 0~65535."
    ::= { aclUdp6RuleEntry 18 }

aclUdp6TimeRangeName         OBJECT-TYPE
    SYNTAX          OCTET STRING (SIZE (0..20))
    MAX-ACCESS      read-create
    STATUS          current
    DESCRIPTION
        "The Time-range of udp6 acl rule. Range 0~20."
    ::= { aclUdp6RuleEntry 19 }

aclUdp6RowStatus         OBJECT-TYPE
    SYNTAX          RowStatus
    MAX-ACCESS      read-create
    STATUS          current
    DESCRIPTION
        "The status of this conceptual row.Now only realize CreateAndGo and Destroy and Active."
    ::= { aclUdp6RuleEntry 21 }

--
-- aclIcmp6RuleTable
--
aclIcmp6RuleTable         OBJECT-TYPE
    SYNTAX          SEQUENCE OF AclIcmp6RuleEntry
    MAX-ACCESS      not-accessible
    STATUS          current
    DESCRIPTION
        "Configure the rule for icmp6 acl group."
    ::= { aclData 13 }

aclIcmp6RuleEntry         OBJECT-TYPE
    SYNTAX          AclIcmp6RuleEntry
    MAX-ACCESS      not-accessible
    STATUS          current
    DESCRIPTION
        "Define the index of aclIcmp6RuleTable."
     INDEX        { aclIcmp6GroupIndex, aclIcmp6RuleIndex }
    ::= { aclIcmp6RuleTable 1 }

    AclIcmp6RuleEntry    ::=
    SEQUENCE {
            aclIcmp6GroupIndex
                Integer32,
            aclIcmp6RuleIndex
                Integer32,
            aclIcmp6Act
                RuleAction,
            aclIcmp6SrcIpv6
                OCTET STRING,
            aclIcmp6SrcPrefixLen
                Integer32,
            aclIcmp6DestIpv6
                OCTET STRING,
            aclIcmp6DestPrefixLen
                Integer32,
            aclIcmp6FlowLabel
                Integer32,
            aclIcmp6Dscp
                DSCPValue,
            aclIcmp6Fragments
                TruthValue,
            aclIcmp6Routed
                TruthValue,
            aclIcmp6Options
                TruthValue,
            aclIcmp6Type
                Integer32,
            aclIcmp6Code
                Integer32,
            aclIcmp6TimeRangeName
                OCTET STRING,
            aclIcmp6RowStatus
                RowStatus
         }

aclIcmp6GroupIndex         OBJECT-TYPE
    SYNTAX          Integer32 (40001..60000)
    MAX-ACCESS      not-accessible
    STATUS          current
    DESCRIPTION
        "The index of icmp6 acl group. Range 40001~60000."
    ::= { aclIcmp6RuleEntry 1 }

aclIcmp6RuleIndex         OBJECT-TYPE
    SYNTAX          Integer32 (1..131071)
    MAX-ACCESS      not-accessible
    STATUS          current
    DESCRIPTION
        "The rule index of icmp6 acl group. Range 1~131071."
    ::= { aclIcmp6RuleEntry 2 }

aclIcmp6Act         OBJECT-TYPE
    SYNTAX          RuleAction
    MAX-ACCESS      read-create
    STATUS          current
    DESCRIPTION
        "The action of icmp6 acl rule.
         (1) permit.
         (2) deny"
    ::= { aclIcmp6RuleEntry 3 }

aclIcmp6SrcIpv6         OBJECT-TYPE
    SYNTAX          OCTET STRING (SIZE (0..46))
    MAX-ACCESS      read-write
    STATUS          current
    DESCRIPTION
        "Source IPv6-address of icmp6 acl group."
    ::= { aclIcmp6RuleEntry 4 }

aclIcmp6SrcPrefixLen         OBJECT-TYPE
    SYNTAX          Integer32 (0..128)
    MAX-ACCESS      read-create
    STATUS          current
    DESCRIPTION
        "Source IPv6-address prefix length of icmp6 acl group.Range 0~128"
    ::= { aclIcmp6RuleEntry 5 }

aclIcmp6DestIpv6         OBJECT-TYPE
    SYNTAX          OCTET STRING (SIZE (0..46))
    MAX-ACCESS      read-create
    STATUS          current
    DESCRIPTION
        "Destination IPv6-address of icmp6 acl group."
    ::= { aclIcmp6RuleEntry 6 }

aclIcmp6DestPrefixLen         OBJECT-TYPE
    SYNTAX          Integer32 (0..128)
    MAX-ACCESS      read-create
    STATUS          current
    DESCRIPTION
        "Destination IPv6-address prefix length of icmp6 acl group.Range 0~128"
    ::= { aclIcmp6RuleEntry 7 }

aclIcmp6FlowLabel         OBJECT-TYPE
    SYNTAX          Integer32 (0..1048576)
    MAX-ACCESS      read-create
    STATUS          current
    DESCRIPTION
        "The value of FlowLabel.1048576 means do not use this filter.Range 0~1048576."
    ::= { aclIcmp6RuleEntry 8 }

aclIcmp6Dscp         OBJECT-TYPE
    SYNTAX          DSCPValue
    MAX-ACCESS      read-create
    STATUS          current
    DESCRIPTION
        "The value of DSCP.64 means do not use this filter.Range 0~64."
    ::= { aclIcmp6RuleEntry 9 }

aclIcmp6Fragments         OBJECT-TYPE
    SYNTAX          TruthValue
    MAX-ACCESS      read-create
    STATUS          current
    DESCRIPTION
        "The flag of matching fragmented packet.
            This node can not be setted true if aclIcmp6Type is setted. True(1),False(2)."
    ::= { aclIcmp6RuleEntry 10 }

aclIcmp6Routed         OBJECT-TYPE
    SYNTAX          TruthValue
    MAX-ACCESS      read-create
    STATUS          current
    DESCRIPTION
        "The flag of matching routed packet. True(1),False(2)."
    ::= { aclIcmp6RuleEntry 11 }

aclIcmp6Options         OBJECT-TYPE
    SYNTAX          TruthValue
    MAX-ACCESS      read-create
    STATUS          obsolete
    DESCRIPTION
        "The flag of matching packet with ipv6 option. True(1),False(2)."
    ::= { aclIcmp6RuleEntry 12 }

aclIcmp6Type         OBJECT-TYPE
    SYNTAX          Integer32 (0..256)
    MAX-ACCESS      read-create
    STATUS          current
    DESCRIPTION
        "The type of ICMPv6 packet.Range 0~256.
            This node can not be setted if aclIcmp6Fragments is true."
    ::= { aclIcmp6RuleEntry 13 }

aclIcmp6Code         OBJECT-TYPE
    SYNTAX          Integer32 (0..256)
    MAX-ACCESS      read-create
    STATUS          current
    DESCRIPTION
        "The code of ICMPv6 packet.Range 0~256.
            This node can not be setted if aclIcmp6Type is not setted."
    ::= { aclIcmp6RuleEntry 14 }

aclIcmp6TimeRangeName         OBJECT-TYPE
    SYNTAX          OCTET STRING (SIZE (0..20))
    MAX-ACCESS      read-create
    STATUS          current
    DESCRIPTION
        "The Time-range of icmp6 acl rule. Range 0~20."
    ::= { aclIcmp6RuleEntry 15 }

aclIcmp6RowStatus         OBJECT-TYPE
    SYNTAX          RowStatus
    MAX-ACCESS      read-create
    STATUS          current
    DESCRIPTION
        "The status of this conceptual row.Now only realize CreateAndGo and Destroy and Active."
    ::= { aclIcmp6RuleEntry 17 }



globalQos        OBJECT IDENTIFIER ::= { qos 1 }
ifQos            OBJECT IDENTIFIER ::= { qos 2 }
cbQoS            OBJECT IDENTIFIER ::= { qos 3 }
srvQos           OBJECT IDENTIFIER ::= { qos 4 }
stats            OBJECT IDENTIFIER ::= { qos 10 }

--
--type definitions
--

--ColorType
    ColorType ::= TEXTUAL-CONVENTION
        STATUS current
        DESCRIPTION
            "Color of the flow. "
        SYNTAX INTEGER
        {
            none(0),
            red(1),
            yellow(2),
            green(3)
        }

--PriMapType
    PriMapType ::= TEXTUAL-CONVENTION
        STATUS current
        DESCRIPTION
            "Type of map."
        SYNTAX INTEGER
        {                            
            cos(1), 
            dscp(2),
            exp(3),
            ipPre(4) 
        }

--IfQueueId
   IfQueueId ::= TEXTUAL-CONVENTION
       STATUS current
       DESCRIPTION
           "Queue Id"
       SYNTAX Integer32 (0..7)




--
--end of type definitions
--

--
-- Node definitions
--

-- ifQosShapeObjects

    ifQosShapeObjects OBJECT IDENTIFIER ::= { ifQos 1 }

-- ifQosShapeIfCfgTable
--
    ifQosShapeIfCfgTable OBJECT-TYPE
        SYNTAX SEQUENCE OF IfQosShapeIfCfgEntry
        MAX-ACCESS not-accessible
        STATUS current
        DESCRIPTION
            "A table of interface shape."
        ::= { ifQosShapeObjects 1 }

    ifQosShapeIfCfgEntry OBJECT-TYPE
        SYNTAX IfQosShapeIfCfgEntry
        MAX-ACCESS not-accessible
        STATUS current
        DESCRIPTION
            "Entry of interface shape talbe."
        INDEX { ifIndex }
        ::= { ifQosShapeIfCfgTable 1 }

    IfQosShapeIfCfgEntry ::=
        SEQUENCE
        {
            ifQosShapeIfCfgType
                INTEGER,
            ifQosShapeIfCfgPercent
                Integer32,                 
            ifQosShapeIfCfgRate
                Integer32,
            ifQosShapeIfCfgRowStatus
                RowStatus
        }

    ifQosShapeIfCfgType OBJECT-TYPE
        SYNTAX INTEGER {percent(1), rate(2)}
        MAX-ACCESS read-create
        STATUS current
        DESCRIPTION
            "Port shape mode type. 
             1 means port shape is based on percent of interface max bandwidth.
             2 means port shape is based on the configured rate."
        ::= { ifQosShapeIfCfgEntry 1 }          

    ifQosShapeIfCfgPercent OBJECT-TYPE
        SYNTAX Integer32 (0..99)
        MAX-ACCESS read-create
        STATUS current
        DESCRIPTION
            "Percent value of interface max bandwidth. Range is <0-99>."
        ::= { ifQosShapeIfCfgEntry 2 }          

    ifQosShapeIfCfgRate OBJECT-TYPE
        SYNTAX Integer32 (0..10000000)
        MAX-ACCESS read-create
        STATUS current
        DESCRIPTION
            "Rate of interface max value. Range <0-10000000>kbps."
        ::= { ifQosShapeIfCfgEntry 3 }          
        
    ifQosShapeIfCfgRowStatus         OBJECT-TYPE
        SYNTAX          RowStatus
        MAX-ACCESS      read-create
        STATUS          current
        DESCRIPTION
            "The status of this conceptual row.Now only realize CreateAndGo and Destroy and Active.
        1 means Active
        4 means CreateAndGo
        6 means Destroy"
        ::= { ifQosShapeIfCfgEntry 4 }   

-- ifQosShapeQueueCfgTable
--
    ifQosShapeQueueCfgTable OBJECT-TYPE
        SYNTAX SEQUENCE OF IfQosShapeQueueCfgEntry
        MAX-ACCESS not-accessible
        STATUS current
        DESCRIPTION
            "A table of interface queue shape."
        ::= { ifQosShapeObjects 2 }

    ifQosShapeQueueCfgEntry OBJECT-TYPE
        SYNTAX IfQosShapeQueueCfgEntry
        MAX-ACCESS not-accessible
        STATUS current
        DESCRIPTION
            "Entry of interface queue shape table."
        INDEX { ifIndex,
                ifQosShapeQueueCfgQueueId}
        ::= { ifQosShapeQueueCfgTable 1 }

    IfQosShapeQueueCfgEntry ::=
        SEQUENCE
        {
            ifQosShapeQueueCfgQueueId
                IfQueueId,
            ifQosShapeQueueCfgType
                INTEGER,
            ifQosShapeQueueCfgPercent
                Integer32,
            ifQosShapeQueueCfgPercentPeak
                Integer32,
            ifQosShapeQueueCfgRate
                Integer32,
            ifQosShapeQueueCfgRatePeak
                Integer32,
            ifQosShapeQueueCfgRowStatus
                RowStatus
        }

    ifQosShapeQueueCfgQueueId OBJECT-TYPE
        SYNTAX IfQueueId
        MAX-ACCESS not-accessible
        STATUS current
        DESCRIPTION
            "Queue Id of the interface. Range <0-7>"
        ::= { ifQosShapeQueueCfgEntry 1 }

    ifQosShapeQueueCfgType OBJECT-TYPE
        SYNTAX INTEGER {percent(1), rate(2)}
        MAX-ACCESS read-create
        STATUS current
        DESCRIPTION
            "Port shape mode type. 
             1 means queue shape is based on percent of interface max bandwidth.
             2 means queue shape is based on the configured rate.
             If no shape is configured, zero will be got."
        ::= { ifQosShapeQueueCfgEntry 2 }      

    ifQosShapeQueueCfgPercent OBJECT-TYPE
        SYNTAX Integer32 (0..100)
        MAX-ACCESS read-create
        STATUS current
        DESCRIPTION
            "Percent value of interface max bandwidth. Range is <0-100>.
             This value influences the commit information rate.
             This value should not be larger than ifQosShapeQueueCfgPercentPeak.
             If the queue shape is rate mode, this value is 0."
        ::= { ifQosShapeQueueCfgEntry 3 }      

    ifQosShapeQueueCfgPercentPeak OBJECT-TYPE
        SYNTAX Integer32 (0..100)
        MAX-ACCESS read-create
        STATUS current
        DESCRIPTION
            "Percent value of interface max bandwidth. Range is <0-100>.
             This value influences the peak information rate.
             This value should not be smaller than ifQosShapeQueueCfgPercent.
             If the queue shape is rate mode, this value is 0."
        ::= { ifQosShapeQueueCfgEntry 4 }      

    ifQosShapeQueueCfgRate OBJECT-TYPE
        SYNTAX Integer32 (0..10000000)
        MAX-ACCESS read-create
        STATUS current
        DESCRIPTION
            "Commit information rate of interface queue shaping. Range <0-10000000>kbps.
             This value should not be larger than ifQosShapeQueueCfgRatePeak.
             If the queue shape is percent mode, this value is 0."
        ::= { ifQosShapeQueueCfgEntry 5 }

    ifQosShapeQueueCfgRatePeak OBJECT-TYPE
        SYNTAX Integer32 (0..10000000)
        MAX-ACCESS read-create
        STATUS current
        DESCRIPTION
            "Peak information rate of interface queue shaping. Range <0-10000000>kbps.
             This value should not be smaller than ifQosShapeQueueCfgRate.
             If the queue shape is percent mode, this value is 0."
        ::= { ifQosShapeQueueCfgEntry 6 }

    ifQosShapeQueueCfgRowStatus         OBJECT-TYPE
        SYNTAX          RowStatus
        MAX-ACCESS      read-create
        STATUS          current
        DESCRIPTION
            "The status of this conceptual row.Now only realize CreateAndGo and Destroy and Active.
        1 means Active
        4 means CreateAndGo
        6 means Destroy"
        ::= { ifQosShapeQueueCfgEntry 7 }   

-- ifQosQueueObjects

    ifQosQueueObjects OBJECT IDENTIFIER ::= { ifQos 2 }

-- ifQosQueueClassDrrWeightTable
--
ifQosQueueClassDrrWeightTable         OBJECT-TYPE
    SYNTAX          SEQUENCE OF IfQosQueueClassDrrWeightEntry
    MAX-ACCESS      not-accessible
    STATUS          current
    DESCRIPTION
        "A table of interface queue class and Drr Weight ."
    ::= { ifQosQueueObjects 1 }

ifQosQueueClassDrrWeightEntry         OBJECT-TYPE
    SYNTAX          IfQosQueueClassDrrWeightEntry
    MAX-ACCESS      not-accessible
    STATUS          current
    DESCRIPTION
        "Interface queue class and Drr Weight entry."
    INDEX     { ifIndex ,ifQosQueueClassDrrWeightQueueId}
    ::= { ifQosQueueClassDrrWeightTable 1 }

IfQosQueueClassDrrWeightEntry    ::=
    SEQUENCE
        {
        ifQosQueueClassDrrWeightQueueId
            IfQueueId,
        ifQosQueueClass
            Integer32,
        ifQosQueueDrrWeight
            Integer32
        }

    ifQosQueueClassDrrWeightQueueId         OBJECT-TYPE
        SYNTAX          IfQueueId
        MAX-ACCESS      not-accessible
        STATUS          current
        DESCRIPTION
        "Queue Id.Range is <0-7>."
        ::= { ifQosQueueClassDrrWeightEntry 1 }
        
    ifQosQueueClass         OBJECT-TYPE
        SYNTAX          Integer32 (-1|0..6)
        MAX-ACCESS      read-write
        STATUS          current
        DESCRIPTION
        "<0-6>:Class Id of the selected queue.
         Set -1 to return it to default value."
        ::= { ifQosQueueClassDrrWeightEntry 2 }                          

    ifQosQueueDrrWeight         OBJECT-TYPE
        SYNTAX          Integer32 (-1|1..100)
        MAX-ACCESS read-write
        STATUS current
        DESCRIPTION
            "DRR weight of selected queue. 
            <1-100>: DRR weight range.
             Set -1 to return it to default value."
        ::= { ifQosQueueClassDrrWeightEntry 3 }  
                    

-- ifQosQueueManageCfgTable
--
    ifQosQueueManageCfgTable OBJECT-TYPE
        SYNTAX SEQUENCE OF IfQosQueueManageCfgEntry
        MAX-ACCESS not-accessible
        STATUS current
        DESCRIPTION
            "A table of interface queue management."
        ::= { ifQosQueueObjects 3 }

    ifQosQueueManageCfgEntry OBJECT-TYPE
        SYNTAX IfQosQueueManageCfgEntry
        MAX-ACCESS not-accessible
        STATUS current
        DESCRIPTION
            "Entry of ifQosQueueManageCfgTable."
        INDEX { ifIndex,
                ifQosQueueManageQueueId }
        ::= { ifQosQueueManageCfgTable 1 }

    IfQosQueueManageCfgEntry ::=
        SEQUENCE
        {
            ifQosQueueManageQueueId
                IfQueueId,
            ifQosQueueManageDropType
                Integer32,
            ifQosQueueManageThresholdPrecedence0
                Integer32,
            ifQosQueueManageThresholdPrecedence1
                Integer32,
            ifQosQueueManageThresholdPrecedence2
                Integer32,
            ifQosQueueManageMinThresholdPre0
                Integer32,
            ifQosQueueManageMinThresholdPre1
                Integer32,
            ifQosQueueManageMinThresholdPre2
                Integer32, 
            ifQosQueueManageMaxThresholdPre0
                Integer32,
            ifQosQueueManageMaxThresholdPre1
                Integer32,
            ifQosQueueManageMaxThresholdPre2
                Integer32,
            ifQosQueueManageDropProbabilityPre0
                Integer32,
            ifQosQueueManageDropProbabilityPre1
                Integer32,
            ifQosQueueManageDropProbabilityPre2
                Integer32
        }        

ifQosQueueManageQueueId         OBJECT-TYPE
    SYNTAX          IfQueueId
    MAX-ACCESS      not-accessible
    STATUS          current
    DESCRIPTION
        "Queue Id.Range is <0-7>"
    ::= { ifQosQueueManageCfgEntry 1 }

ifQosQueueManageDropType         OBJECT-TYPE
    SYNTAX          Integer32(-1..0)
    MAX-ACCESS      read-write
    STATUS          current
    DESCRIPTION
        "Queue management mode.
         (-1) taildrop.
         (0-10) the value of EWMA factor,default EWMA factor is 9.
         If this value is (0-10), the drop type is weighted random early drop(wred) mode."
    ::= { ifQosQueueManageCfgEntry 2 }

ifQosQueueManageThresholdPrecedence0    OBJECT-TYPE
    SYNTAX          Integer32 (-1..12884)
    MAX-ACCESS      read-write
    STATUS          current
    DESCRIPTION
        "Drop threshold for precedence0, only for taildrop mode.
             0 is returned for other mode.Range is <0-12884>.
             The set of this value will be ignored for non-taildrop mode.
             Set -1 to delete current configuration and retrieve default configuration.
        For 1G port, default value is 224;
        For 10G port, default value is 576"
    ::= { ifQosQueueManageCfgEntry 3 }

ifQosQueueManageThresholdPrecedence1    OBJECT-TYPE
    SYNTAX          Integer32 (-1|1..12885)
    MAX-ACCESS      read-write
    STATUS          current
    DESCRIPTION
        "Drop threshold for precedence1, only for taildrop mode.
        0 is returned for other mode.Range is <1-12885>.
        The set of this value will be ignored for non-taildrop mode.
        Set -1 to delete current configuration and retrieve default configuration.
        For 1G port, default value is 240;
        For 10G port, default value is 592."
    ::= { ifQosQueueManageCfgEntry 4 }

ifQosQueueManageThresholdPrecedence2    OBJECT-TYPE
    SYNTAX          Integer32 (-1|2..12886)
    MAX-ACCESS      read-write
    STATUS          current
    DESCRIPTION
        "Drop threshold for precedence1, only for taildrop mode.Range is <2-12886>.
             The set of this value will be ignored for non-taildrop mode.
             Set -1 to delete current configuration and retrieve default configuration
             for all precedence.
        For 1G port, default value is 256;
        For 10G port, default value is 608."
    ::= { ifQosQueueManageCfgEntry 5 }

ifQosQueueManageMinThresholdPre0    OBJECT-TYPE
    SYNTAX          Integer32 (-1|0..12886)
    MAX-ACCESS      read-write
    STATUS          current
    DESCRIPTION
        "Random-detect drop precedence0 min threshold, only for wred mode.Range is <0-12886>.
             The set of this value will be ignored for non-wred mode.
             Set -1 to delete current configuration and retrieve default configuration
             for all precedence.
        For 1G port, default value is 16;"
    ::= { ifQosQueueManageCfgEntry 6 }

ifQosQueueManageMinThresholdPre1    OBJECT-TYPE
    SYNTAX          Integer32 (-1|0..12886)
    MAX-ACCESS      read-write
    STATUS          current
    DESCRIPTION
        "Random-detect drop precedence1 min threshold, only for wred mode.Range is <0-12886>.
             The set of this value will be ignored for non-wred mode.
             Set -1 to delete current configuration and retrieve default configuration
             for all precedence.
        For 1G port, default value is 24;"
    ::= { ifQosQueueManageCfgEntry 7 }

ifQosQueueManageMinThresholdPre2    OBJECT-TYPE
    SYNTAX          Integer32 (-1|0..12886)
    MAX-ACCESS      read-write
    STATUS          current
    DESCRIPTION
        "Random-detect drop precedence2 min threshold, only for wred mode.
         Range is <0-12886>.For 1G port, default value is 32;
         Set -1 to delete current configuration and retrieve default configuration."
    ::= { ifQosQueueManageCfgEntry 8 }

ifQosQueueManageMaxThresholdPre0    OBJECT-TYPE
    SYNTAX          Integer32 (-1|1..12887)
    MAX-ACCESS      read-write
    STATUS          current
    DESCRIPTION
        "Random-detect drop precedence0 max threshold, only for wred mode,
             0 is returned for other mode.Range is <1-12887>.
             The set of this value will be ignored for non-wred mode.
             Set -1 to delete current configuration and retrieve default configuration
             for all precedence.
        For 1G port, default value is 480;"
    ::= { ifQosQueueManageCfgEntry 9 }

ifQosQueueManageMaxThresholdPre1    OBJECT-TYPE
    SYNTAX          Integer32 (-1|1..12887)
    MAX-ACCESS      read-write
    STATUS          current
    DESCRIPTION
        "Random-detect drop precedence1 max threshold, only for wred mode.
             The set of this value will be ignored for non-wred mode.Range is <1-12887>.
             Set -1 to delete current configuration and retrieve default configuration
             for all precedence.
        For 1G port, default value is 496;"
    ::= { ifQosQueueManageCfgEntry 10 }

ifQosQueueManageMaxThresholdPre2    OBJECT-TYPE
    SYNTAX          Integer32 (-1|1..12887)
    MAX-ACCESS      read-write
    STATUS          current
    DESCRIPTION
        "Random-detect drop precedence2 max threshold, only for wred mode.
             The set of this value will be ignored for non-taildrop mode.Range is <1-12887>.
             Set -1 to delete current configuration and retrieve default configuration
             for all precedence.
        For 1G port, default value is 512;"
    ::= { ifQosQueueManageCfgEntry 11 }

ifQosQueueManageDropProbabilityPre0    OBJECT-TYPE
    SYNTAX          Integer32 (-1|0..65535)
    MAX-ACCESS      read-write
    STATUS          current
    DESCRIPTION
        "Random-detect drop precedence0 drop probability, only for wred mode.
         Set -1 to delete current configuration and retrieve default configuration.
         The default value is 1024.Range is <0-65535>."
    DEFVAL{ 1024 }
    ::= { ifQosQueueManageCfgEntry 12 }

ifQosQueueManageDropProbabilityPre1    OBJECT-TYPE
    SYNTAX          Integer32 (-1|0..65535)
    MAX-ACCESS      read-write
    STATUS          current
    DESCRIPTION
        "Random-detect drop precedence1 drop probability, only for wred mode.
         Set -1 to delete current configuration and retrieve default configuration.
         The default value is 1024.Range is <0-65535>."
    DEFVAL{ 1024 }
    ::= { ifQosQueueManageCfgEntry 13 }

ifQosQueueManageDropProbabilityPre2    OBJECT-TYPE
    SYNTAX          Integer32 (-1|0..65535)
    MAX-ACCESS      read-write
    STATUS          current
    DESCRIPTION
        "Random-detect drop precedence2 drop probability, only for wred mode.
         Set -1 to delete current configuration and retrieve default configuration.
         The default value is 1024.Range is <0-65535>."
    DEFVAL{ 1024 }
    ::= { ifQosQueueManageCfgEntry 14 }

--ifQosCarObjects

ifQosCarObjects OBJECT IDENTIFIER    ::= { ifQos 3 }

--ifQosCarApplyTable

ifQosCarApplyTable         OBJECT-TYPE
    SYNTAX          SEQUENCE OF IfQosCarApplyEntry
    MAX-ACCESS      not-accessible
    STATUS          current
    DESCRIPTION
        "A table of interface CAR applied."
    ::= { ifQosCarObjects 1 }

ifQosCarApplyEntry     OBJECT-TYPE
    SYNTAX          IfQosCarApplyEntry
    MAX-ACCESS      not-accessible
    STATUS          current
    DESCRIPTION
        "Entry of ifQosCarApplyTable."
    INDEX           { ifIndex,
                      ifQosCarApplyDirection }
    ::= { ifQosCarApplyTable 1 }

    IfQosCarApplyEntry    ::=
    SEQUENCE
        {
            ifQosCarApplyDirection
                INTEGER,
            ifQosCarApplyColorMode
                INTEGER,
            ifQosCarApplyCir
                Integer32,
            ifQosCarApplyCbs
                Integer32,
            ifQosCarApplyType
                INTEGER,
            ifQosCarApplyPir
                Integer32,
            ifQosCarApplyPbs
                Integer32,
            ifQosCarApplyDropColor
                ColorType,
            ifQosCarApplyUseL3Length
                INTEGER,
            ifQosCarApplyRowStatus 
                RowStatus 
        }

ifQosCarApplyDirection         OBJECT-TYPE
    SYNTAX          INTEGER
        {
            input(1),
            output(2)
        }
    MAX-ACCESS      not-accessible
    STATUS          current
    DESCRIPTION
        "Direction of this port-policer applied on.
         (1) input.
         (2) output."
    ::= { ifQosCarApplyEntry 1 }

ifQosCarApplyColorMode         OBJECT-TYPE
    SYNTAX          INTEGER
        {
            colorAware(1),
            colorBlind(2)
        }
    MAX-ACCESS      read-create
    STATUS          current
    DESCRIPTION
        "Value 1 for color aware mode policer,
         value 2 for color blind mode policer.
        "
    ::= { ifQosCarApplyEntry 2 }

ifQosCarApplyCir         OBJECT-TYPE
    SYNTAX          Integer32 (8..10000000)
    MAX-ACCESS      read-create
    STATUS          current
    DESCRIPTION
        "Commit information rate (kbps).
         Range is <8-10000000>."
    ::= { ifQosCarApplyEntry 3 }

ifQosCarApplyCbs         OBJECT-TYPE
    SYNTAX          Integer32 (1000..128000)
    MAX-ACCESS      read-create
    STATUS          current
    DESCRIPTION
        "Commit burst size (bytes).
         Range is <1000-128000>."
    DEFVAL {128000}
    ::= { ifQosCarApplyEntry 4 }

ifQosCarApplyType         OBJECT-TYPE
    SYNTAX          INTEGER
        {
            rfc2697(1),
            rfc2698(2),
            rfc4115(3),
            bwp(4)
        }
    MAX-ACCESS      read-create
    STATUS          current
    DESCRIPTION
        "Set (1) is select rfc2697 mode.
         Set (2) is select rfc2698 mode.
         Set (3) is select rfc4115 mode.
         Set (4) is select bwp mode."
    ::= { ifQosCarApplyEntry 5 }
            
-- ifQosCarApplyEbs         OBJECT-TYPE
--     SYNTAX          Integer32 (1000..128000)
--     MAX-ACCESS      read-create
--     STATUS          current
--     DESCRIPTION
--         "Excess burst size (bytes).
--          Range is <1000-128000>."
--     DEFVAL {128000}
--     ::= { ifQosCarApplyEntry 6 }

ifQosCarApplyPir         OBJECT-TYPE
    SYNTAX          Integer32 (8..10000000)
    MAX-ACCESS      read-create
    STATUS          current
    DESCRIPTION
        "When Type mode is rcf2698 means Peak information rate (kbps).
         When Type mode is rfc2697&rfc4115&bwp means Excess Information Rate (kbps).
         Range is <8-10000000>."
    ::= { ifQosCarApplyEntry 7 }               

ifQosCarApplyPbs         OBJECT-TYPE
    SYNTAX          Integer32 (1000..128000)
    MAX-ACCESS      read-create
    STATUS          current
    DESCRIPTION
        "When Type mode is rcf2698 means Peak burst size (bytes).
         When Type mode is rfc2697&rfc4115&bwp means Excess Burst Size (bytes).
         Range is <1000-128000>."
    DEFVAL {128000}
    ::= { ifQosCarApplyEntry 8 }

ifQosCarApplyDropColor         OBJECT-TYPE
    SYNTAX          INTEGER
    {
     red(1),
     yellow(2)
    }
    MAX-ACCESS      read-create
    STATUS          current
    DESCRIPTION
        "Drop color configuration.When configuring 'red(1)', 
             it only drops red packet; configuring 'yellow(2)', 
             it drops both 'red' and 'yellow' packet.
        "
    DEFVAL {red}
    ::= { ifQosCarApplyEntry 9 }

ifQosCarApplyUseL3Length         OBJECT-TYPE
    SYNTAX          INTEGER 
        {
            no(2),
            yes(1)
        }
    MAX-ACCESS      read-create
    STATUS          current
    DESCRIPTION
        "2 for using L2 frame length;
             1 for using L3 length.
        "
    DEFVAL {no}
    ::= { ifQosCarApplyEntry 10 }

ifQosCarApplyRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { ifQosCarApplyEntry 11 }   
        
                     
-- ifQosPriObjects

    ifQosPriObjects OBJECT IDENTIFIER    ::= { ifQos 4 }

-- ifQosCosTable
--
ifQosCosTable         OBJECT-TYPE
    SYNTAX          SEQUENCE OF IfQosCosEntry
    MAX-ACCESS      not-accessible
    STATUS          current
    DESCRIPTION
        "A table of interface cos value."
    ::= { ifQosPriObjects 1 }

ifQosCosEntry         OBJECT-TYPE
    SYNTAX          IfQosCosEntry
    MAX-ACCESS      not-accessible
    STATUS          current
    DESCRIPTION
        "Entry of ifQosCosTable."
    INDEX     { ifIndex }
    ::= { ifQosCosTable 1 }

    IfQosCosEntry    ::=
    SEQUENCE
        {
            ifQosCosValue
                Integer32
        }

ifQosCosValue         OBJECT-TYPE
    SYNTAX          Integer32 (0..7)
    MAX-ACCESS      read-write
    STATUS          current
    DESCRIPTION
        "Cos value for this interface.Range is <0-7>.
         The default CoS for each interface is 0.
        "
    ::= { ifQosCosEntry 1 }


-- ifQosTrustTypeTable
--
ifQosTrustTypeTable         OBJECT-TYPE
    SYNTAX          SEQUENCE OF IfQosTrustTypeEntry
    MAX-ACCESS      not-accessible
    STATUS          current
    DESCRIPTION
        "A table of interface trust type."
    ::= { ifQosPriObjects 2 }

ifQosTrustTypeEntry         OBJECT-TYPE
    SYNTAX          IfQosTrustTypeEntry
    MAX-ACCESS      not-accessible
    STATUS          current
    DESCRIPTION
        "Entry of ifQosTrustTypeTable."
    INDEX     { ifIndex }
    ::= { ifQosTrustTypeTable 1 }

IfQosTrustTypeEntry    ::=
    SEQUENCE
        {
            ifQosTrustTypeValue
                INTEGER
        }

ifQosTrustTypeValue         OBJECT-TYPE
    SYNTAX   INTEGER
        {
            trustDefault(-1),
            trustPort(0),
            trustSTagCos(2),
            trustDscpExp(3),
            trustIpPre(4),
            trustCTagCos(5)
        }
    MAX-ACCESS      read-write
    STATUS          current
    DESCRIPTION
        "Trust priority type for this interface.
             Set trust-default to delete current configuration and retrieve default configuration.
            trustDefault(-1)
            trustPort(0)
            trustSTagCos(2)
            trustDscpExp(3)
            trustIpPre(4)
            trustCTagCos(5)
        "
    ::= { ifQosTrustTypeEntry 1 }


-- ifQosDomainTable
--
ifQosDomainTable         OBJECT-TYPE
    SYNTAX          SEQUENCE OF IfQosDomainEntry
    MAX-ACCESS      not-accessible
    STATUS          current
    DESCRIPTION
        "A table of interface Domain value."
    ::= { ifQosPriObjects 3 }

ifQosDomainEntry         OBJECT-TYPE
    SYNTAX          IfQosDomainEntry
    MAX-ACCESS      not-accessible
    STATUS          current
    DESCRIPTION
        "Entry of ifQosDomainTable."
    INDEX     { ifIndex }
    ::= { ifQosDomainTable 1 }

IfQosDomainEntry    ::=
    SEQUENCE
        {
            ifQosDomainValue
                Integer32
        }

ifQosDomainValue         OBJECT-TYPE
    SYNTAX          Integer32 (0..7)
    MAX-ACCESS      read-write
    STATUS          current
    DESCRIPTION
        "Domain value for this interface.
         Range <0-7>. The default value is
   0"
    DEFVAL{0}
    ::= { ifQosDomainEntry 1 }
-- ifQosReplacePriObjects

    ifQosReplacePriObjects OBJECT IDENTIFIER    ::= { ifQos 5 }

-- ifQosReplaceTable
--
ifQosReplaceTable         OBJECT-TYPE
    SYNTAX          SEQUENCE OF IfQosReplaceEntry
    MAX-ACCESS      not-accessible
    STATUS          current
    DESCRIPTION
        "A table of ifQosReplaceEntry."
    ::= { ifQosReplacePriObjects 1 }

ifQosReplaceEntry         OBJECT-TYPE
    SYNTAX          IfQosReplaceEntry
    MAX-ACCESS      not-accessible
    STATUS          current
    DESCRIPTION
        "Entry of ifQosReplaceTable."
    INDEX     { ifIndex }
    ::= { ifQosReplaceTable 1 }

IfQosReplaceEntry    ::=
    SEQUENCE
        {
        ifQosReplaceType
            INTEGER
        }

ifQosReplaceType         OBJECT-TYPE
    SYNTAX          INTEGER
        {
            none(0),
            cos(1),
            cosctag(2),
            cosstag(3),
            dscpExp(4),
            ctagdscp(5),
            stagdscp(6),
            nodscp(7),
            nocos(8)
         }
    MAX-ACCESS      read-write
    STATUS          current
    DESCRIPTION
        "Replace priority type for this interface. The defult cos is stagcos;
         The value of set this node only can be follow:
            cos(1),
            cosctag(2),
            cosstag(3),
            dscpExp(4),
            nodscp(7),
            nocos(8)"
    DEFVAL {cos}
    ::= { ifQosReplaceEntry 1 }


-- Sub Module: CBQOS
--
-- Node definitions
--

-- cbQoSClassifierObjects

    cbQoSClassifierObjects OBJECT IDENTIFIER    ::= { cbQoS 1 }

cbQoSClassifierIndexNext         OBJECT-TYPE
    SYNTAX          Integer32 (10000..20000)
    MAX-ACCESS      read-only
    STATUS          current
    DESCRIPTION
        "This object contains an appropriate value to be used for
             cbQoSClassifierIndex when creating rows in the
             cbQoSClassifierCfgInfoTable.
             If the value of this node is less than 0,
             it indicates creating a Rowin cbQoSClassifierCfgInfoTable is not permitted.
        "
    ::= { cbQoSClassifierObjects 1 }

-- cbQoSClassifierCfgInfoTable
--
cbQoSClassifierCfgInfoTable         OBJECT-TYPE
    SYNTAX          SEQUENCE OF CBQoSClassifierCfgInfoEntry
    MAX-ACCESS      not-accessible
    STATUS          current
    DESCRIPTION
        "A table of Classifier configuration information."
    ::= { cbQoSClassifierObjects 2 }

cbQoSClassifierCfgInfoEntry         OBJECT-TYPE
    SYNTAX          CBQoSClassifierCfgInfoEntry
    MAX-ACCESS      not-accessible
    STATUS          current
    DESCRIPTION
        "Classifier Configuration Information Entry."
    INDEX     { cbQoSClassifierIndex }
    ::= { cbQoSClassifierCfgInfoTable 1 }

CBQoSClassifierCfgInfoEntry    ::=
    SEQUENCE
        {
            cbQoSClassifierIndex
                Integer32,
            cbQoSClassifierName
                OCTET STRING,
            cbQoSClassifierRuleCount
                Integer32,
            cbQoSClassifierOperator
                INTEGER,
            cbQoSClassifierMatchRuleNextIndex
                Integer32,
            cbQoSClassifierRowStatus
                RowStatus
        }

cbQoSClassifierIndex         OBJECT-TYPE
    SYNTAX          Integer32 (10000..20000)
    MAX-ACCESS      not-accessible
    STATUS          current
    DESCRIPTION
        "Index of this class-map.Range is <10000-20000>."
    ::= { cbQoSClassifierCfgInfoEntry 1 }

cbQoSClassifierName         OBJECT-TYPE
    SYNTAX          OCTET STRING (SIZE (0..40))
    MAX-ACCESS      read-create
    STATUS          current
    DESCRIPTION
        "Name of class-map. Only used in creating a conceptual row,
             can not modified in an 'active' Row        "
    ::= { cbQoSClassifierCfgInfoEntry 2 }

cbQoSClassifierRuleCount         OBJECT-TYPE
    SYNTAX          Integer32
    MAX-ACCESS      read-only
    STATUS          current
    DESCRIPTION
        "The counter of match rules in class-map."
    ::= { cbQoSClassifierCfgInfoEntry 3 }

cbQoSClassifierOperator         OBJECT-TYPE
    SYNTAX          INTEGER
        {
            and(1),
            or(2)
        }
    MAX-ACCESS      read-write
    STATUS          current
    DESCRIPTION
        "Operator of the match rules of class-map. Default match operator is match-any.
             'and(1)' for match-all rules. 'or(2)' for match-any rules.
        "
    DEFVAL {or}
    ::= { cbQoSClassifierCfgInfoEntry 4 }

cbQoSClassifierMatchRuleNextIndex         OBJECT-TYPE
    SYNTAX          Integer32
    MAX-ACCESS      read-only
    STATUS          current
    DESCRIPTION
        "This object contains an appropriate value to be used for
             cbQoSMatchRuleIndex when creating rows in the
             cbQoSMatchRuleCfgInfoTable.Begin with 0.
             If the value of this node is less than 0,
             it indicates creating a Rowin cbQoSMatchRuleCfgInfoTable is not permitted.
        "
    ::= { cbQoSClassifierCfgInfoEntry 5 }

cbQoSClassifierRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { cbQoSClassifierCfgInfoEntry 6 }


--cbQoSMatchRuleCfgInfoTable

cbQoSMatchRuleCfgInfoTable         OBJECT-TYPE
    SYNTAX          SEQUENCE OF CBQoSMatchRuleCfgInfoEntry
    MAX-ACCESS      not-accessible
    STATUS          current
    DESCRIPTION
        "A table of match rule configuration in class-map. "
    ::= { cbQoSClassifierObjects 3 }

cbQoSMatchRuleCfgInfoEntry         OBJECT-TYPE
    SYNTAX          CBQoSMatchRuleCfgInfoEntry
    MAX-ACCESS      not-accessible
    STATUS          current
    DESCRIPTION
        "Match Rule Entry in Class-map."
    INDEX        { cbQoSClassifierIndex, cbQoSMatchRuleIndex }
    ::= { cbQoSMatchRuleCfgInfoTable 1 }

CBQoSMatchRuleCfgInfoEntry    ::=
    SEQUENCE
        {
            cbQoSMatchRuleIndex
                Integer32,
            cbQoSMatchRuleACLName
                OCTET STRING,
            cbQoSMatchRuleRowStatus 
                 RowStatus 
        }

cbQoSMatchRuleIndex         OBJECT-TYPE
    SYNTAX          Integer32 (10000..20000)
    MAX-ACCESS      not-accessible
    STATUS          current
    DESCRIPTION
        "Index of Match Rule. Currently only access-group(ACL) is used as matching rule. 
         Range is <10000-20000>."
    ::= { cbQoSMatchRuleCfgInfoEntry 1 }

cbQoSMatchRuleACLName         OBJECT-TYPE
    SYNTAX          OCTET STRING (SIZE (1..20))
    MAX-ACCESS      read-create
    STATUS          current
    DESCRIPTION
        "Match ACl name.Only used in creating a conceptual row,
                 can not modified in an 'active' Row     "
    ::= { cbQoSMatchRuleCfgInfoEntry 2 }

cbQoSMatchRuleRowStatus OBJECT-TYPE
        SYNTAX RowStatus
        MAX-ACCESS read-create
        STATUS current
        DESCRIPTION
            "The status of this conceptual row.Now only realize CreateAndGo and
         Destroy and Active.
        1 means Active
        4 means CreateAndGo
        6 means Destroy"
        ::= { cbQoSMatchRuleCfgInfoEntry 3 }

-- match evc is not supported by humber currently. 2011-08-05

--cbQoSMatchEvcTable         OBJECT-TYPE
--    SYNTAX          SEQUENCE OF CbQoSMatchEvcEntry
--    MAX-ACCESS      not-accessible
--    STATUS          current
--    DESCRIPTION
--        "The table of Match EVC is used to define EVC matching rule for a QoS class map.
--        If CoS values are configured, CoS field in the packet from the EVC is inspected
--        and only those matching the configured values are regarded as matching packets.
--        Otherwise, CoS field is ignored and only EVC is considered in the matching rule."
--    ::= { cbQoSClassifierObjects 4 }
--
--cbQoSMatchEvcEntry         OBJECT-TYPE
--    SYNTAX          CbQoSMatchEvcEntry
--    MAX-ACCESS      not-accessible
--    STATUS          current
--    DESCRIPTION
--        "One item of match entry."
--    INDEX { cbQoSMatchEvcClassMapIndex, cbQoSMatchEvcEvcIndex }
--    ::= { cbQoSMatchEvcTable 1 }
--
--    CbQoSMatchEvcEntry    ::=
--    SEQUENCE
--        {
--            cbQoSMatchEvcClassMapIndex
--                Integer32,
--            cbQoSMatchEvcEvcIndex
--                Integer32,
--            cbQoSMatchEvcAddCos
--                OCTET STRING,
--            cbQoSMatchEvcRowStatus
--                RowStatus
--        }
--
--cbQoSMatchEvcClassMapIndex         OBJECT-TYPE
--    SYNTAX          Integer32 (1..2048)
--    MAX-ACCESS      read-only
--    STATUS          current
--    DESCRIPTION
--        "The index of Class-map."
--    ::= { cbQoSMatchEvcEntry 1 }
--
--
--cbQoSMatchEvcEvcIndex         OBJECT-TYPE
--    SYNTAX          Integer32 (1..512)
--    MAX-ACCESS      read-only
--    STATUS          current
--    DESCRIPTION
--        "The index of EVC entry."
--    ::= { cbQoSMatchEvcEntry 2 }
--
--cbQoSMatchEvcAddCos         OBJECT-TYPE
--    SYNTAX          OCTET STRING (SIZE (1..15))
--    MAX-ACCESS      read-write
--    STATUS          current
--    DESCRIPTION
--        "Add COS of Match EVC. The format is like 1,2,3."
--    ::= { cbQoSMatchEvcEntry 3 }
--
--
--cbQoSMatchEvcRowStatus         OBJECT-TYPE
--    SYNTAX          RowStatus
--    MAX-ACCESS      read-create
--    STATUS          current
--    DESCRIPTION
--        "The status of this conceptual row.Now only realize CreateAndGo and
--         Destroy and Active."
--    ::= { cbQoSMatchEvcEntry 4 }

--
-- cbQoSPolicyObjects
--

    cbQoSPolicyObjects OBJECT IDENTIFIER    ::= { cbQoS 2 }

cbQoSPolicyIndexNext         OBJECT-TYPE
    SYNTAX          Integer32
    MAX-ACCESS      read-only
    STATUS          current
    DESCRIPTION
        "This object contains an appropriate value to be used for
             cbQoSPolicyIndex when creating rows in the
             cbQoSPolicyCfgInfoTable.
        "
    ::= { cbQoSPolicyObjects 1 }


-- cbQoSPolicyCfgInfoTable
--
cbQoSPolicyCfgInfoTable         OBJECT-TYPE
    SYNTAX          SEQUENCE OF CBQoSPolicyCfgInfoEntry
    MAX-ACCESS      not-accessible
    STATUS          current
    DESCRIPTION
        "A table of policy-map."
    ::= { cbQoSPolicyObjects 2 }

cbQoSPolicyCfgInfoEntry         OBJECT-TYPE
    SYNTAX          CBQoSPolicyCfgInfoEntry
    MAX-ACCESS      not-accessible
    STATUS          current
    DESCRIPTION
        "Policy-map table Entry."
    INDEX     {cbQoSPolicyIndex}
    ::= { cbQoSPolicyCfgInfoTable 1 }

CBQoSPolicyCfgInfoEntry    ::=
    SEQUENCE
        {
            cbQoSPolicyIndex
                Integer32,
            cbQoSPolicyName
                OCTET STRING,
            cbQoSPolicyClassCount
                Integer32,
            cbQoSPolicyClassNextIndex
                Integer32,
            cbQoSPolicyRowStatus
                RowStatus
        }

cbQoSPolicyIndex         OBJECT-TYPE
    SYNTAX          Integer32 (10000..20000)
    MAX-ACCESS      not-accessible
    STATUS          current
    DESCRIPTION
        "Index of this policy-map.Range is <10000-20000>."
    ::= { cbQoSPolicyCfgInfoEntry 1 }

cbQoSPolicyName         OBJECT-TYPE
    SYNTAX          OCTET STRING (SIZE(1..40))
    MAX-ACCESS      read-create
    STATUS          current
    DESCRIPTION
        "Name of this policy-map. Only used in creating a conceptual row,
             can not modified in an 'active' Row        "
    ::= { cbQoSPolicyCfgInfoEntry 2 }

cbQoSPolicyClassCount         OBJECT-TYPE
    SYNTAX          Integer32
    MAX-ACCESS      read-only
    STATUS          current
    DESCRIPTION
        "The counter of class-maps in this policy-map."
    ::= { cbQoSPolicyCfgInfoEntry 3 }

cbQoSPolicyClassNextIndex         OBJECT-TYPE
    SYNTAX          Integer32
    MAX-ACCESS      read-only
    STATUS          current
    DESCRIPTION
        "This object contains an appropriate value to be used for
             cbQoSPolicyClassIndex  when creating rows in the
             cbQoSPolicyClassCfgInfoTable.
             If the returned value is less 0,
             it indicates creating a Rowis not permitted."
    ::= { cbQoSPolicyCfgInfoEntry 4 }

cbQoSPolicyRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { cbQoSPolicyCfgInfoEntry 5 }    
        

-- cbQoSPolicyClassCfgInfoTable
--
cbQoSPolicyClassCfgInfoTable         OBJECT-TYPE
    SYNTAX          SEQUENCE OF CBQoSPolicyClassCfgInfoEntry
    MAX-ACCESS      not-accessible
    STATUS          current
    DESCRIPTION
        "A table of policy-class."
    ::= { cbQoSPolicyObjects 3 }

cbQoSPolicyClassCfgInfoEntry         OBJECT-TYPE
    SYNTAX          CBQoSPolicyClassCfgInfoEntry
    MAX-ACCESS      not-accessible
    STATUS          current
    DESCRIPTION
        "Policy-class table Entry."
    INDEX        {cbQoSPolicyClassIndex,
                  cbQoSPolicyClassClassifierIndex}
    ::= { cbQoSPolicyClassCfgInfoTable 1 }

CBQoSPolicyClassCfgInfoEntry    ::=
    SEQUENCE
        {
            cbQoSPolicyClassIndex
                Integer32,
            cbQoSPolicyClassClassifierIndex
                Integer32,
            cbQoSPolicyClassClassifierName
                OCTET STRING,
            cbQoSPolicyClassRowStatus
                RowStatus
        }

cbQoSPolicyClassIndex         OBJECT-TYPE
    SYNTAX          Integer32 (10000..20000)
    MAX-ACCESS      not-accessible
    STATUS          current
    DESCRIPTION
        "Index of this policy-class.Range is <10000-20000>."
    ::= { cbQoSPolicyClassCfgInfoEntry 1 }

cbQoSPolicyClassClassifierIndex         OBJECT-TYPE
    SYNTAX          Integer32 (10000..20000)
    MAX-ACCESS      not-accessible
    STATUS          current
    DESCRIPTION
        "Index of classifier applied by a policy.
             It is corresponding to cbQoSClassifierName.
             The maximum index value 20000 is reserved for class-map class-default only."
    ::= { cbQoSPolicyClassCfgInfoEntry 2 }

cbQoSPolicyClassClassifierName         OBJECT-TYPE
    SYNTAX          OCTET STRING (SIZE(1..40))
    MAX-ACCESS      read-create
    STATUS          current
    DESCRIPTION
        "Name of classifier applied by a policy.
             It should exist in cbQoSClassifierCfgInfoTable.
             Only used in creating a conceptual row,  can not modified in an 'active' row.
        "
    ::= { cbQoSPolicyClassCfgInfoEntry 3 }

cbQoSPolicyClassRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { cbQoSPolicyClassCfgInfoEntry 4 }   


-- cbQoSBehaviorObjects

cbQoSBehaviorObjects OBJECT IDENTIFIER    ::= { cbQoS 3 }

cbQoSAggregativeCarIndexNext         OBJECT-TYPE
    SYNTAX          Integer32
    MAX-ACCESS      read-only
    STATUS          current
    DESCRIPTION
        "This object contains an appropriate value to be used for
             cbQoSAggregativeCarIndex when creating rows in the
             cbQoSAggregativeCarCfgInfoTable.
        "
    ::= { cbQoSBehaviorObjects 1 }

-- cbQoSAggregativeCarCfgInfoTable
--
cbQoSAggregativeCarCfgInfoTable         OBJECT-TYPE
    SYNTAX          SEQUENCE OF CBQoSAggregativeCarCfgInfoEntry
    MAX-ACCESS      not-accessible
    STATUS          current
    DESCRIPTION
        "A table of aggregate-policer."
    ::= { cbQoSBehaviorObjects 2 }

cbQoSAggregativeCarCfgInfoEntry         OBJECT-TYPE
    SYNTAX          CBQoSAggregativeCarCfgInfoEntry
    MAX-ACCESS      not-accessible
    STATUS          current
    DESCRIPTION
        "Aggregate-policer table Entry."
    INDEX     {cbQoSAggregativeCarIndex}
    ::= { cbQoSAggregativeCarCfgInfoTable 1 }

    CBQoSAggregativeCarCfgInfoEntry    ::=
    SEQUENCE
        {
            cbQoSAggregativeCarIndex
                Integer32,
            cbQoSAggregativeCarName
                OCTET STRING,
            cbQoSAggregativeCarColorMode
                INTEGER,
            cbQoSAggregativeCarCir
                Integer32,
            cbQoSAggregativeCarCbs
                Integer32,
            cbQoSAggregativeCarType
                INTEGER,
            cbQoSAggregativeCarEbs
                Integer32,
            cbQoSAggregativeCarPir
                Integer32,
            cbQoSAggregativeCarPbs
                Integer32,
            cbQoSAggregativeCarDropColor
                ColorType,
            cbQoSAggregativeCarUseL3Length
                INTEGER,
            cbQoSAggregativeCarStats
                INTEGER,
            cbQoSAggregativeCarRowStatus
                RowStatus
        }

cbQoSAggregativeCarIndex         OBJECT-TYPE
    SYNTAX          Integer32 (10000..20000)
    MAX-ACCESS      not-accessible
    STATUS          current
    DESCRIPTION
        "Index of aggregate-policer.Range is <10000-20000>."
    ::= { cbQoSAggregativeCarCfgInfoEntry 1 }

cbQoSAggregativeCarName         OBJECT-TYPE
    SYNTAX          OCTET STRING (SIZE (1..40))
    MAX-ACCESS      read-create
    STATUS          current
    DESCRIPTION
        "Name of aggregate-policer.Only used in creating a conceptual row,
             can not modified in an 'active' row.
        "
    ::= { cbQoSAggregativeCarCfgInfoEntry 2 }

cbQoSAggregativeCarColorMode         OBJECT-TYPE
    SYNTAX          INTEGER
        {
            colorAware(1),
            colorBlind(2)
        }
    MAX-ACCESS      read-create
    STATUS          current
    DESCRIPTION
        "Value 1 for color aware mode policer;
             value 2 for color blind mode policer.
             Can modified in an 'active' row.
        "
       DEFVAL {colorBlind}
    ::= { cbQoSAggregativeCarCfgInfoEntry 3 }

cbQoSAggregativeCarCir         OBJECT-TYPE
    SYNTAX          Integer32 (8..10000000)
    MAX-ACCESS      read-create
    STATUS          current
    DESCRIPTION
        "Commit information rate (kbps).Range is <8-10000000>.
             Only used in creating a conceptual row,
             can not modified in an 'active' row.
        "
    ::= { cbQoSAggregativeCarCfgInfoEntry 4 }

cbQoSAggregativeCarCbs         OBJECT-TYPE
    SYNTAX          Integer32 (1000..128000)
    MAX-ACCESS      read-create
    STATUS          current
    DESCRIPTION
        "Commit burst size (bytes).Range is <1000-128000>.
             Only used in creating a conceptual row,
             can not modified in an 'active' row."
    DEFVAL {128000}
    ::= { cbQoSAggregativeCarCfgInfoEntry 5 }

cbQoSAggregativeCarType        OBJECT-TYPE
    SYNTAX          INTEGER
        {
            trtcm-mode(1),
            srtcm-mode(2)
        }
    MAX-ACCESS      read-create
    STATUS          current
    DESCRIPTION
        "Set (1) is select TRTCM mode.
         Set (2) is select SRTCM mode."
    ::= { cbQoSAggregativeCarCfgInfoEntry 6 }

cbQoSAggregativeCarEbs         OBJECT-TYPE
    SYNTAX          Integer32 (1000..128000)
    MAX-ACCESS      read-create
    STATUS          current
    DESCRIPTION
        "Excess burst size (bytes).Range is <1000-128000>.
             Only used in creating a conceptual row,
             can not modified in an 'active' row.
             If the cbQoSAggregativeCarPir is not zero,
             this value will be ignored.
        "
    DEFVAL {128000}
    ::= { cbQoSAggregativeCarCfgInfoEntry 7 }

cbQoSAggregativeCarPir         OBJECT-TYPE
    SYNTAX          Integer32 (8..10000000)
    MAX-ACCESS      read-create
    STATUS          current
    DESCRIPTION
        "Peak information rate (kbps).Range is <8-10000000>.
             Only used in creating a conceptual row,
             can not modified in an 'active' row.
             This valude should not be less than cbQoSAggregativeCarCir.
        "
    ::= { cbQoSAggregativeCarCfgInfoEntry 8}

cbQoSAggregativeCarPbs         OBJECT-TYPE
    SYNTAX          Integer32 (1000..128000)
    MAX-ACCESS      read-create
    STATUS          current
    DESCRIPTION
        "Peak burst size (bytes).Range is <1000-128000>.
             Only used in creating a conceptual row,
             can not modified in an 'active' row.
             If the cbQoSAggregativeCarPir is zero,
             this value will be ignored;
             This valude should not be less than cbQoSAggregativeCarCbs.
        "
    DEFVAL {128000}
    ::= { cbQoSAggregativeCarCfgInfoEntry 9 }

cbQoSAggregativeCarDropColor         OBJECT-TYPE
    SYNTAX          INTEGER
    {
     red(1),
     yellow(2)
    }
    MAX-ACCESS      read-create
    STATUS          current
    DESCRIPTION
        "Drop color configuration.When configuring 'red',
             it only drops red packet; configuring 'yellow',
             it drops both 'red' and 'yellow' packet.
             Only used in creating a conceptual row,
             can not modified in an 'active' row.
        "
    DEFVAL {red}
    ::= { cbQoSAggregativeCarCfgInfoEntry 10 }

cbQoSAggregativeCarUseL3Length         OBJECT-TYPE
    SYNTAX          INTEGER
        {
            no(2),
            yes(1)
        }
    MAX-ACCESS      read-create
    STATUS          current
    DESCRIPTION
        "2 for using L2 frame length;
             1 for using L3 length.
             Only used in creating a conceptual row,
             can not modified in an 'active' row.
        "
        DEFVAL {no}
    ::= { cbQoSAggregativeCarCfgInfoEntry 11 }

cbQoSAggregativeCarStats         OBJECT-TYPE
    SYNTAX          INTEGER
        {
            no(2),
            yes(1)
        }
    MAX-ACCESS      read-create
    STATUS          current
    DESCRIPTION
        "2 policer stats is disable;
             1 policer stats is enable.
             Only used in creating a conceptual row,
             can not modified in an 'active' row.
        "
        DEFVAL {no}
    ::= { cbQoSAggregativeCarCfgInfoEntry 12 }

cbQoSAggregativeCarRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { cbQoSAggregativeCarCfgInfoEntry 13 }


-- cbQoSBehaviorCarCfgInfoTable
-- 
cbQoSBehaviorCarCfgInfoTable         OBJECT-TYPE
    SYNTAX          SEQUENCE OF CbQoSBehaviorCarCfgInfoEntry
    MAX-ACCESS      not-accessible
    STATUS          current
    DESCRIPTION
        "A table of behavior."
    ::= { cbQoSBehaviorObjects 3 }

cbQoSBehaviorCarCfgInfoEntry         OBJECT-TYPE
    SYNTAX          CbQoSBehaviorCarCfgInfoEntry
    MAX-ACCESS      not-accessible
    STATUS          current
    DESCRIPTION
        "Behavior table Entry."
    INDEX         {cbQoSBehaviorCarPolicyIndex,
                   cbQoSBehaviorCarPolicyClassIndex}
    ::= { cbQoSBehaviorCarCfgInfoTable 1 }

CbQoSBehaviorCarCfgInfoEntry    ::=
    SEQUENCE
        {
            cbQoSBehaviorCarPolicyIndex
               Integer32,
            cbQoSBehaviorCarPolicyClassIndex
               Integer32,
            cbQoSBehaviorCarColorMode
                INTEGER,
            cbQoSBehaviorCarCir
                Integer32,
            cbQoSBehaviorCarCbs
                Integer32,
            cbQoSBehaviorCarType
                INTEGER,
            cbQoSBehaviorCarPir
                Integer32,
            cbQoSBehaviorCarPbs
                Integer32,
            cbQoSBehaviorCarDropColor
                ColorType,
            cbQoSBehaviorCarUseL3Length
                INTEGER,
            cbQoSBehaviorCarStats
                INTEGER,
            cbQoSBehaviorCarRowStatus
                RowStatus
        }

cbQoSBehaviorCarPolicyIndex         OBJECT-TYPE
    SYNTAX          Integer32(10000..20000)
    MAX-ACCESS      not-accessible
    STATUS          current
    DESCRIPTION
        "Index of Policy-map. Range is <10000-20000>.
         Associated with cbQoSPolicyIndex of cbQoSPolicyCfgInfoEntry.
        "
    ::= { cbQoSBehaviorCarCfgInfoEntry 1 }

cbQoSBehaviorCarPolicyClassIndex         OBJECT-TYPE
    SYNTAX          Integer32(10000..20000)
    MAX-ACCESS      not-accessible
    STATUS          current
    DESCRIPTION
        "Index of Policy class-map. Range is <10000-20000>.
         Associated with cbQoSPolicyClassIndex of cbQoSPolicyClassCfgInfoEntry.
        "
    ::= { cbQoSBehaviorCarCfgInfoEntry 2 }


cbQoSBehaviorCarColorMode         OBJECT-TYPE
    SYNTAX          INTEGER
        {
            colorAware(1),
            colorBlind(2)
        }
    MAX-ACCESS      read-create
    STATUS          current
    DESCRIPTION
        "Value 1 for color aware mode policer,
             value 2 for color blind mode policer.
             Only for policer behavior."
    ::= { cbQoSBehaviorCarCfgInfoEntry 5 }

cbQoSBehaviorCarCir         OBJECT-TYPE
    SYNTAX          Integer32 (8..10000000)
    MAX-ACCESS      read-create
    STATUS          current
    DESCRIPTION
        "Commit information rate (kbps).Range is <8-10000000>.
             Only for policer behavior.
        "
    ::= { cbQoSBehaviorCarCfgInfoEntry 6 }

cbQoSBehaviorCarCbs         OBJECT-TYPE
    SYNTAX          Integer32 (1000..128000)
    MAX-ACCESS      read-create
    STATUS          current
    DESCRIPTION
        "Commit burst size (bytes).Range is <1000-128000>.
             Only for policer behavior.
        "
     DEFVAL {128000}
    ::= { cbQoSBehaviorCarCfgInfoEntry 7 }

cbQoSBehaviorCarType        OBJECT-TYPE
    SYNTAX          INTEGER
        {
            rfc2697(1),
            rfc2698(2),
            rfc4115(3),
            bwp(4)
        }
    MAX-ACCESS      read-create
    STATUS          current
    DESCRIPTION
        "Set (1) is select rfc2697 mode.
         Set (2) is select rfc2698 mode.
         Set (3) is select rfc4115 mode.
         Set (4) is select bwp mode."
    ::= { cbQoSBehaviorCarCfgInfoEntry 8 }

-- cbQoSBehaviorCarEbs         OBJECT-TYPE
--     SYNTAX          Integer32 (1000..128000)
--     MAX-ACCESS      read-create
--     STATUS          current
--     DESCRIPTION
--         "Excess burst size (bytes).Range is <1000-128000>.
--              Only for policer behavior.
--         "
--         -- DEFVAL {128000}
--     ::= { cbQoSBehaviorCarCfgInfoEntry 9 }

cbQoSBehaviorCarPir         OBJECT-TYPE
    SYNTAX          Integer32 (8..10000000)
    MAX-ACCESS      read-create
    STATUS          current
    DESCRIPTION
        "Peak information rate (kbps).Range is <8-10000000>.
             Only for policer behavior.
        "
    ::= { cbQoSBehaviorCarCfgInfoEntry 10 }

cbQoSBehaviorCarPbs         OBJECT-TYPE
    SYNTAX          Integer32 (1000..128000)
    MAX-ACCESS      read-create
    STATUS          current
    DESCRIPTION
        "Peak burst size (bytes).Range is <1000-128000>.
             Only for policer behavior.
        "
        -- DEFVAL {128000}
    ::= { cbQoSBehaviorCarCfgInfoEntry 11 }

cbQoSBehaviorCarDropColor         OBJECT-TYPE
    SYNTAX          INTEGER
    {
     red(1),
     yellow(2)
    }
    MAX-ACCESS      read-create
    STATUS          current
    DESCRIPTION
        "Drop color configuration.Only 'red' and 'yellow' can be used here.
             When configuring 'red(1)', it only drops red packet;
             configuring 'yellow(2)', it drops both 'red' and 'yellow' packet.
             Only for policer behavior.
             When policy mode is aggregative policer, the result of DropColor will be none(0).
        "
         DEFVAL  {red}
    ::= { cbQoSBehaviorCarCfgInfoEntry 12 }

cbQoSBehaviorCarUseL3Length         OBJECT-TYPE
    SYNTAX          INTEGER
        {
            no(2),
            yes(1)
        }
    MAX-ACCESS      read-create
    STATUS          current
    DESCRIPTION
        "2 for using L2 frame length;
             1 for using L3 length.
             Only for policer behavior.
        "
    DEFVAL {no}
    ::= { cbQoSBehaviorCarCfgInfoEntry 13 }

cbQoSBehaviorCarStats         OBJECT-TYPE
    SYNTAX          INTEGER
        {
            no(2),
            yes(1)
        }
    MAX-ACCESS      read-create
    STATUS          current
    DESCRIPTION
        "2 policer stats is disable;
             1 policer stats is enable.
             Only for policer behavior.
        "
    DEFVAL {no}
    ::= { cbQoSBehaviorCarCfgInfoEntry 14 }

cbQoSBehaviorCarRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { cbQoSBehaviorCarCfgInfoEntry 15 }



-- cbQoSBehaviorPriColorCfgInfoTable
--
cbQoSBehaviorPriColorCfgInfoTable         OBJECT-TYPE
    SYNTAX          SEQUENCE OF CbQoSBehaviorPriColorCfgInfoEntry
    MAX-ACCESS      not-accessible
    STATUS          current
    DESCRIPTION
        "A table of setting priority-color behavior."
    ::= { cbQoSBehaviorObjects 4 }

cbQoSBehaviorPriColorCfgInfoEntry         OBJECT-TYPE
    SYNTAX          CbQoSBehaviorPriColorCfgInfoEntry
    MAX-ACCESS      not-accessible
    STATUS          current
    DESCRIPTION
        "Setting priority-color table Entry."
    INDEX         {cbQoSBehaviorPriColorPolicyIndex,
                   cbQoSBehaviorPriColorPolicyClassIndex}
    ::= { cbQoSBehaviorPriColorCfgInfoTable 1 }

CbQoSBehaviorPriColorCfgInfoEntry    ::=
    SEQUENCE
        {
            cbQoSBehaviorPriColorPolicyIndex
             Integer32,
            cbQoSBehaviorPriColorPolicyClassIndex
             Integer32,
            cbQoSBehaviorPriColorSetPriority
             Integer32,
            cbQoSBehaviorPriColorSetColor
             ColorType
        }

cbQoSBehaviorPriColorPolicyIndex         OBJECT-TYPE
    SYNTAX          Integer32(10000..20000)
    MAX-ACCESS      not-accessible
    STATUS          current
    DESCRIPTION
        "Index of Policy-map. Associated with cbQoSPolicyIndex of cbQoSPolicyCfgInfoEntry.
        "
    ::= { cbQoSBehaviorPriColorCfgInfoEntry 1 }

cbQoSBehaviorPriColorPolicyClassIndex         OBJECT-TYPE
    SYNTAX          Integer32(10000..20000)
    MAX-ACCESS      not-accessible
    STATUS          current
    DESCRIPTION
        "Index of Policy class-map.Range is <10000-20000>.
         Associated with cbQoSPolicyClassIndex of cbQoSPolicyClassCfgInfoEntry.
        "
    ::= { cbQoSBehaviorPriColorCfgInfoEntry 2 }

cbQoSBehaviorPriColorSetPriority OBJECT-TYPE
        SYNTAX Integer32 (0..63)
        MAX-ACCESS read-write
        STATUS current
        DESCRIPTION
            "Internal priority value.Range id <0-63>.
             Default priority is 0."
        ::= { cbQoSBehaviorPriColorCfgInfoEntry 3 }

cbQoSBehaviorPriColorSetColor OBJECT-TYPE
        SYNTAX ColorType
        MAX-ACCESS read-write
        STATUS current
        DESCRIPTION
            "Internal color. Set (1)red, (2)yellow, (3)green.
             Set (0) means no set priority."
        ::= { cbQoSBehaviorPriColorCfgInfoEntry 4 }



-- cbQoSBehaviorOptionTable
--
cbQoSBehaviorOptionTable         OBJECT-TYPE
    SYNTAX          SEQUENCE OF CbQoSBehaviorOptionEntry
    MAX-ACCESS      not-accessible
    STATUS          current
    DESCRIPTION
        "A table of behavior."
    ::= { cbQoSBehaviorObjects 5 }

cbQoSBehaviorOptionEntry         OBJECT-TYPE
    SYNTAX          CbQoSBehaviorOptionEntry
    MAX-ACCESS      not-accessible
    STATUS          current
    DESCRIPTION
        "ClassTrafficOption table Entry."
    INDEX         {cbQoSBehaviorOptionPolicyIndex, 
                   cbQoSBehaviorOptionPolicyClassIndex}
    ::= { cbQoSBehaviorOptionTable 1 }

CbQoSBehaviorOptionEntry    ::=
    SEQUENCE
        {
            cbQoSBehaviorOptionPolicyIndex
            	Integer32,
            cbQoSBehaviorOptionPolicyClassIndex
            	Integer32,
          	cbQoSBehaviorOptionTrust
            	INTEGER,
            cbQoSBehaviorOptionStatsEn              
                INTEGER,                      
            cbQoSBehaviorOptionRedirectIfindex       
                Integer32,                       
            cbQoSBehaviorOptionMonitorSession           
                Integer32
        }   

cbQoSBehaviorOptionPolicyIndex         OBJECT-TYPE
    SYNTAX          Integer32(10000..20000)
    MAX-ACCESS      not-accessible
    STATUS          current
    DESCRIPTION
        "Index of Policy-map.Range is <10000-20000>.
         Associated with cbQoSPolicyIndex of cbQoSPolicyCfgInfoEntry.
        "
    ::= { cbQoSBehaviorOptionEntry 1 }

cbQoSBehaviorOptionPolicyClassIndex         OBJECT-TYPE
    SYNTAX          Integer32(10000..20000)
    MAX-ACCESS      not-accessible
    STATUS          current
    DESCRIPTION
        "Index of Policy class-map.Range is <10000-20000>.
         Associated with cbQoSPolicyClassIndex of cbQoSPolicyClassCfgInfoEntry.
        "
    ::= { cbQoSBehaviorOptionEntry 2 }

cbQoSBehaviorOptionTrust         OBJECT-TYPE
    SYNTAX INTEGER
        {  
            trustNone(-1),                           
            trustPort(0),
            trustCos(2),
            trustDscp(3),
            trustIpPre(4),
            trustCosCtag(5),
            trustCosStag(6)
        }
    MAX-ACCESS      read-write
    STATUS          current
    DESCRIPTION
        "Use which prioritization type for this flow.
            trustNone(-1)                
            trustPort(0)
            trustCos(2)
            trustDscp(3)
            trustIpPre(4)
            trustCosCtag(5)
            trustCosStag(6)
        "
    DEFVAL { trustNone }
    ::= { cbQoSBehaviorOptionEntry 3 }

cbQoSBehaviorOptionStatsEn         OBJECT-TYPE
    SYNTAX          INTEGER 
        {
            enable(1),
            disable(2)
        }
    MAX-ACCESS      read-write
    STATUS          current
    DESCRIPTION
        "1 for enable statistics for each ace in class map;
         2 for disable statistics for each ace in class map.
         Default value is 2."
    DEFVAL { disable }
    ::= { cbQoSBehaviorOptionEntry 4 }

cbQoSBehaviorOptionRedirectIfindex         OBJECT-TYPE
    SYNTAX          Integer32 (0..65535)
    MAX-ACCESS      read-write
    STATUS          current
    DESCRIPTION
        "<1-65535>:Interface index of redirect.
         Set 0 means no redirect. "
    DEFVAL { 0 }
    ::= { cbQoSBehaviorOptionEntry 5 }    

cbQoSBehaviorOptionMonitorSession         OBJECT-TYPE
    SYNTAX          Integer32 (0..3)
    MAX-ACCESS      read-write
    STATUS          current
    DESCRIPTION
        "<1-3> monitor session number;
         0 no monitor, default value is 0."
    DEFVAL { 0 }
    ::= { cbQoSBehaviorOptionEntry 6 }    


-- cbQoSBehaviorCarAgpCfgTable
-- 
cbQoSBehaviorCarAgpCfgTable         OBJECT-TYPE
    SYNTAX          SEQUENCE OF CbQoSBehaviorCarAgpCfgEntry
    MAX-ACCESS      not-accessible
    STATUS          current
    DESCRIPTION
        "A table of behavior."
    ::= { cbQoSBehaviorObjects 6 }

cbQoSBehaviorCarAgpCfgEntry         OBJECT-TYPE
    SYNTAX          CbQoSBehaviorCarAgpCfgEntry
    MAX-ACCESS      not-accessible
    STATUS          current
    DESCRIPTION
        "Behavior table Entry."
    INDEX         {cbQoSBehaviorCarAgpPolicyIndex,
                   cbQoSBehaviorCarAgpPolicyClassIndex}
    ::= { cbQoSBehaviorCarAgpCfgTable 1 }

CbQoSBehaviorCarAgpCfgEntry    ::=
    SEQUENCE
        {
            cbQoSBehaviorCarAgpPolicyIndex
               Integer32,
            cbQoSBehaviorCarAgpPolicyClassIndex
               Integer32,
            cbQoSBehaviorCarAgpCarName
                OCTET STRING,
            cbQoSBehaviorCarAgpRowStatus
                RowStatus
        }

cbQoSBehaviorCarAgpPolicyIndex         OBJECT-TYPE
    SYNTAX          Integer32(10000..20000)
    MAX-ACCESS      not-accessible
    STATUS          current
    DESCRIPTION
        "Index of Policy-map. Range is <10000-20000>.
         Associated with cbQoSPolicyIndex of cbQoSPolicyCfgInfoEntry.
        "
    ::= { cbQoSBehaviorCarAgpCfgEntry 1 }

cbQoSBehaviorCarAgpPolicyClassIndex         OBJECT-TYPE
    SYNTAX          Integer32(10000..20000)
    MAX-ACCESS      not-accessible
    STATUS          current
    DESCRIPTION
        "Index of Policy class-map. Range is <10000-20000>.
         Associated with cbQoSPolicyClassIndex of cbQoSPolicyClassCfgInfoEntry.
        "
    ::= { cbQoSBehaviorCarAgpCfgEntry 2 }

cbQoSBehaviorCarAgpCarName         OBJECT-TYPE
    SYNTAX          OCTET STRING (SIZE(0..40))
    MAX-ACCESS      read-create
    STATUS          current
    DESCRIPTION
        "Only for aggregative policer name.
        "
    ::= { cbQoSBehaviorCarAgpCfgEntry 3 }

cbQoSBehaviorCarAgpRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { cbQoSBehaviorCarAgpCfgEntry 15 }




-- cbQoSApplyPolicyObjects

    cbQoSApplyPolicyObjects OBJECT IDENTIFIER    ::= { cbQoS 4 }

-- cbQoSIfApplyPolicyTable
-- 
cbQoSIfApplyPolicyTable         OBJECT-TYPE
    SYNTAX          SEQUENCE OF CBQoSIfApplyPolicyEntry
    MAX-ACCESS      not-accessible
    STATUS          current
    DESCRIPTION
        "A table of policy applied on interface."
    ::= { cbQoSApplyPolicyObjects 1 }

cbQoSIfApplyPolicyEntry         OBJECT-TYPE
    SYNTAX          CBQoSIfApplyPolicyEntry
    MAX-ACCESS      not-accessible
    STATUS          current
    DESCRIPTION
        "Policy-applied table Entry."
    INDEX        {cbQoSIfApplyPolicyIfIndex,
               cbQoSIfApplyPolicyDirection}
    ::= { cbQoSIfApplyPolicyTable 1 }

    CBQoSIfApplyPolicyEntry    ::=
    SEQUENCE
        {
            cbQoSIfApplyPolicyIfIndex
                Integer32,
            cbQoSIfApplyPolicyDirection
                INTEGER,
            cbQoSIfApplyPolicyIndex
                Integer32,
            cbQoSIfApplyPolicyName
                OCTET STRING,
            cbQoSIfApplyPolicyRowStatus 
                RowStatus 
        }
    
cbQoSIfApplyPolicyIfIndex         OBJECT-TYPE
    SYNTAX          Integer32 (0..65535)
    MAX-ACCESS      not-accessible
    STATUS          current
    DESCRIPTION
        "Ifindex. The interface should only be physical, vlan, or linkagg interface. "
    ::= { cbQoSIfApplyPolicyEntry 1 }

cbQoSIfApplyPolicyDirection         OBJECT-TYPE
    SYNTAX          INTEGER
        {
            input(1),
            output(2)
        }
    MAX-ACCESS      not-accessible
    STATUS          current
    DESCRIPTION
        "Direction of this service-policy applied on.
         1. input direction.
         2. output direction."
    ::= { cbQoSIfApplyPolicyEntry 2 }

cbQoSIfApplyPolicyIndex         OBJECT-TYPE
    SYNTAX          Integer32
    MAX-ACCESS      read-only
    STATUS          current
    DESCRIPTION
        "Index of policy in cbQoSPolicyCfgInfoTable.
             It is corresponding to cbQoSIfApplyPolicyName."
    ::= { cbQoSIfApplyPolicyEntry 3 } 

cbQoSIfApplyPolicyName         OBJECT-TYPE
    SYNTAX          OCTET STRING (SIZE(1..40))
    MAX-ACCESS      read-create
    STATUS          current
    DESCRIPTION
        "Name of policy applied.
             It should exist in cbQoSPolicyCfgInfoTable.
             Only used in creating a conceptual row,  can not modified in an 'active' Row        "
    ::= { cbQoSIfApplyPolicyEntry 4 }     

cbQoSIfApplyPolicyRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { cbQoSIfApplyPolicyEntry 5 }

-- Sub Module: GLOBALQOS

            

   globalQosEnable OBJECT-TYPE
        SYNTAX INTEGER
        {
            enable(1), 
            disable(2)
        }
        MAX-ACCESS read-write
        STATUS current
        DESCRIPTION
            "Enable/disable qos globally. enable(1),disable(2)."
        ::= { globalQos 1 }


    globalQosFlowFirst OBJECT-TYPE
        SYNTAX INTEGER
        {
            false(2), 
            true(1)
        }
        MAX-ACCESS read-write
        STATUS current
        DESCRIPTION
            "Set 'true(1)' for flow policer first, 'false(2)' for port policer first.
            Default value is false(2)."
        DEFVAL{false}
        ::= { globalQos 2 }

    globalQosResetMapObjects OBJECT IDENTIFIER ::= { globalQos 3 }

    globalQosResetDomainMapTable OBJECT-TYPE
        SYNTAX SEQUENCE OF GlobalQosResetDomainMapEntry
        MAX-ACCESS not-accessible
        STATUS current
        DESCRIPTION
            "Reset configuration of qos maping table in specified domain."
        ::= { globalQosResetMapObjects 1 }

    globalQosResetDomainMapEntry OBJECT-TYPE
        SYNTAX GlobalQosResetDomainMapEntry
        MAX-ACCESS not-accessible
        STATUS current
        DESCRIPTION
            "Entry of globalQosResetDomainMapTable."
        INDEX {
        			 globalQosResetDomainMapDomain
        			 }
        ::= { globalQosResetDomainMapTable 1 }

    GlobalQosResetDomainMapEntry ::=
        SEQUENCE
        {
           globalQosResetDomainMapDomain
                Integer32,
            globalQosResetDomainMapType
                INTEGER      
        }

     globalQosResetDomainMapDomain OBJECT-TYPE
        SYNTAX Integer32 (0..7)
        MAX-ACCESS not-accessible
        STATUS current
        DESCRIPTION
            "Qos domain.Range is <0-7>."
        ::= { globalQosResetDomainMapEntry 1 }

    globalQosResetDomainMapType OBJECT-TYPE
        SYNTAX INTEGER
        {                            
            cosPriColor(1),    
            dscpPriColor(2),
            expPriColor(3), 
            ipPrecPriColor(4), 
            priColorCos(5),
            priColorDscp(6), 
            priColorExp(7) 
        }
        MAX-ACCESS read-write
        STATUS current
        DESCRIPTION
            "Restore the whole running map table to system default table. 
             Set the value to restore related table.
             cosPriColor(1)      Restore the COS-to-Priority/Color map
             dscpPriColor(2)     Restore dscp-priority-color map
             expPriColor(3)      Restore the exp-to-priority/color map
             ipPrecPriColor(4)   Restore the IP Precedence to Pri/Color map
             priColorCos(5)      Restore PRI_COLOR-to-COS map
             priColorDscp(6)     Restore PRI_COLOR-to-DSCP map
             priColorExp(7)      Restore PRI_COLOR-to-EXP map
             The get of this value alway return 0"
        ::= { globalQosResetDomainMapEntry 2 }
        
    globalQosResetPriColorQidTid OBJECT-TYPE
        SYNTAX Integer32 (0..1)
        MAX-ACCESS read-write
        STATUS current
        DESCRIPTION
            "Set 1 to reset priority-color-queueId-thresholdId mapping.
             Zero will be returned. "
        ::= { globalQosResetMapObjects 2 }

-- globalQosMapObjects

    globalQosMapObjects OBJECT IDENTIFIER ::= { globalQos 4 }

-- globalQosMapIngressTable
--
    globalQosMapIngressTable OBJECT-TYPE
        SYNTAX SEQUENCE OF GlobalQosMapIngressEntry
        MAX-ACCESS not-accessible
        STATUS current
        DESCRIPTION
            "Running table of interface ingress map."
        ::= { globalQosMapObjects 1 }

    globalQosMapIngressEntry OBJECT-TYPE
        SYNTAX GlobalQosMapIngressEntry
        MAX-ACCESS not-accessible
        STATUS current
        DESCRIPTION
            "Entry of globalQosMapIngressTable."
        INDEX {
        			 globalQosMapIngressType, 
        			 globalQosMapIngressDomain,
               globalQosMapIngressValue}
        ::= { globalQosMapIngressTable 1 }

    GlobalQosMapIngressEntry ::=
        SEQUENCE
        {
           globalQosMapIngressType
                PriMapType,
           globalQosMapIngressDomain
                Integer32,
            globalQosMapIngressValue
                Integer32,                    
             globalQosMapIngressToPriority
                Integer32,   
            globalQosMapIngressToColor
                ColorType
        }

    globalQosMapIngressType OBJECT-TYPE
        SYNTAX PriMapType
        MAX-ACCESS not-accessible
        STATUS current
        DESCRIPTION
            "Type of map.
            cos(1), 
            dscp(2),
            exp(3),
            ipPre(4) "
        ::= { globalQosMapIngressEntry 1 }

     globalQosMapIngressDomain OBJECT-TYPE
        SYNTAX Integer32 (0..7)
        MAX-ACCESS not-accessible
        STATUS current
        DESCRIPTION
            "Ingress domain. Range is <0-7>."
        ::= { globalQosMapIngressEntry 2 }
        
    globalQosMapIngressValue OBJECT-TYPE
        SYNTAX Integer32     (1..2147483647)
        MAX-ACCESS not-accessible
        STATUS current
        DESCRIPTION
            "Different type has different  GlobalQosMapIngressValue.
             Type-name       Range of GlobalQosMapIngressValue
             cos             (0..7)
             dscp            (0..63)
             ipPre          (0..7)
             exp             (0..7)"
        ::= { globalQosMapIngressEntry 3 }

     globalQosMapIngressToPriority OBJECT-TYPE
        SYNTAX Integer32 (0..63)
        MAX-ACCESS read-write
        STATUS current
        DESCRIPTION
            "Internal priority value.Range is <0-63>."
        ::= { globalQosMapIngressEntry 4 }

     globalQosMapIngressToColor OBJECT-TYPE
        SYNTAX ColorType
        MAX-ACCESS read-write
        STATUS current
        DESCRIPTION
            "Internal color.Set (1)red, (2)yellow, (3)green."
        ::= { globalQosMapIngressEntry 5 }
        
-- globalQosMapEgressTable
--
    globalQosMapEgressTable OBJECT-TYPE
        SYNTAX SEQUENCE OF GlobalQosMapEgressEntry
        MAX-ACCESS not-accessible
        STATUS current
        DESCRIPTION
            "Running table of interface egress map."
        ::= { globalQosMapObjects 2 }

    globalQosMapEgressEntry OBJECT-TYPE
        SYNTAX GlobalQosMapEgressEntry
        MAX-ACCESS not-accessible
        STATUS current
        DESCRIPTION
            "Entry of globalQosMapEgressTable"
        INDEX {
        			 globalQosMapEgressType, 
        			 globalQosMapEgressDomain,
               globalQosMapEgressPriority,
               globalQosMapEgressColor}
        ::= { globalQosMapEgressTable 1 }

    GlobalQosMapEgressEntry ::=
        SEQUENCE
        {
            globalQosMapEgressType
                PriMapType,
            globalQosMapEgressDomain
                Integer32,
            globalQosMapEgressPriority
                Integer32,                    
             globalQosMapEgressColor
                ColorType,   
             globalQosMapEgressValue
                Integer32
        }         

    globalQosMapEgressType OBJECT-TYPE
        SYNTAX PriMapType
        MAX-ACCESS not-accessible
        STATUS current
        DESCRIPTION
            "Type of the egress map-table. Only value cos(1), dscp(2), exp(3) can be use."
        ::= { globalQosMapEgressEntry 1 }

     globalQosMapEgressDomain OBJECT-TYPE
        SYNTAX Integer32 (0..7)
        MAX-ACCESS not-accessible
        STATUS current
        DESCRIPTION
            "Egress domain.Range is <0-7>."
        ::= { globalQosMapEgressEntry 2 }
        
     globalQosMapEgressPriority OBJECT-TYPE
        SYNTAX Integer32 (0..63)
        MAX-ACCESS not-accessible
        STATUS current
        DESCRIPTION
            "Internal priority value.Range is <0-63>."
        ::= { globalQosMapEgressEntry 3 }

     globalQosMapEgressColor OBJECT-TYPE
        SYNTAX ColorType
        MAX-ACCESS not-accessible
        STATUS current
        DESCRIPTION
            "Internal color. Set (1)red, (2)yellow, (3)green."
        ::= { globalQosMapEgressEntry 4 }

    globalQosMapEgressValue OBJECT-TYPE
        SYNTAX Integer32
        MAX-ACCESS read-write
        STATUS current
        DESCRIPTION
            "Different type has different  GlobalQosMapIngressValue.
             Type-name       Range of GlobalQosMapIngressValue
             cos             (0..7)
             dscp            (0..63)
             exp             (0..7)"
        ::= { globalQosMapEgressEntry 5 }
        
    globalQosMapPriColorQidTidTable OBJECT-TYPE
        SYNTAX SEQUENCE OF GlobalQosMapPriColorQidTidEntry
        MAX-ACCESS not-accessible
        STATUS current
        DESCRIPTION
            "A table of qos map priority-color to QueueId - thresholdId."
        ::= { globalQosMapObjects 3 }

    globalQosMapPriColorQidTidEntry OBJECT-TYPE
        SYNTAX GlobalQosMapPriColorQidTidEntry
        MAX-ACCESS not-accessible
        STATUS current
        DESCRIPTION
            "Entry of globalQosMapPriColorQidTidTable."
        INDEX {
        			 globalQosMapPriColorQidTidPriority,
               globalQosMapPriColorQidTidColor}
        ::= { globalQosMapPriColorQidTidTable 1 }

    GlobalQosMapPriColorQidTidEntry ::=
        SEQUENCE
        {
            globalQosMapPriColorQidTidPriority
                Integer32,
            globalQosMapPriColorQidTidColor
                ColorType,
            globalQosMapPriColorQidTidQueueId
                IfQueueId,
            globalQosMapPriColorQidTidThresholdId
                Integer32
        }         


     globalQosMapPriColorQidTidPriority OBJECT-TYPE
        SYNTAX Integer32 (0..63)
        MAX-ACCESS not-accessible
        STATUS current
        DESCRIPTION
            "QoS Map Priority to be configured.Range is <0-63>."
        ::= { globalQosMapPriColorQidTidEntry 1 }
        
     globalQosMapPriColorQidTidColor OBJECT-TYPE
        SYNTAX ColorType
        MAX-ACCESS not-accessible
        STATUS current
        DESCRIPTION
            "Internal color. Set (1)red, (2)yellow, (3)green."
        ::= { globalQosMapPriColorQidTidEntry 2 }
   
    globalQosMapPriColorQidTidQueueId OBJECT-TYPE
        SYNTAX IfQueueId
        MAX-ACCESS read-write
        STATUS current
        DESCRIPTION
            "The queue id to be mapped to.Range is <0-7>."
        ::= { globalQosMapPriColorQidTidEntry 3 }

    globalQosMapPriColorQidTidThresholdId OBJECT-TYPE
        SYNTAX Integer32 (0..3)
        MAX-ACCESS read-write
        STATUS current
        DESCRIPTION
            "The threasholdId id to be mapped to.Range is <0-3>."
        ::= { globalQosMapPriColorQidTidEntry 4 }


-- globalQosMapIngressDefaultTable
--
    globalQosMapIngressDefaultTable OBJECT-TYPE
        SYNTAX SEQUENCE OF GlobalQosMapIngressDefaultEntry
        MAX-ACCESS not-accessible
        STATUS current
        DESCRIPTION
            "A table of interface ingress map."
        ::= { globalQosMapObjects 4 }

    globalQosMapIngressDefaultEntry OBJECT-TYPE
        SYNTAX GlobalQosMapIngressDefaultEntry
        MAX-ACCESS not-accessible
        STATUS current
        DESCRIPTION
            "Entry of globalQosMapIngressDefaultTable."
        INDEX {
        			 globalQosMapIngressDefaultType, 
        			 globalQosMapIngressDefaultDomain,
               globalQosMapIngressDefaultValue}
        ::= { globalQosMapIngressDefaultTable 1 }

    GlobalQosMapIngressDefaultEntry ::=
        SEQUENCE
        {
            globalQosMapIngressDefaultType
                PriMapType,
            globalQosMapIngressDefaultDomain
                Integer32,
            globalQosMapIngressDefaultValue
                Integer32,                    
             globalQosMapIngressDefaultToPriority
                Integer32,   
             globalQosMapIngressDefaultToColor
                ColorType
        }

    globalQosMapIngressDefaultType OBJECT-TYPE
        SYNTAX PriMapType
        MAX-ACCESS not-accessible
        STATUS current
        DESCRIPTION
            "Type of map.
            cos(1), 
            dscp(2),
            exp(3),
            ipPre(4) "
        ::= { globalQosMapIngressDefaultEntry 1 }

     globalQosMapIngressDefaultDomain OBJECT-TYPE
        SYNTAX Integer32 (0..7)
        MAX-ACCESS not-accessible
        STATUS current
        DESCRIPTION
            "Ingress domain."
        ::= { globalQosMapIngressDefaultEntry 2 }
        
    globalQosMapIngressDefaultValue OBJECT-TYPE
        SYNTAX Integer32        (1..2147483647)
        MAX-ACCESS not-accessible
        STATUS current
        DESCRIPTION
            "Different type has different  GlobalQosMapIngressValue.
             Type-name       Range of GlobalQosMapIngressValue
             cos             (0..7)
             dscp            (0..63)
             ipPre          (0..7)
             exp             (0..7)"
        ::= { globalQosMapIngressDefaultEntry 3 }

     globalQosMapIngressDefaultToPriority OBJECT-TYPE
        SYNTAX Integer32 (0..63)
        MAX-ACCESS read-only
        STATUS current
        DESCRIPTION
            "Internal priority value."
        ::= { globalQosMapIngressDefaultEntry 4 }

     globalQosMapIngressDefaultToColor OBJECT-TYPE
        SYNTAX ColorType
        MAX-ACCESS read-only
        STATUS current
        DESCRIPTION
            "Internal color.Set (1)red, (2)yellow, (3)green."
        ::= { globalQosMapIngressDefaultEntry 5 }

-- globalQosMapEgressDefaultTable
--
    globalQosMapEgressDefaultTable OBJECT-TYPE
        SYNTAX SEQUENCE OF GlobalQosMapEgressDefaultEntry
        MAX-ACCESS not-accessible
        STATUS current
        DESCRIPTION
            "A table of interface egress map."
        ::= { globalQosMapObjects 5 }

    globalQosMapEgressDefaultEntry OBJECT-TYPE
        SYNTAX GlobalQosMapEgressDefaultEntry
        MAX-ACCESS not-accessible
        STATUS current
        DESCRIPTION
            "Entry of globalQosMapEgressDefaultTable."
        INDEX {
        			 globalQosMapEgressDefaultType, 
        			 globalQosMapEgressDefaultDomain,
               globalQosMapEgressDefaultPriority,
               globalQosMapEgressDefaultColor}
        ::= { globalQosMapEgressDefaultTable 1 }

    GlobalQosMapEgressDefaultEntry ::=
        SEQUENCE
        {
            globalQosMapEgressDefaultType
                PriMapType,
            globalQosMapEgressDefaultDomain
                Integer32,
            globalQosMapEgressDefaultPriority
                Integer32,                    
             globalQosMapEgressDefaultColor
                ColorType,   
             globalQosMapEgressDefaultValue
                Integer32
        }         

    globalQosMapEgressDefaultType OBJECT-TYPE
        SYNTAX PriMapType
        MAX-ACCESS not-accessible
        STATUS current
        DESCRIPTION
            "Type of the egress map-table. Only valude cos(1), dscp(2), exp(3) can be use."
        ::= { globalQosMapEgressDefaultEntry 1 }

     globalQosMapEgressDefaultDomain OBJECT-TYPE
        SYNTAX Integer32 (0..7)
        MAX-ACCESS not-accessible
        STATUS current
        DESCRIPTION
            "Egress domain."
        ::= { globalQosMapEgressDefaultEntry 2 }
   
     globalQosMapEgressDefaultPriority OBJECT-TYPE
        SYNTAX Integer32 (0..63)
        MAX-ACCESS not-accessible
        STATUS current
        DESCRIPTION
            "Internal priority value."
        ::= { globalQosMapEgressDefaultEntry 3 }

     globalQosMapEgressDefaultColor OBJECT-TYPE
        SYNTAX ColorType
        MAX-ACCESS not-accessible
        STATUS current
        DESCRIPTION
            "Internal color. Set (1)red, (2)yellow, (3)green."
        ::= { globalQosMapEgressDefaultEntry 4 }
     
    globalQosMapEgressDefaultValue OBJECT-TYPE
        SYNTAX Integer32
        MAX-ACCESS read-only
        STATUS current
        DESCRIPTION
            "Different type has different  GlobalQosMapIngressValue.
             Type-name       Range of GlobalQosMapIngressValue
             cos             (0..7)
             dscp            (0..63)
             exp             (0..7)"
        ::= { globalQosMapEgressDefaultEntry 5 }            


        
    globalQosMapPriColorQidTidDefaultTable OBJECT-TYPE
        SYNTAX SEQUENCE OF GlobalQosMapPriColorQidTidDefaultEntry
        MAX-ACCESS not-accessible
        STATUS current
        DESCRIPTION
            "A table of default qos mapping configuration of priority-color to QueueId - thresholdId."
        ::= { globalQosMapObjects 6 }

    globalQosMapPriColorQidTidDefaultEntry OBJECT-TYPE
        SYNTAX GlobalQosMapPriColorQidTidDefaultEntry
        MAX-ACCESS not-accessible
        STATUS current
        DESCRIPTION
            "Entry of globalQosMapPriColorQidTidDefaultTable."
        INDEX {
        			 globalQosMapPriColorQidTidDefaultPriority,
               globalQosMapPriColorQidTidDefaultColor}
        ::= { globalQosMapPriColorQidTidDefaultTable 1 }

    GlobalQosMapPriColorQidTidDefaultEntry ::=
        SEQUENCE
        {
            globalQosMapPriColorQidTidDefaultPriority
                Integer32,
            globalQosMapPriColorQidTidDefaultColor
                ColorType,
            globalQosMapPriColorQidTidDefaultQueueId
                IfQueueId,
            globalQosMapPriColorQidTidDefaultThresholdId
                Integer32
        }         


     globalQosMapPriColorQidTidDefaultPriority OBJECT-TYPE
        SYNTAX Integer32 (0..63)
        MAX-ACCESS not-accessible
        STATUS current
        DESCRIPTION
            "Internal priority."
        ::= { globalQosMapPriColorQidTidDefaultEntry 1 }
        
     globalQosMapPriColorQidTidDefaultColor OBJECT-TYPE
        SYNTAX ColorType
        MAX-ACCESS not-accessible
        STATUS current
        DESCRIPTION
            "Internal color. Set (1)red, (2)yellow, (3)green."
        ::= { globalQosMapPriColorQidTidDefaultEntry 2 }
   
    globalQosMapPriColorQidTidDefaultQueueId OBJECT-TYPE
        SYNTAX IfQueueId
        MAX-ACCESS read-only
        STATUS current
        DESCRIPTION
            "The queue id."
        ::= { globalQosMapPriColorQidTidDefaultEntry 3 }        

    globalQosMapPriColorQidTidDefaultThresholdId OBJECT-TYPE
        SYNTAX Integer32
        MAX-ACCESS read-only
        STATUS current
        DESCRIPTION
            "The threasholdId id."
        ::= { globalQosMapPriColorQidTidDefaultEntry 4 }
    
    globalQosCfiTable OBJECT-TYPE
        SYNTAX SEQUENCE OF GlobalQosCfiEntry
        MAX-ACCESS not-accessible
        STATUS current
        DESCRIPTION
            "A table of qos domain cfi config."
        ::= { globalQos 5 }

    globalQosCfiEntry OBJECT-TYPE
        SYNTAX GlobalQosCfiEntry
        MAX-ACCESS not-accessible
        STATUS current
        DESCRIPTION
            "Entry of globalQosCfiTable."
        INDEX {
        			 globalQosCfiDomain}
        ::= { globalQosCfiTable 1 }

    GlobalQosCfiEntry ::=
        SEQUENCE
        {
            globalQosCfiDomain
                Integer32,
            globalQosCfiEnable
                TruthValue
        }         


     globalQosCfiDomain OBJECT-TYPE
        SYNTAX Integer32 (0..7)
        MAX-ACCESS not-accessible
        STATUS current
        DESCRIPTION
            "QoS domain to be configured. Range is <0~7>."
        ::= { globalQosCfiEntry 1 }
   
    globalQosCfiEnable OBJECT-TYPE
        SYNTAX TruthValue
        MAX-ACCESS read-write
        STATUS current
        DESCRIPTION
            "Cfi enable status of qos domain.
             Set (1)enable, (2)disable.
             Default:(2)disable."
        DEFVAL{disable}
        ::= { globalQosCfiEntry 2 }



-- Sub Module: STATS
                            
                                                           
        
--
--type definitions 
--


--Direction
    DirectionType    ::= TEXTUAL-CONVENTION
    STATUS          current
    DESCRIPTION
        "The direction of policy  on at interface."
    SYNTAX          INTEGER
        {
            inbound(1),
            outbound(2)
        }

--Enable
    EnableType    ::= TEXTUAL-CONVENTION
    STATUS          current
    DESCRIPTION
        "The direction of policy  on at interface."
    SYNTAX          INTEGER
        {
            enabled(1),
            disabled(2)
        }

--Clear value
    QosStatsClear    ::= TEXTUAL-CONVENTION
    STATUS          current
    DESCRIPTION
        "cleared: Reset the value of the rule's counter.
             nouse: 'nouse' will be returned when getting.
        "
    SYNTAX          INTEGER
        {
            cleared(0),
            nouse(1)
        }
            
--
--end of type definitions 
--

--srvQos definition
srvQosSapIngressObjects        OBJECT IDENTIFIER     ::= { srvQos 1 }
srvQosSapEgressObjects         OBJECT IDENTIFIER     ::= { srvQos 2 }
srvQosFreeQueueInfoObjects     OBJECT IDENTIFIER     ::= { srvQos 3 }

--sap ingress definition--
srvQosSapIngressTable                    OBJECT-TYPE
 SYNTAX          SEQUENCE OF SrvQosSapIngressEntry
 MAX-ACCESS      not-accessible
 STATUS          current
 DESCRIPTION
  "Table of qos sap ingress."
 ::= { srvQosSapIngressObjects 1 }

srvQosSapIngressEntry                     OBJECT-TYPE
    SYNTAX          SrvQosSapIngressEntry
    MAX-ACCESS      not-accessible
    STATUS          current
    DESCRIPTION
     "Entries of qos sap ingress."
    INDEX   {srvQosSapIngressName}
    ::= { srvQosSapIngressTable 1 }

SrvQosSapIngressEntry ::=
 SEQUENCE
 {
  srvQosSapIngressName
   OCTET STRING,
  srvQosSapIngressRowStatus
   RowStatus,
  srvQosSapIngressDescription
   OCTET STRING,
  srvQosSapIngressApplyPolicyMap
      OCTET STRING
 }

srvQosSapIngressName         OBJECT-TYPE
    SYNTAX          OCTET STRING
    MAX-ACCESS      not-accessible
    STATUS          current
    DESCRIPTION
     "Name of the qos sap ingress."
    ::= { srvQosSapIngressEntry 1}

srvQosSapIngressRowStatus         OBJECT-TYPE
    SYNTAX          RowStatus
    MAX-ACCESS      read-create
    STATUS          current
    DESCRIPTION
     "Status of the srvQosSapIngressEntry row.
       1 means Active
        4 means CreateAndGo
        6 means Destroy."
    ::= { srvQosSapIngressEntry 2}

srvQosSapIngressDescription      OBJECT-TYPE
    SYNTAX          OCTET STRING
    MAX-ACCESS      read-write
    STATUS          current
    DESCRIPTION
     "Descrption of the qos sap ingress."
    ::= { srvQosSapIngressEntry 3}

srvQosSapIngressApplyPolicyMap      OBJECT-TYPE
    SYNTAX          OCTET STRING
    MAX-ACCESS      read-write
    STATUS          current
    DESCRIPTION
     "Policy map  for the qos sap ingress."
    ::= { srvQosSapIngressEntry 4}

--sap ingress policer definition--
srvQosSapIngressPolicerTable                    OBJECT-TYPE
 SYNTAX          SEQUENCE OF SrvQosSapIngressPolicerEntry
 MAX-ACCESS      not-accessible
 STATUS          current
 DESCRIPTION
  "Table of qos sap ingress policer."
 ::= { srvQosSapIngressObjects 2}

srvQosSapIngressPolicerEntry                     OBJECT-TYPE
    SYNTAX          SrvQosSapIngressPolicerEntry
    MAX-ACCESS      not-accessible
    STATUS          current
    DESCRIPTION
     "Entries of qos sap ingress policer."
    INDEX   {srvQosSapIngressName}
    ::= { srvQosSapIngressPolicerTable 1 }

SrvQosSapIngressPolicerEntry ::=
 SEQUENCE
 {
  srvQosSapIngressPolicerMode
      INTEGER,
  srvQosSapIngressPolicerCir
      Integer32,
  srvQosSapIngressPolicerCbs
      Integer32,
  srvQosSapIngressPolicerEbs
      Integer32,
  srvQosSapIngressPolicerPir
      Integer32,
  srvQosSapIngressPolicerPbs
      Integer32,
  srvQosSapIngressPolicerDropColor
      INTEGER,
  srvQosSapIngressPolicerUseL3Length
      INTEGER
 }


srvQosSapIngressPolicerMode      OBJECT-TYPE
    SYNTAX          INTEGER{ colorAware(0), colorBlind(1) }
    MAX-ACCESS      read-write
    STATUS          current
    DESCRIPTION
     "Policer mode of the qos sap ingress."
    ::= { srvQosSapIngressPolicerEntry 1}

srvQosSapIngressPolicerCir      OBJECT-TYPE
    SYNTAX          Integer32(1..10000000)
    MAX-ACCESS      read-write
    STATUS          current
    DESCRIPTION
     "Cir of the qos sap ingress."
    ::= { srvQosSapIngressPolicerEntry 2}

srvQosSapIngressPolicerCbs      OBJECT-TYPE
    SYNTAX          Integer32(0..4000000)
    MAX-ACCESS      read-write
    STATUS          current
    DESCRIPTION
     "Cbs of the qos sap ingress."
    ::= { srvQosSapIngressPolicerEntry 3}

srvQosSapIngressPolicerEbs      OBJECT-TYPE
    SYNTAX          Integer32(0..4000000)
    MAX-ACCESS      read-write
    STATUS          current
    DESCRIPTION
     "Ebs of the qos sap ingress."
    ::= { srvQosSapIngressPolicerEntry 4}

srvQosSapIngressPolicerPir      OBJECT-TYPE
    SYNTAX          Integer32(1..10000000)
    MAX-ACCESS      read-write
    STATUS          current
    DESCRIPTION
     "Pir of the qos sap ingress."
    ::= { srvQosSapIngressPolicerEntry 5}

srvQosSapIngressPolicerPbs      OBJECT-TYPE
    SYNTAX          Integer32(0..4000000)
    MAX-ACCESS      read-write
    STATUS          current
    DESCRIPTION
     "Pbs of the qos sap ingress."
    ::= { srvQosSapIngressPolicerEntry 6}

srvQosSapIngressPolicerDropColor      OBJECT-TYPE
    SYNTAX          INTEGER{ none(0), red(1),  yellow(2), green(3) }
    MAX-ACCESS      read-write
    STATUS          current
    DESCRIPTION
     "Drop color of the qos sap ingress."
    ::= { srvQosSapIngressPolicerEntry 7}

srvQosSapIngressPolicerUseL3Length      OBJECT-TYPE
    SYNTAX          INTEGER{ false(0), true(1) }
    MAX-ACCESS      read-write
    STATUS          current
    DESCRIPTION
     "If L3 length is used for the qos sap ingress."
    ::= { srvQosSapIngressPolicerEntry 8}

srvQosSapEgressTable                    OBJECT-TYPE
 SYNTAX          SEQUENCE OF SrvQosSapEgressEntry
 MAX-ACCESS      not-accessible
 STATUS          current
 DESCRIPTION
  "Table of qos sap Egress."
 ::= { srvQosSapEgressObjects 1 }

--sap egress definition--
srvQosSapEgressEntry                     OBJECT-TYPE
    SYNTAX          SrvQosSapEgressEntry
    MAX-ACCESS      not-accessible
    STATUS          current
    DESCRIPTION
     "Entries of qos sap Egress."
    INDEX   {srvQosSapEgressName}
    ::= { srvQosSapEgressTable 1 }

SrvQosSapEgressEntry ::=
 SEQUENCE
 {
  srvQosSapEgressName
   OCTET STRING,
  srvQosSapEgressRowStatus
   RowStatus,
  srvQosSapEgressDescription
   OCTET STRING,
  srvQosSapEgressShapeAverage
   Integer32
 }

srvQosSapEgressName         OBJECT-TYPE
    SYNTAX          OCTET STRING
    MAX-ACCESS      not-accessible
    STATUS          current
    DESCRIPTION
     "Name of the qos sap Egress."
    ::= { srvQosSapEgressEntry 1}

srvQosSapEgressRowStatus         OBJECT-TYPE
    SYNTAX          RowStatus
    MAX-ACCESS      read-create
    STATUS          current
    DESCRIPTION
     "Status of the srvQosSapEgressEntry row.
       1 means Active
        4 means CreateAndGo
        6 means Destroy."
    ::= { srvQosSapEgressEntry 2}

srvQosSapEgressDescription      OBJECT-TYPE
    SYNTAX          OCTET STRING
    MAX-ACCESS      read-write
    STATUS          current
    DESCRIPTION
     "Descrption of the qos sap Egress."
    ::= { srvQosSapEgressEntry 3}

srvQosSapEgressShapeAverage       OBJECT-TYPE
    SYNTAX          Integer32(0..1000000)
    MAX-ACCESS      read-write
    STATUS          current
    DESCRIPTION
     "Total Rate of the qos sap Egress."
    ::= { srvQosSapEgressEntry 4}

--sap egress queue definition--
srvQosSapEgressQueueTable          OBJECT-TYPE
 SYNTAX          SEQUENCE OF SrvQosSapEgressQueueEntry
 MAX-ACCESS      not-accessible
 STATUS          current
 DESCRIPTION
  "Table of qos sap egress queue."
 ::= { srvQosSapEgressObjects 2 }

srvQosSapEgressQueueEntry                     OBJECT-TYPE
    SYNTAX          SrvQosSapEgressQueueEntry
    MAX-ACCESS      not-accessible
    STATUS          current
    DESCRIPTION
     "Entries of qos sap egress queue."
    INDEX   {srvQosSapEgressName, srvQosSapEgressQueueId}
    ::= { srvQosSapEgressQueueTable 1 }

SrvQosSapEgressQueueEntry ::=
 SEQUENCE
 {
  srvQosSapEgressQueueId
   Integer32,
  srvQosSapEgressQueueShapeAverageRateCir
   Integer32,
  srvQosSapEgressQueueShapeAverageRatePir
   Integer32
 }

srvQosSapEgressQueueId          OBJECT-TYPE
    SYNTAX          Integer32(0..3)
    MAX-ACCESS      not-accessible
    STATUS          current
    DESCRIPTION
     "Id of the qos sap Egress Queue."
    ::= { srvQosSapEgressQueueEntry 1}

srvQosSapEgressQueueShapeAverageRateCir       OBJECT-TYPE
    SYNTAX          Integer32(0..10000000)
    MAX-ACCESS      read-create
    STATUS          current
    DESCRIPTION
     "Shape rate for commit information rate, kbps."
    ::= { srvQosSapEgressQueueEntry 2}

srvQosSapEgressQueueShapeAverageRatePir       OBJECT-TYPE
    SYNTAX          Integer32(0..10000000)
    MAX-ACCESS      read-create
    STATUS          current
    DESCRIPTION
     "Shape rate for peak information rate, kbps."
    ::= { srvQosSapEgressQueueEntry 3}

--sap egress queue info definition--
srvQosSapEgressQueueInfoTable          OBJECT-TYPE
 SYNTAX          SEQUENCE OF SrvQosSapEgressQueueInfoEntry
 MAX-ACCESS      not-accessible
 STATUS          current
 DESCRIPTION
  "Table of qos sap egress queue info."
 ::= { srvQosSapEgressObjects 3 }

srvQosSapEgressQueueInfoEntry                     OBJECT-TYPE
    SYNTAX          SrvQosSapEgressQueueInfoEntry
    MAX-ACCESS      not-accessible
    STATUS          current
    DESCRIPTION
     "Entries of qos sap egress queue info."
    INDEX   {srvQosSapEgressName, srvQosSapEgressQueueId}
    ::= { srvQosSapEgressQueueInfoTable 1 }

SrvQosSapEgressQueueInfoEntry ::=
 SEQUENCE
 {
  srvQosSapEgressQueueInfoRandomDetect
   Integer32,
  srvQosSapEgressQueueInfoTailDropThreshold0
   Integer32,
  srvQosSapEgressQueueInfoTailDropThreshold1
   Integer32,
  srvQosSapEgressQueueInfoTailDropThreshold2
   Integer32,
  srvQosSapEgressQueueInfoTailDropThreshold3
   Integer32,
  srvQosSapEgressQueueInfoRandomDetectMinThreshold0
   Integer32,
  srvQosSapEgressQueueInfoRandomDetectMinThreshold1
   Integer32,
  srvQosSapEgressQueueInfoRandomDetectMinThreshold2
   Integer32,
  srvQosSapEgressQueueInfoRandomDetectMinThreshold3
   Integer32,
  srvQosSapEgressQueueInfoRandomDetectMaxThreshold0
   Integer32,
  srvQosSapEgressQueueInfoRandomDetectMaxThreshold1
   Integer32,
  srvQosSapEgressQueueInfoRandomDetectMaxThreshold2
   Integer32,
  srvQosSapEgressQueueInfoRandomDetectMaxThreshold3
   Integer32,
  srvQosSapEgressQueueInfoRandomDetectDropProbability0
   Integer32,
  srvQosSapEgressQueueInfoRandomDetectDropProbability1
   Integer32,
  srvQosSapEgressQueueInfoRandomDetectDropProbability2
   Integer32,
  srvQosSapEgressQueueInfoRandomDetectDropProbability3
   Integer32
 }

srvQosSapEgressQueueInfoRandomDetect              OBJECT-TYPE
    SYNTAX          Integer32 (-1..10)
    MAX-ACCESS      read-write
    STATUS          current
    DESCRIPTION
     "-1: Tail Drop
     0-10: WRED Exponential-Weighted-Moving-Average (EWMA) factor."
    ::= { srvQosSapEgressQueueInfoEntry 1}

srvQosSapEgressQueueInfoTailDropThreshold0        OBJECT-TYPE
    SYNTAX          Integer32(0..24571)
    MAX-ACCESS      read-write
    STATUS          current
    DESCRIPTION
     "Tail drop threshold0."
    ::= { srvQosSapEgressQueueInfoEntry 2}

srvQosSapEgressQueueInfoTailDropThreshold1        OBJECT-TYPE
    SYNTAX          Integer32(1..24572)
    MAX-ACCESS      read-write
    STATUS          current
    DESCRIPTION
     "Tail drop threshold1, should greater than threshold0."
    ::= { srvQosSapEgressQueueInfoEntry 3}

srvQosSapEgressQueueInfoTailDropThreshold2        OBJECT-TYPE
    SYNTAX          Integer32(2..24573)
    MAX-ACCESS      read-write
    STATUS          current
    DESCRIPTION
     "Tail drop threshold2, should greater than threshold1."
    ::= { srvQosSapEgressQueueInfoEntry 4}

srvQosSapEgressQueueInfoTailDropThreshold3        OBJECT-TYPE
    SYNTAX          Integer32(3..24574)
    MAX-ACCESS      read-write
    STATUS          current
    DESCRIPTION
     "Tail drop threshold3, should greater than threshold2."
    ::= { srvQosSapEgressQueueInfoEntry 5}


srvQosSapEgressQueueInfoRandomDetectMinThreshold0     OBJECT-TYPE
    SYNTAX          Integer32(0..24573)
    MAX-ACCESS      read-write
    STATUS          current
    DESCRIPTION
     "Random-detect threshold0's min threshold range."
    ::= { srvQosSapEgressQueueInfoEntry 6}

srvQosSapEgressQueueInfoRandomDetectMinThreshold1     OBJECT-TYPE
    SYNTAX          Integer32(0..24573)
    MAX-ACCESS      read-write
    STATUS          current
    DESCRIPTION
     "Random-detect threshold1's min threshold range."
    ::= { srvQosSapEgressQueueInfoEntry 7}

srvQosSapEgressQueueInfoRandomDetectMinThreshold2     OBJECT-TYPE
    SYNTAX          Integer32(0..24573)
    MAX-ACCESS      read-write
    STATUS          current
    DESCRIPTION
     "Random-detect threshold2's min threshold range."
    ::= { srvQosSapEgressQueueInfoEntry 8}

srvQosSapEgressQueueInfoRandomDetectMinThreshold3     OBJECT-TYPE
    SYNTAX          Integer32(0..24573)
    MAX-ACCESS      read-write
    STATUS          current
    DESCRIPTION
     "Random-detect threshold3's min threshold range."
    ::= { srvQosSapEgressQueueInfoEntry 9}

srvQosSapEgressQueueInfoRandomDetectMaxThreshold0     OBJECT-TYPE
    SYNTAX          Integer32(1..24574)
    MAX-ACCESS      read-write
    STATUS          current
    DESCRIPTION
     "Random-detect threshold0's max threshold range."
    ::= { srvQosSapEgressQueueInfoEntry 10}

srvQosSapEgressQueueInfoRandomDetectMaxThreshold1     OBJECT-TYPE
    SYNTAX          Integer32(1..24574)
    MAX-ACCESS      read-write
    STATUS          current
    DESCRIPTION
     "Random-detect threshold1's max threshold range."
    ::= { srvQosSapEgressQueueInfoEntry 11}

srvQosSapEgressQueueInfoRandomDetectMaxThreshold2     OBJECT-TYPE
    SYNTAX          Integer32(1..24574)
    MAX-ACCESS      read-write
    STATUS          current
    DESCRIPTION
     "Random-detect threshold2's max threshold range."
    ::= { srvQosSapEgressQueueInfoEntry 12}

srvQosSapEgressQueueInfoRandomDetectMaxThreshold3     OBJECT-TYPE
    SYNTAX          Integer32(1..24574)
    MAX-ACCESS      read-write
    STATUS          current
    DESCRIPTION
     "Random-detect threshold3's max threshold range."
    ::= { srvQosSapEgressQueueInfoEntry 13}

srvQosSapEgressQueueInfoRandomDetectDropProbability0     OBJECT-TYPE
    SYNTAX          Integer32(0..65535)
    MAX-ACCESS      read-write
    STATUS          current
    DESCRIPTION
     "Random-detect threshold0 drop probability range."
    ::= { srvQosSapEgressQueueInfoEntry 14}

srvQosSapEgressQueueInfoRandomDetectDropProbability1     OBJECT-TYPE
    SYNTAX          Integer32(0..65535)
    MAX-ACCESS      read-write
    STATUS          current
    DESCRIPTION
     "Random-detect threshold1 drop probability range."
    ::= { srvQosSapEgressQueueInfoEntry 15}

srvQosSapEgressQueueInfoRandomDetectDropProbability2     OBJECT-TYPE
    SYNTAX          Integer32(0..65535)
    MAX-ACCESS      read-write
    STATUS          current
    DESCRIPTION
     "Random-detect threshold2 drop probability range."
    ::= { srvQosSapEgressQueueInfoEntry 16}

srvQosSapEgressQueueInfoRandomDetectDropProbability3     OBJECT-TYPE
    SYNTAX          Integer32(0..65535)
    MAX-ACCESS      read-write
    STATUS          current
    DESCRIPTION
     "Random-detect threshold3 drop probability range."
    ::= { srvQosSapEgressQueueInfoEntry 17}

--"show qos free-queue-info"
srvQosFreeQueueInfoServiceQueueNum       OBJECT-TYPE
    SYNTAX          Integer32
    MAX-ACCESS      read-only
    STATUS          current
    DESCRIPTION
     "Number of queues allocated by each service."
    ::= { srvQosFreeQueueInfoObjects 1}

srvQosFreeQueueInfoMaxSupportQueueNum       OBJECT-TYPE
    SYNTAX          Integer32
    MAX-ACCESS      read-only
    STATUS          current
    DESCRIPTION
     "The maximum support queue number."
    ::= { srvQosFreeQueueInfoObjects 2}

srvQosFreeQueueInfoAllocatedQueueNum       OBJECT-TYPE
    SYNTAX          Integer32
    MAX-ACCESS      read-only
    STATUS          current
    DESCRIPTION
     "The allocated queue number."
    ::= { srvQosFreeQueueInfoObjects 3}

srvQosFreeQueueInfoMaxSupportServiceNum       OBJECT-TYPE
    SYNTAX          Integer32
    MAX-ACCESS      read-only
    STATUS          current
    DESCRIPTION
     "The maximum support service number."
    ::= { srvQosFreeQueueInfoObjects 4}

srvQosFreeQueueInfoAllocatedServiceNum       OBJECT-TYPE
    SYNTAX          Integer32
    MAX-ACCESS      read-only
    STATUS          current
    DESCRIPTION
     "The allocated service number."
    ::= { srvQosFreeQueueInfoObjects 5}

--
-- Node definitions
--

-- Globle Stats enable

qosStatsEnableObjects OBJECT IDENTIFIER    ::= { stats 1 }

qosStatsPolicyEnable         OBJECT-TYPE
    SYNTAX          EnableType
    MAX-ACCESS      read-write
    STATUS          current
    DESCRIPTION
        "The status of policer statistics.
         (1) enable.
         (2) disable."
    ::= { qosStatsEnableObjects 1 }

qosStatsQueueEnable         OBJECT-TYPE
    SYNTAX          EnableType
    MAX-ACCESS      read-write
    STATUS          current
    DESCRIPTION
        "The status of queue statistics.
         (1) enable.
         (2) disable."
    ::= { qosStatsEnableObjects 2 }

-- Globle Stats clear

qosStatsClearStaticsObjects OBJECT IDENTIFIER    ::= { stats 2 }

-- Clear Policy QosStats

qosStatsClearPolicyTable         OBJECT-TYPE
    SYNTAX          SEQUENCE OF QosStatsClearPolicyEntry
    MAX-ACCESS      not-accessible
    STATUS          current
    DESCRIPTION
        "A table of clearing Stats for Policy in a QoS policy applied on the interface."
    ::= { qosStatsClearStaticsObjects 1 }

qosStatsClearPolicyEntry         OBJECT-TYPE
    SYNTAX          QosStatsClearPolicyEntry
    MAX-ACCESS      not-accessible
    STATUS          current
    DESCRIPTION
        "Clear Stats information entry."
    INDEX     {qosStatsClearPolicyIndex }
    ::= { qosStatsClearPolicyTable 1 }

QosStatsClearPolicyEntry    ::=
    SEQUENCE
        {
        qosStatsClearPolicyIndex
            Integer32,
        qosStatsClearPolicyPolicerStats
            QosStatsClear,
        qosStatsClearPolicyAceMatchStats
            QosStatsClear
        }

qosStatsClearPolicyIndex         OBJECT-TYPE
    SYNTAX          Integer32 (10000..20000)
    MAX-ACCESS      not-accessible
    STATUS          current
    DESCRIPTION
        "Policy map entry index. Range 10000~20000."
    ::= { qosStatsClearPolicyEntry 1 }

qosStatsClearPolicyPolicerStats         OBJECT-TYPE
    SYNTAX          QosStatsClear
    MAX-ACCESS      read-write
    STATUS          current
    DESCRIPTION
        "Reset the value of the policer statistics in policy-map.Clear(0)."
    ::= { qosStatsClearPolicyEntry 2 }

qosStatsClearPolicyAceMatchStats         OBJECT-TYPE
    SYNTAX          QosStatsClear
    MAX-ACCESS      read-write
    STATUS          current
    DESCRIPTION
        "Reset the value of the ace-matching statistics in policy-map.Clear(0)."
    ::= { qosStatsClearPolicyEntry 3 }

-- Clearing port-policy QosStats

qosStatsClearPortPolicyTable         OBJECT-TYPE
    SYNTAX          SEQUENCE OF QosStatsClearPortPolicyEntry
    MAX-ACCESS      not-accessible
    STATUS          current
    DESCRIPTION
        "A table of clearing Stats for Policy
             in a QoS PortPolicy applied on the interface."
    ::= { qosStatsClearStaticsObjects 2 }

qosStatsClearPortPolicyEntry         OBJECT-TYPE
    SYNTAX          QosStatsClearPortPolicyEntry
    MAX-ACCESS      not-accessible
    STATUS          current
    DESCRIPTION
        "Clear Stats information entry."
    INDEX         { qosStatsClearPortPolicyIfIndex,
                    qosStatsClearPortPolicyDirection }
    ::= { qosStatsClearPortPolicyTable 1 }

QosStatsClearPortPolicyEntry    ::=
    SEQUENCE
        {
        qosStatsClearPortPolicyIfIndex
                Integer32,
        qosStatsClearPortPolicyDirection
                DirectionType,
        qosStatsClearPortPolicyStats
            QosStatsClear
        }

qosStatsClearPortPolicyIfIndex         OBJECT-TYPE
    SYNTAX          Integer32 (0..65535)
    MAX-ACCESS      not-accessible
    STATUS          current
    DESCRIPTION
        "Interface Index, equal to ifIndex."
    ::= { qosStatsClearPortPolicyEntry 1 }

qosStatsClearPortPolicyDirection         OBJECT-TYPE
    SYNTAX          DirectionType
    MAX-ACCESS      not-accessible
    STATUS          current
    DESCRIPTION
        "Policy direction:
             inbound  (1)
             outbound (2)"
    ::= { qosStatsClearPortPolicyEntry 2 }

qosStatsClearPortPolicyStats         OBJECT-TYPE
    SYNTAX          QosStatsClear
    MAX-ACCESS      read-write
    STATUS          current
    DESCRIPTION
        "Reset the statistics of port policer.Clear(0)."
    ::= { qosStatsClearPortPolicyEntry 3 }

-- Clear Agg policy QosStats

qosStatsClearAggPolicyTable         OBJECT-TYPE
    SYNTAX          SEQUENCE OF QosStatsClearAggPolicyEntry
    MAX-ACCESS      not-accessible
    STATUS          current
    DESCRIPTION
        "A table of clearing Stats for Policy in a QoS AggPolicy applied on the
         interface."
    ::= { qosStatsClearStaticsObjects 3 }

qosStatsClearAggPolicyEntry         OBJECT-TYPE
    SYNTAX          QosStatsClearAggPolicyEntry
    MAX-ACCESS      not-accessible
    STATUS          current
    DESCRIPTION
        "Clear agg policer stats information entry."
    INDEX     { qosStatsClearAggPolicyIndex  }
    ::= { qosStatsClearAggPolicyTable 1 }

QosStatsClearAggPolicyEntry    ::=
    SEQUENCE
        {
        qosStatsClearAggPolicyIndex
                Integer32,
        qosStatsClearAggPolicyStats
            QosStatsClear
        }

qosStatsClearAggPolicyIndex         OBJECT-TYPE
    SYNTAX          Integer32 (0..65535)
    MAX-ACCESS      not-accessible
    STATUS          current
    DESCRIPTION
        "Index of aggregate-policer."
    ::= { qosStatsClearAggPolicyEntry 1 }
          
qosStatsClearAggPolicyStats         OBJECT-TYPE
    SYNTAX          QosStatsClear
    MAX-ACCESS      read-write
    STATUS          current
    DESCRIPTION
        "Reset the value of the Stats.Clear(0)."
    ::= { qosStatsClearAggPolicyEntry 2 }

-- Clear queue QosStats

qosStatsClearQueueTable         OBJECT-TYPE
    SYNTAX          SEQUENCE OF QosStatsClearQueueEntry
    MAX-ACCESS      not-accessible
    STATUS          current
    DESCRIPTION
        "A table of clearing Stats for Policy in a QoS Queue applied on the 
         interface."
    ::= { qosStatsClearStaticsObjects 4 }

qosStatsClearQueueEntry         OBJECT-TYPE
    SYNTAX          QosStatsClearQueueEntry
    MAX-ACCESS      not-accessible
    STATUS          current
    DESCRIPTION
        "Clear Stats information entry."
    INDEX     { qosStatsClearQueueifIndex,
                qosStatsClearQueueId}
    ::= { qosStatsClearQueueTable 1 }

QosStatsClearQueueEntry    ::=
    SEQUENCE
        { 
            qosStatsClearQueueifIndex
                Integer32,
            qosStatsClearQueueId
                IfQueueId,
            qosStatsClearQueueStats
                QosStatsClear
        }
        
qosStatsClearQueueifIndex         OBJECT-TYPE
    SYNTAX          Integer32 (0..65535)
    MAX-ACCESS      not-accessible
    STATUS          current
    DESCRIPTION
        "Interface Index, equal to ifIndex."
    ::= { qosStatsClearQueueEntry 1 } 

qosStatsClearQueueId         OBJECT-TYPE
    SYNTAX          IfQueueId
    MAX-ACCESS      not-accessible
    STATUS          current
    DESCRIPTION
        "Interface queue id."
    ::= { qosStatsClearQueueEntry 2 } 

qosStatsClearQueueStats         OBJECT-TYPE
    SYNTAX          QosStatsClear
    MAX-ACCESS      read-write
    STATUS          current
    DESCRIPTION
        "Reset the value of the Stats.Clear(0)."
    ::= { qosStatsClearQueueEntry 3 }
                                                                    
-- Running Stats information

qosStatsRunStaticsObjects OBJECT IDENTIFIER    ::= { stats 3 }

-- Policy Stats,policy Running Stats information

qosStatsCbPolicyRunInfoTable         OBJECT-TYPE
    SYNTAX          SEQUENCE OF QosStatsCbPolicyRunInfoEntry
    MAX-ACCESS      not-accessible
    STATUS          current
    DESCRIPTION
        "A table of Running Stats for Policy in a QoS policy applied on the interface."
    ::= { qosStatsRunStaticsObjects 1 }

qosStatsCbPolicyRunInfoEntry         OBJECT-TYPE
    SYNTAX          QosStatsCbPolicyRunInfoEntry
    MAX-ACCESS      not-accessible
    STATUS          current
    DESCRIPTION
        "Policy Stats information entry."
    INDEX          { qosStatsCbPolicyIfIndex,        
                     qosStatsCbPolicyDirection,
                     qosStatsPolicyClassIndex }
    ::= { qosStatsCbPolicyRunInfoTable 1 }

QosStatsCbPolicyRunInfoEntry    ::=
    SEQUENCE
        { 
        qosStatsCbPolicyIfIndex
            Integer32,
        qosStatsCbPolicyDirection
            DirectionType,
        qosStatsPolicyClassIndex
            Integer32,    
        qosStatsPolicyGreenPackets
            Counter64,
        qosStatsPolicyGreenBytes
            Counter64,
        qosStatsPolicyRedPackets
            Counter64,
        qosStatsPolicyRedBytes
            Counter64,
        qosStatsPolicyYellowPackets
            Counter64,
        qosStatsPolicyYellowBytes
            Counter64,
        qosStatsPolicyClassBasedPkts
            Counter64,
        qosStatsPolicyClassBasedBytes
            Counter64
        }

qosStatsCbPolicyIfIndex         OBJECT-TYPE
    SYNTAX          Integer32 (0..65535)
    MAX-ACCESS      not-accessible
    STATUS          current
    DESCRIPTION
        "Interface Index, equal to ifIndex."
    ::= { qosStatsCbPolicyRunInfoEntry 1 }

qosStatsCbPolicyDirection         OBJECT-TYPE
    SYNTAX          DirectionType
    MAX-ACCESS      not-accessible
    STATUS          current
    DESCRIPTION
        "Policy direction:
             inbound (1)
             outbound (2)
        "
    ::= { qosStatsCbPolicyRunInfoEntry 2 }
        
qosStatsPolicyClassIndex         OBJECT-TYPE
    SYNTAX          Integer32 (0..65535)
    MAX-ACCESS      not-accessible
    STATUS          current
    DESCRIPTION
        "PolicyClass Index in a QoS policy."
    ::= { qosStatsCbPolicyRunInfoEntry 3 }

qosStatsPolicyGreenPackets         OBJECT-TYPE
    SYNTAX          Counter64
    MAX-ACCESS      read-only
    STATUS          current
    DESCRIPTION
        "Number of green packets."
    ::= { qosStatsCbPolicyRunInfoEntry 4 }

qosStatsPolicyGreenBytes         OBJECT-TYPE
    SYNTAX          Counter64
    MAX-ACCESS      read-only
    STATUS          current
    DESCRIPTION
        "Number of green bytes."
    ::= { qosStatsCbPolicyRunInfoEntry 5 }

qosStatsPolicyRedPackets         OBJECT-TYPE
    SYNTAX          Counter64
    MAX-ACCESS      read-only
    STATUS          current
    DESCRIPTION
        "Number of red packets."
    ::= { qosStatsCbPolicyRunInfoEntry 6 }

qosStatsPolicyRedBytes         OBJECT-TYPE
    SYNTAX          Counter64
    MAX-ACCESS      read-only
    STATUS          current
    DESCRIPTION
        "Number of red bytes."
    ::= { qosStatsCbPolicyRunInfoEntry 7 }

qosStatsPolicyYellowPackets         OBJECT-TYPE
    SYNTAX          Counter64
    MAX-ACCESS      read-only
    STATUS          current
    DESCRIPTION
        "Number of yellow packets."
    ::= { qosStatsCbPolicyRunInfoEntry 8 }

qosStatsPolicyYellowBytes         OBJECT-TYPE
    SYNTAX          Counter64
    MAX-ACCESS      read-only
    STATUS          current
    DESCRIPTION
        "Number of yellow bytes."
    ::= { qosStatsCbPolicyRunInfoEntry 9 }
    
qosStatsPolicyClassBasedPkts         OBJECT-TYPE
    SYNTAX          Counter64
    MAX-ACCESS      read-only
    STATUS          current
    DESCRIPTION
        "Number of policy class matching packets."
    ::= { qosStatsCbPolicyRunInfoEntry 10 }

qosStatsPolicyClassBasedBytes         OBJECT-TYPE
    SYNTAX          Counter64
    MAX-ACCESS      read-only
    STATUS          current
    DESCRIPTION
        "Number of policy class matching bytes."
    ::= { qosStatsCbPolicyRunInfoEntry 11 }

-- Port policy: policy Running Stats information on port

        
qosStatsPortPolicyRunInfoTable         OBJECT-TYPE
    SYNTAX          SEQUENCE OF QosStatsPortPolicyRunInfoEntry
    MAX-ACCESS      not-accessible
    STATUS          current
    DESCRIPTION
        "A table of Running Stats in a QoS policy applied on the port."
    ::= { qosStatsRunStaticsObjects 2 }

qosStatsPortPolicyRunInfoEntry         OBJECT-TYPE
    SYNTAX          QosStatsPortPolicyRunInfoEntry
    MAX-ACCESS      not-accessible
    STATUS          current
    DESCRIPTION
        "Policy Stats information entry."
   INDEX          { qosStatsCbPolicyIfIndex,        
                    qosStatsCbPolicyDirection }
    ::= { qosStatsPortPolicyRunInfoTable 1 }

QosStatsPortPolicyRunInfoEntry    ::=
    SEQUENCE
        {  
            qosStatsPortPolicyIfIndex
                Integer32,
            qosStatsPortPolicyDirection
                DirectionType,
            qosStatsPortPolicyGreenPackets
                Counter64,
            qosStatsPortPolicyGreenBytes
                Counter64,
            qosStatsPortPolicyRedPackets
                Counter64,
            qosStatsPortPolicyRedBytes
                Counter64,
            qosStatsPortPolicyYellowPackets
                Counter64,
            qosStatsPortPolicyYellowBytes
                Counter64
        }

qosStatsPortPolicyIfIndex         OBJECT-TYPE
    SYNTAX          Integer32
    MAX-ACCESS      not-accessible
    STATUS          current
    DESCRIPTION
        "Interface Index, equal to ifIndex."
    ::= { qosStatsPortPolicyRunInfoEntry 1 }

qosStatsPortPolicyDirection         OBJECT-TYPE
    SYNTAX          DirectionType
    MAX-ACCESS      not-accessible
    STATUS          current
    DESCRIPTION
        "Policy direction:
             inbound (1)
             outbound (2)
        "
    ::= { qosStatsPortPolicyRunInfoEntry 2 }

qosStatsPortPolicyGreenPackets         OBJECT-TYPE
    SYNTAX          Counter64
    MAX-ACCESS      read-only
    STATUS          current
    DESCRIPTION
        "Number of green packets."
    ::= { qosStatsPortPolicyRunInfoEntry 3 }

qosStatsPortPolicyGreenBytes         OBJECT-TYPE
    SYNTAX          Counter64
    MAX-ACCESS      read-only
    STATUS          current
    DESCRIPTION
        "Number of green bytes."
    ::= { qosStatsPortPolicyRunInfoEntry 4 }

qosStatsPortPolicyRedPackets         OBJECT-TYPE
    SYNTAX          Counter64
    MAX-ACCESS      read-only
    STATUS          current
    DESCRIPTION
        "Number of red packets."
    ::= { qosStatsPortPolicyRunInfoEntry 5 }

qosStatsPortPolicyRedBytes         OBJECT-TYPE
    SYNTAX          Counter64
    MAX-ACCESS      read-only
    STATUS          current
    DESCRIPTION
        "Number of red bytes."
    ::= { qosStatsPortPolicyRunInfoEntry 6 }

qosStatsPortPolicyYellowPackets         OBJECT-TYPE
    SYNTAX          Counter64
    MAX-ACCESS      read-only
    STATUS          current
    DESCRIPTION
        "Number of yellow packets."
    ::= { qosStatsPortPolicyRunInfoEntry 7 }

qosStatsPortPolicyYellowBytes         OBJECT-TYPE
    SYNTAX          Counter64
    MAX-ACCESS      read-only
    STATUS          current
    DESCRIPTION
        "Number of yellow bytes."
    ::= { qosStatsPortPolicyRunInfoEntry 8 }

-- Queue Stats

qosStatsIfQueueRunInfoTable         OBJECT-TYPE
    SYNTAX          SEQUENCE OF QosStatsIfQueueRunInfoEntry
    MAX-ACCESS      not-accessible
    STATUS          current
    DESCRIPTION
        "A table of Running Stats for queue
        in a QoS policy applied on the interface."
    ::= { qosStatsRunStaticsObjects 3 }

qosStatsIfQueueRunInfoEntry         OBJECT-TYPE
    SYNTAX          QosStatsIfQueueRunInfoEntry
    MAX-ACCESS      not-accessible
    STATUS          current
    DESCRIPTION
        "Queue Stats entry."
    INDEX          { qosStatsQueueIfIndex,
                qosStatsQueueID }
    ::= { qosStatsIfQueueRunInfoTable 1 }

QosStatsIfQueueRunInfoEntry    ::=
    SEQUENCE
        {
            qosStatsQueueIfIndex
                Integer32,
            qosStatsQueueID
                Integer32,
            qosStatsIfQueueTransmittedPackets
                Counter64,
            qosStatsIfQueueTransmittedBytes
                Counter64,
            qosStatsIfQueueDropPackets
                Counter64,
            qosStatsIfQueueDropBytes
                Counter64
        }

qosStatsQueueIfIndex         OBJECT-TYPE
    SYNTAX          Integer32 (0..65535)
    MAX-ACCESS      not-accessible
    STATUS          current
    DESCRIPTION
        "Interface Index, equal to ifIndex."
    ::= { qosStatsIfQueueRunInfoEntry 1 }

qosStatsQueueID         OBJECT-TYPE
    SYNTAX          Integer32 (0..15)
    MAX-ACCESS      not-accessible
    STATUS          current
    DESCRIPTION
        "Queue ID. Range <0-7>."
    ::= { qosStatsIfQueueRunInfoEntry 2 }

qosStatsIfQueueTransmittedPackets         OBJECT-TYPE
    SYNTAX          Counter64
    MAX-ACCESS      read-only
    STATUS          current
    DESCRIPTION
        "Number of packets enqueued."
    ::= { qosStatsIfQueueRunInfoEntry 3 }

qosStatsIfQueueTransmittedBytes         OBJECT-TYPE
    SYNTAX          Counter64
    MAX-ACCESS      read-only
    STATUS          current
    DESCRIPTION
        "Number of bytes enqueued."
    ::= { qosStatsIfQueueRunInfoEntry 4 }

qosStatsIfQueueDropPackets         OBJECT-TYPE
    SYNTAX          Counter64
    MAX-ACCESS      read-only
    STATUS          current
    DESCRIPTION
        "Number of packets discarded when enqueued by tail-drop/wred method. It's zero if the system does not support queue drop statistics."
    ::= { qosStatsIfQueueRunInfoEntry 5 }

qosStatsIfQueueDropBytes         OBJECT-TYPE
    SYNTAX          Counter64
    MAX-ACCESS      read-only
    STATUS          current
    DESCRIPTION
        "Number of bytes discarded when enqueued by tail-drop/wred method.
         It's zero if the system does not support queue drop statistics."
    ::= { qosStatsIfQueueRunInfoEntry 6 }

qosStatsCbPolicyAceBasedRunInfoTable         OBJECT-TYPE
    SYNTAX          SEQUENCE OF QosStatsCbPolicyAceBasedRunInfoEntry
    MAX-ACCESS      not-accessible
    STATUS          current
    DESCRIPTION
        "A table of Running Stats for matching QoS policy Ace applied on the interface. The matching ace statistics is only for match-any class-map in policy-map"
    ::= { qosStatsRunStaticsObjects 4 }

qosStatsCbPolicyAceBasedRunInfoEntry         OBJECT-TYPE
    SYNTAX          QosStatsCbPolicyAceBasedRunInfoEntry
    MAX-ACCESS      not-accessible
    STATUS          current
    DESCRIPTION
        "Policy Stats information entry."
    INDEX          { qosStatsCbAceBasedIfIndex,
                     qosStatsCbAceBasedDirection,
                     qosStatsCbAceBasedPolicyClassIndex,
                     qosStatsCbAceBasedMatchRuleIndex,
                     qosStatsCbAceBasedAclGroupRuleIndex }
    ::= { qosStatsCbPolicyAceBasedRunInfoTable 1 }

QosStatsCbPolicyAceBasedRunInfoEntry    ::=
    SEQUENCE
        {
        qosStatsCbAceBasedIfIndex
            Integer32,
        qosStatsCbAceBasedDirection
            DirectionType,
        qosStatsCbAceBasedPolicyClassIndex
            Integer32,
        qosStatsCbAceBasedMatchRuleIndex
            Integer32,
        qosStatsCbAceBasedAclGroupRuleIndex
            Integer32,
        qosStatsCbAceBasedPkts
            Counter64,
        qosStatsCbAceBasedBytes
            Counter64
        }

qosStatsCbAceBasedIfIndex         OBJECT-TYPE
    SYNTAX          Integer32 (0..65535)
    MAX-ACCESS      not-accessible
    STATUS          current
    DESCRIPTION
        "Interface Index, equal to ifIndex."
    ::= { qosStatsCbPolicyAceBasedRunInfoEntry 1 }

qosStatsCbAceBasedDirection         OBJECT-TYPE
    SYNTAX          DirectionType
    MAX-ACCESS      not-accessible
    STATUS          current
    DESCRIPTION
        "Policy direction:
             inbound (1)
             outbound (2)
        "
    ::= { qosStatsCbPolicyAceBasedRunInfoEntry 2 }

qosStatsCbAceBasedPolicyClassIndex         OBJECT-TYPE
    SYNTAX          Integer32 (0..65535)
    MAX-ACCESS      not-accessible
    STATUS          current
    DESCRIPTION
        "PolicyClass index in policy-map."
    ::= { qosStatsCbPolicyAceBasedRunInfoEntry 3 }

qosStatsCbAceBasedMatchRuleIndex         OBJECT-TYPE
    SYNTAX          Integer32(0..65535)
    MAX-ACCESS      not-accessible
    STATUS          current
    DESCRIPTION
        "Match rule index in Class-map."
    ::= { qosStatsCbPolicyAceBasedRunInfoEntry 4 }

qosStatsCbAceBasedAclGroupRuleIndex         OBJECT-TYPE
    SYNTAX          Integer32(1..2147483646)
    MAX-ACCESS      not-accessible
    STATUS          current
    DESCRIPTION
        "Rule index(sequence num in cli) in acl Group. "
    ::= { qosStatsCbPolicyAceBasedRunInfoEntry 5 }

qosStatsCbAceBasedPkts         OBJECT-TYPE
    SYNTAX          Counter64
    MAX-ACCESS      read-only
    STATUS          current
    DESCRIPTION
        "Number of packets matching ace in policy-map."
    ::= { qosStatsCbPolicyAceBasedRunInfoEntry 6 }

qosStatsCbAceBasedBytes         OBJECT-TYPE
    SYNTAX          Counter64
    MAX-ACCESS      read-only
    STATUS          current
    DESCRIPTION
        "Bytes of packets matching ace in policy-map."
    ::= { qosStatsCbPolicyAceBasedRunInfoEntry 7 }

-- Agg Policy Stats,policy Running Stats information


qosStatsAggPolicyRunInfoTable         OBJECT-TYPE
    SYNTAX          SEQUENCE OF QosStatsAggPolicyRunInfoEntry
    MAX-ACCESS      not-accessible
    STATUS          current
    DESCRIPTION
        "A table of Running Stats in a QoS aggregate policy applied on the interface."
    ::= { qosStatsRunStaticsObjects 5 }

qosStatsAggPolicyRunInfoEntry         OBJECT-TYPE
    SYNTAX          QosStatsAggPolicyRunInfoEntry
    MAX-ACCESS      not-accessible
    STATUS          current
    DESCRIPTION
        "Aggregate Policy Stats information entry."
   INDEX          { qosStatsAggPolicyIndex }
    ::= { qosStatsAggPolicyRunInfoTable 1 }

QosStatsAggPolicyRunInfoEntry    ::=
    SEQUENCE
        {
            qosStatsAggPolicyIndex
                Integer32,
            qosStatsAggPolicyRedPackets
                Counter64,
            qosStatsAggPolicyRedBytes
                Counter64,
            qosStatsAggPolicyGreenPackets
                Counter64,
            qosStatsAggPolicyGreenBytes
                Counter64,
            qosStatsAggPolicyYellowPackets
                Counter64,
            qosStatsAggPolicyYellowBytes
                Counter64
        }

qosStatsAggPolicyIndex         OBJECT-TYPE
    SYNTAX          Integer32 (0..65535)
    MAX-ACCESS      not-accessible
    STATUS          current
    DESCRIPTION
        "Index of aggregate-policer."
    ::= { qosStatsAggPolicyRunInfoEntry 1 }

qosStatsAggPolicyRedPackets         OBJECT-TYPE
    SYNTAX          Counter64
    MAX-ACCESS      read-only
    STATUS          current
    DESCRIPTION
        "Number of red packets."
    ::= { qosStatsAggPolicyRunInfoEntry 2 }

qosStatsAggPolicyRedBytes         OBJECT-TYPE
    SYNTAX          Counter64
    MAX-ACCESS      read-only
    STATUS          current
    DESCRIPTION
        "Number of red bytes."
    ::= { qosStatsAggPolicyRunInfoEntry 3 }

qosStatsAggPolicyGreenPackets         OBJECT-TYPE
    SYNTAX          Counter64
    MAX-ACCESS      read-only
    STATUS          current
    DESCRIPTION
        "Number of green packets."
    ::= { qosStatsAggPolicyRunInfoEntry 4 }

qosStatsAggPolicyGreenBytes         OBJECT-TYPE
    SYNTAX          Counter64
    MAX-ACCESS      read-only
    STATUS          current
    DESCRIPTION
        "Number of green bytes."
    ::= { qosStatsAggPolicyRunInfoEntry 5 }

qosStatsAggPolicyYellowPackets         OBJECT-TYPE
    SYNTAX          Counter64
    MAX-ACCESS      read-only
    STATUS          current
    DESCRIPTION
        "Number of yellow packets."
    ::= { qosStatsAggPolicyRunInfoEntry 6 }

qosStatsAggPolicyYellowBytes         OBJECT-TYPE
    SYNTAX          Counter64
    MAX-ACCESS      read-only
    STATUS          current
    DESCRIPTION
        "Number of yellow bytes."
    ::= { qosStatsAggPolicyRunInfoEntry 7 }




-- Sub Module: IGSP

EnabledStatus::= TEXTUAL-CONVENTION
    STATUS          current
    DESCRIPTION
        "A simpleStatus value for the object."
    SYNTAX          INTEGER { enabled(1), disabled(0) }


-- ==================================================================
--
-- ======================= definition begin =========================
--
-- ==================================================================

    lswIgmpsnoopingMibObject OBJECT IDENTIFIER    ::= {   igsp 1  }
    lswIgmpsnoopingTrap OBJECT IDENTIFIER    ::= {   igsp 2  }
igmpSnoopingStatus        OBJECT-TYPE
    SYNTAX          INTEGER{enable(1),disable(2)}
    MAX-ACCESS      read-write
    STATUS          current
    DESCRIPTION
        "Configure to enable IGMP Snooping.
        enable(1)
        disable(2)"
    ::= { lswIgmpsnoopingMibObject  1 }

igmpSnoopingFastLeaveStatus         OBJECT-TYPE
    SYNTAX          INTEGER{enable(1),disable(2)}
    MAX-ACCESS      read-write
    STATUS          current
    DESCRIPTION
        "Configure to enable IGMP Snooping Fast Leave.
        enable(1)
        disable(2)"
    ::= { lswIgmpsnoopingMibObject  2 }

igmpSnoopingVersion            OBJECT-TYPE
    SYNTAX          INTEGER   (1..3)
    MAX-ACCESS      read-write
    STATUS          current
    DESCRIPTION        "Configure to set IGMP Snooping Version."
    ::= { lswIgmpsnoopingMibObject  3 }

igmpSnoopingMaxMemberNumber            OBJECT-TYPE
    SYNTAX          INTEGER   (1..8192)
    MAX-ACCESS      read-write
    STATUS          current
    DESCRIPTION        "Configure the max member number."
    ::= { lswIgmpsnoopingMibObject  4 }

igmpSnoopingDiscardUnknownstatus         OBJECT-TYPE
    SYNTAX          INTEGER{enable(1),disable(2)}
    MAX-ACCESS      read-write
    STATUS          current
    DESCRIPTION
        "Configure to enable IGMP Snooping Discard unknown multicast traffic.
        enable(1)
        disable(2)"
    ::= { lswIgmpsnoopingMibObject  5 }

igmpSnoopingReportSuppressionStatus         OBJECT-TYPE
    SYNTAX          INTEGER{enable(1),disable(2)}
    MAX-ACCESS      read-write
    STATUS          current
    DESCRIPTION
        "Configure to enable IGMP Snooping Report-Suppression.
        enable(1)
        disable(2)"
    ::= { lswIgmpsnoopingMibObject  6 }

igmpSnoopingLastMemberQueryInterval            OBJECT-TYPE
    SYNTAX          INTEGER   (1000..25500)
    MAX-ACCESS      read-write
    STATUS          current
    DESCRIPTION        "Configure to set IGMP Snooping Last Member Query Interval. Interval range 1000~25500."
    ::= { lswIgmpsnoopingMibObject  7 }

igmpSnoopingQueryInterval            OBJECT-TYPE
    SYNTAX          INTEGER   (2..18000)
    MAX-ACCESS      read-write
    STATUS          current
    DESCRIPTION        "Configure to set IGMP Snooping Query Interval.Must more than query max response time. Interval range 2~18000."
    ::= { lswIgmpsnoopingMibObject  8 }

igmpSnoopingQueryMaxResponseTime            OBJECT-TYPE
    SYNTAX          INTEGER   (1..25)
    MAX-ACCESS      read-write
    STATUS          current
    DESCRIPTION        "Configure to set IGMP Snooping Query Max Response Time.Time range 1~25."
    ::= { lswIgmpsnoopingMibObject  9 }
	
igmpSnoopingVlanTable         OBJECT-TYPE
    SYNTAX          SEQUENCE OF IgmpSnoopingVlanEntry
    MAX-ACCESS      not-accessible
    STATUS          current
    DESCRIPTION
        "The table contains, one entry per vlan, 
             infomation about the IGMP Snooping."
    ::= { lswIgmpsnoopingMibObject 10 }

igmpSnoopingVlanEntry         OBJECT-TYPE
    SYNTAX          IgmpSnoopingVlanEntry
    MAX-ACCESS      not-accessible
    STATUS          current
    DESCRIPTION
        "Entry containing information about the
                    IGMP Snooping on vlan."
    INDEX     { igmpSnoopingVlanID }
    ::= { igmpSnoopingVlanTable 1 }

IgmpSnoopingVlanEntry    ::=    SEQUENCE {
        igmpSnoopingVlanID                         
            Integer32,
        igmpSnoopingVlanEnabled                    
            EnabledStatus,
        igmpSnoopingVlanFastLeaveStatus 
            EnabledStatus,
        igmpSnoopingVlanReportSuppressionStatus 
            EnabledStatus ,        
        igmpSnoopingVlanVersion                    
            INTEGER,
        igmpSnoopingVlanMaxMemberNumber   
            INTEGER,         
        igmpSnoopingVlanDiscardUnknownStatus       
            EnabledStatus,
        igmpSnoopingVlanGroupAccesslist            
            OCTET STRING,
        igmpSnoopingVlanLastMemberQueryInterval    
            INTEGER,
        igmpSnoopingVlanQuerier                    
            EnabledStatus ,
        igmpSnoopingVlanQuerierOperationalAddress  
            IpAddress,
        igmpSnoopingVlanQuerierConfigureAddress    
            IpAddress,
        igmpSnoopingVlanQuerierTimeout             
            INTEGER,
        igmpSnoopingVlanQueryInterval              
            INTEGER,
        igmpSnoopingVlanQueryMaxResponseTime       
            INTEGER,
        igmpSnoopingVlanStatusGrpJoinsCnt          
            Counter32,
        igmpSnoopingVlanStatusGrpLeavesCnt         
            Counter32,
        igmpSnoopingVlanStatusV1QuerierWCnt        
            Counter32,
        igmpSnoopingVlanStatusV2QuerierWCnt        
            Counter32,        
        igmpSnoopingVlanStatusResetCounters        
            INTEGER,
        igmpSnoopingVlanGrpNum
            INTEGER,
        igmpSnoopingVlanElectedQuerierAddress  
            IpAddress
        }
        
igmpSnoopingVlanID         OBJECT-TYPE
    SYNTAX          Integer32(1..4094)
    MAX-ACCESS      not-accessible
    STATUS          current
    DESCRIPTION
        "An index uniquely identifies the VLAN id which IGMP 
             snooping is enabled or disabled."
    ::= { igmpSnoopingVlanEntry 1 }

igmpSnoopingVlanEnabled         OBJECT-TYPE
    SYNTAX          INTEGER{enable(1),disable(2)}
    MAX-ACCESS      read-write
    STATUS          current
    DESCRIPTION
        "Indicating whether IGMP snooping is enabled on this VLAN.
        enable(1)
        disable(2)"
       -- DEFVAL     { enabled }
    ::= { igmpSnoopingVlanEntry 2 }
        
igmpSnoopingVlanFastLeaveStatus         OBJECT-TYPE
    SYNTAX          INTEGER{enable(1),disable(2)}
    MAX-ACCESS      read-write
    STATUS          current
    DESCRIPTION
        "Configure to enable IGMP Snooping Fast Leave on VLAN,
        enable(1)
        disable(2)."
    ::= { igmpSnoopingVlanEntry 3 }        

igmpSnoopingVlanReportSuppressionStatus         OBJECT-TYPE
    SYNTAX          INTEGER{enable(1),disable(2)}
    MAX-ACCESS      read-write
    STATUS          current
    DESCRIPTION
        "Configure to enable IGMP Snooping Report-Suppression on VLAN.
        enable(1)
        disable(2)"
    ::= { igmpSnoopingVlanEntry 4 }    
                
igmpSnoopingVlanVersion         OBJECT-TYPE
    SYNTAX          INTEGER   (1..3)
    MAX-ACCESS      read-write
    STATUS          current
    DESCRIPTION
        "Configure to set IGMP Snooping Version on VLAN.Version range 1~3."
    ::= { igmpSnoopingVlanEntry 5 }      

igmpSnoopingVlanMaxMemberNumber         OBJECT-TYPE
    SYNTAX          INTEGER   (1..8192)
    MAX-ACCESS      read-write
    STATUS          current
    DESCRIPTION
        "Configure the max member number on VLAN.Range 1~8192."
    ::= { igmpSnoopingVlanEntry 6 }    

    igmpSnoopingVlanDiscardUnknownStatus OBJECT-TYPE
    SYNTAX          INTEGER{enable(1),disable(2)}
    MAX-ACCESS      read-write
    STATUS          current
    DESCRIPTION
        "Configure to enable IGMP Snooping Discard unknown multicast traffic on VLAN.
        enable(1)
        disable(2)"
    ::= { igmpSnoopingVlanEntry 7 }    

igmpSnoopingVlanGroupAccesslist         OBJECT-TYPE
    SYNTAX          OCTET STRING (SIZE (0..20))
    MAX-ACCESS      read-write
    STATUS          current
    DESCRIPTION
        "Configure the IGMP Snooping Group Acess-list on VLAN."
    ::= { igmpSnoopingVlanEntry 8 }    
                
igmpSnoopingVlanLastMemberQueryInterval         OBJECT-TYPE
    SYNTAX          INTEGER   (1000..25500)
    MAX-ACCESS      read-write
    STATUS          current
    DESCRIPTION
        "Configure to set IGMP Snooping Last Member Query Interval on VLAN. Interval range 1000~25500."
    ::= { igmpSnoopingVlanEntry 10 } 
        
igmpSnoopingVlanQuerier         OBJECT-TYPE
    SYNTAX          EnabledStatus
    MAX-ACCESS      read-write
    STATUS          current
    DESCRIPTION
        "Configure to Enable or Disable IGMP Snooping Querier on VLAN.
        enable(1)
        disable(2)"
    ::= { igmpSnoopingVlanEntry 11 } 

igmpSnoopingVlanQuerierOperationalAddress         OBJECT-TYPE
    SYNTAX          IpAddress
    MAX-ACCESS      read-only
    STATUS          current
    DESCRIPTION
        "Configure to get IGMP Snooping Querier Operational Adress on VLAN."
    ::= { igmpSnoopingVlanEntry 12 } 
        
igmpSnoopingVlanQuerierConfigureAddress         OBJECT-TYPE
    SYNTAX          IpAddress
    MAX-ACCESS      read-write
    STATUS          current
    DESCRIPTION
        "Configure to set IGMP Snooping Querier Configure Adress on VLAN."
    ::= { igmpSnoopingVlanEntry 13 }         
        
igmpSnoopingVlanQuerierTimeout         OBJECT-TYPE
    SYNTAX          INTEGER   (60..300)
    MAX-ACCESS      read-write
    STATUS          current
    DESCRIPTION
        "Configure to set IGMP Snooping Querier Timeout value on VLAN. Timeout range 60~300. "
    ::= { igmpSnoopingVlanEntry 14 }         
        
igmpSnoopingVlanQueryInterval         OBJECT-TYPE
    SYNTAX          INTEGER   (2..18000)
    MAX-ACCESS      read-write
    STATUS          current
    DESCRIPTION
        "Configure to set IGMP Snooping Query Interval on VLAN. Query interval should be greater than Query Response Interval. Interval range 2~18000."
    ::= { igmpSnoopingVlanEntry 15 }   
        
igmpSnoopingVlanQueryMaxResponseTime         OBJECT-TYPE
    SYNTAX          INTEGER   (1..25)
    MAX-ACCESS      read-write
    STATUS          current
    DESCRIPTION
        "Configure to set IGMP Snooping Query Max Response Time on VLAN."
    ::= { igmpSnoopingVlanEntry 16 }   

igmpSnoopingVlanStatusGrpJoinsCnt         OBJECT-TYPE
    SYNTAX          Counter32   
    MAX-ACCESS      read-only
    STATUS          obsolete
    DESCRIPTION
        "Configure to get IGMP Snooping Group Joins Count on VLAN."
    ::= { igmpSnoopingVlanEntry 17 }  
        
igmpSnoopingVlanStatusGrpLeavesCnt         OBJECT-TYPE
    SYNTAX          Counter32   
    MAX-ACCESS      read-only
    STATUS          obsolete
    DESCRIPTION
        "Configure to get IGMP Snooping Group Leaves Count on VLAN."
    ::= { igmpSnoopingVlanEntry 18 }          

igmpSnoopingVlanStatusV1QuerierWCnt         OBJECT-TYPE
    SYNTAX          Counter32   
    MAX-ACCESS      read-only
    STATUS          obsolete
    DESCRIPTION
        "Configure to get IGMP Snooping Group V1-Querier Warnings Count on VLAN."
    ::= { igmpSnoopingVlanEntry 19 }          

igmpSnoopingVlanStatusV2QuerierWCnt         OBJECT-TYPE
    SYNTAX          Counter32   
    MAX-ACCESS      read-only
    STATUS          obsolete
    DESCRIPTION
        "Configure to get IGMP Snooping Group V2-Querier Warnings Count on VLAN."
    ::= { igmpSnoopingVlanEntry 20 }  

igmpSnoopingVlanStatusResetCounters         OBJECT-TYPE
    SYNTAX          INTEGER {
                           reset(1)
                            }  
    MAX-ACCESS      read-write
    STATUS          obsolete
    DESCRIPTION
        "Configure to reset IGMP SnoopingStatus Counters on VLAN.
        1 reset."
    ::= { igmpSnoopingVlanEntry 21 }  

igmpSnoopingVlanGrpNum         OBJECT-TYPE
    SYNTAX          INTEGER  
    MAX-ACCESS      read-only
    STATUS          current
    DESCRIPTION
        "Configure to get IGMP Snooping group number on VLAN."
    ::= { igmpSnoopingVlanEntry 22 }
	
igmpSnoopingVlanElectedQuerierAddress         OBJECT-TYPE
    SYNTAX          IpAddress
    MAX-ACCESS      read-only
    STATUS          current
    DESCRIPTION
        "Configure to get IGMP Snooping Elected Querier Adress on VLAN."
    ::= { igmpSnoopingVlanEntry 23 }
	
igmpSnoopingMrouterPortTable         OBJECT-TYPE
    SYNTAX          SEQUENCE OF IgmpSnoopingMrouterPortEntry
    MAX-ACCESS      not-accessible
    STATUS          current
    DESCRIPTION
        "A table that contains information about igmp snooping mrouter port list
			per vlan."
    ::= { lswIgmpsnoopingMibObject 11 }
    
igmpSnoopingMrouterPortEntry         OBJECT-TYPE
    SYNTAX          IgmpSnoopingMrouterPortEntry
    MAX-ACCESS      not-accessible
    STATUS          current
    DESCRIPTION
        "Information about IGMP Snooping Mrouter Port on VLAN."
    INDEX           { igmpSnoopingVlanid, igmpSnoopingmrouterPort}
    ::= { igmpSnoopingMrouterPortTable 1 }
    
IgmpSnoopingMrouterPortEntry    ::=
    SEQUENCE {
			igmpSnoopingVlanid
                Integer32,
			igmpSnoopingmrouterPort
                Integer32,
            igmpSnoopingmrouterPortRowStatus 
RowStatus 
        }

igmpSnoopingVlanid         OBJECT-TYPE
    SYNTAX          Integer32(1..4094)
    MAX-ACCESS      not-accessible
    STATUS          current
    DESCRIPTION
        "The VLAN identifier of this mrouter port."
    ::= { igmpSnoopingMrouterPortEntry 1 }
    
igmpSnoopingmrouterPort         OBJECT-TYPE
    SYNTAX          Integer32 (1..1152)
    MAX-ACCESS      not-accessible
    STATUS          current
    DESCRIPTION
        "mrouter port ifindex .
		1~1024 is switch port, 1025~1151 is agg port(agg1~127)."
    ::= { igmpSnoopingMrouterPortEntry 2 }
    
igmpSnoopingmrouterPortRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { igmpSnoopingMrouterPortEntry 3 }
	
igmpSnoopingGrpNum         OBJECT-TYPE
    SYNTAX          INTEGER  
    MAX-ACCESS      read-only
    STATUS          current
    DESCRIPTION
        "Configure to get IGMP Snooping total group number."
    ::= { lswIgmpsnoopingMibObject 12 }
	
igmpSnoopingGrplimitReach NOTIFICATION-TYPE
      OBJECTS { configSave }
      STATUS  current
      DESCRIPTION
              "Igmp snooping group record reaches total limit"
      ::= { lswIgmpsnoopingTrap 1 }

igmpSnoopingVlanGrplimitReach NOTIFICATION-TYPE
      OBJECTS { configSave }
      STATUS  current
      DESCRIPTION
              "Igmp snooping group record reaches limit on vlan"
      ::= { lswIgmpsnoopingTrap 2 }
	 
igmpSnoopingVlanQuerierSwitch NOTIFICATION-TYPE
      OBJECTS { igmpSnoopingVlanQuerierOperationalAddress }
      STATUS  current
      DESCRIPTION
              "Igmp snooping group querier changes"
      ::= { lswIgmpsnoopingTrap 3 }
	  
-- Sub Module: LINKAGG


--
--  for load balance
--


linkAggLoadBalance         OBJECT-TYPE
     SYNTAX          INTEGER
             {
                 dst-mac(1),
                 src-mac(2),
                 src-dst-mac(3),
                 src-ip(4),
                 dst-ip(5),
                 src-dst-ip(6)
             }
    MAX-ACCESS      read-write
    STATUS          current
    DESCRIPTION
        "Config load balance.
        1 dst-mac.
        2 src-mac.
        3 src-dst-mac.
        4 src-ip.
        5 dst-ip.
        6 src-dst-ip."
    ::= { linkAgg 1  }   

           
             
lacpObject OBJECT IDENTIFIER    ::= { linkAgg 2 }             
--
--  config lacp system priority
--             
lacpSysPriorityCfg   OBJECT IDENTIFIER    ::= { lacpObject 1 }
lacpSysPriority         OBJECT-TYPE
    SYNTAX          Integer32 (1..65535)
    MAX-ACCESS      read-write
    STATUS          current
    DESCRIPTION
        "Config lacp system priority."
    ::= { lacpSysPriorityCfg 1 }                 
       


--
--  config channel group on port
--             
lacpIfCfgTable         OBJECT-TYPE
    SYNTAX          SEQUENCE OF LacpIfCfgEntry
    MAX-ACCESS      not-accessible
    STATUS          current
    DESCRIPTION
        "This table is used for lacp configuration on interface."
    ::= { lacpObject 2 }    
             
             
             
lacpIfCfgEntry         OBJECT-TYPE
    SYNTAX          LacpIfCfgEntry
    MAX-ACCESS      not-accessible
    STATUS          current
    DESCRIPTION
        "This table is used for lacp configuration on interface."
    INDEX             
             {
                 lacpIfCfgAdminAggNumber, ifIndex
             }
    ::= { lacpIfCfgTable 1 }

LacpIfCfgEntry    ::=
    SEQUENCE
     {
         lacpIfCfgAdminAggNumber
               Integer32,
         lacpIfCfgMode
               INTEGER,
         lacpIfCfgRowStatus 
               RowStatus 
     }                
                  
  
  
lacpIfCfgAdminAggNumber         OBJECT-TYPE
    SYNTAX          Integer32 (1..31)
    MAX-ACCESS      not-accessible
    STATUS          current
    DESCRIPTION
        "Config channel group number."
    ::= { lacpIfCfgEntry 1 }        
             
               
             
lacpIfCfgMode         OBJECT-TYPE
    SYNTAX          INTEGER
     {
         passive(1),
         active(2)
     }
    MAX-ACCESS      read-create
    STATUS          current
    DESCRIPTION
        "The channel group mode."
    ::= { lacpIfCfgEntry 2 }             
             

lacpIfCfgRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { lacpIfCfgEntry 3 }        
             

--
--  config lacp parameter on port
--

lacpIfCfgParaTable         OBJECT-TYPE
    SYNTAX          SEQUENCE OF LacpIfCfgParaEntry
    MAX-ACCESS      not-accessible
    STATUS          current
    DESCRIPTION
        "This table is used for lacp configuration on interface."
    ::= { lacpObject 3 }    
             
             
             
lacpIfCfgParaEntry         OBJECT-TYPE
    SYNTAX          LacpIfCfgParaEntry
    MAX-ACCESS      not-accessible
    STATUS          current
    DESCRIPTION
        "This table is used for lacp configuration on interface."
    INDEX             
             {
                 ifIndex
             }
    ::= { lacpIfCfgParaTable 1 }

LacpIfCfgParaEntry    ::=
    SEQUENCE {
                 lacpIfCfgParaPriority      
                       Integer32,
                 lacpIfCfgParaTimeOut
                       INTEGER               
             }                
             
lacpIfCfgParaPriority         OBJECT-TYPE
    SYNTAX          Integer32 (1..65535)
    MAX-ACCESS      read-write
    STATUS          current
    DESCRIPTION
        "Config lacp priority on interface."
    ::= { lacpIfCfgParaEntry 1 }               


lacpIfCfgParaTimeOut         OBJECT-TYPE
    SYNTAX          INTEGER
             {
                 short(1),
                 long(2)
             }
    MAX-ACCESS      read-write
    STATUS          current
    DESCRIPTION
        "Config lacp expire timer on interface."
    ::= { lacpIfCfgParaEntry 2 }       
             
             
--             
--  display port state              
--             
               
             
lacpPortStateTable         OBJECT-TYPE
    SYNTAX          SEQUENCE OF LacpPortStateEntry
    MAX-ACCESS      not-accessible
    STATUS          current
    DESCRIPTION
        "This table is used for displaying port state of interface."
    ::= { lacpObject 4 }                 
             

lacpPortStateEntry         OBJECT-TYPE
    SYNTAX          LacpPortStateEntry
    MAX-ACCESS      not-accessible
    STATUS          current
    DESCRIPTION
        "This table is used for lacp configuration on interface."
    INDEX              
             {
                 lacpPortStateGroupNum, ifIndex
             }
    ::= { lacpPortStateTable 1 }


LacpPortStateEntry    ::=
    SEQUENCE {
                 lacpPortStateGroupNum
                     Integer32,
                 lacpPortState
                     OCTET STRING           
             }                        

lacpPortStateGroupNum         OBJECT-TYPE
    SYNTAX          Integer32 (1..255)
    MAX-ACCESS      not-accessible
    STATUS          current
    DESCRIPTION
        "Display port state."
    ::= { lacpPortStateEntry 1 }      
             
lacpPortState         OBJECT-TYPE
    SYNTAX          OCTET STRING (SIZE(0..255))
    MAX-ACCESS      read-only
    STATUS          current
    DESCRIPTION
        "Display port state."
    ::= { lacpPortStateEntry 2 }               
             
             

--
--  display lacp actor state
--
             
lacpActorStateTable         OBJECT-TYPE
    SYNTAX          SEQUENCE OF LacpActorStateEntry
    MAX-ACCESS      not-accessible
    STATUS          current
    DESCRIPTION
        "This table is used for displaying actor state."
    ::= { lacpObject 5 }    
             
             
             
lacpActorStateEntry         OBJECT-TYPE
    SYNTAX          LacpActorStateEntry
    MAX-ACCESS      not-accessible
    STATUS          current
    DESCRIPTION
        "This table is used for displaying actor state."
    INDEX             
             {
                 lacpActorGroupNum, ifIndex
             }
    ::= { lacpActorStateTable 1 }

LacpActorStateEntry    ::=
    SEQUENCE {
                 lacpActorGroupNum
                     Integer32,
                 lacpActorSystemId
                     OCTET STRING,
                 lacpActorPortNum
                     Integer32,
                 lacpActorPortTransitPduType
                     OCTET STRING,
                 lacpActorPortMode
                     OCTET STRING,
                 lacpActorPortPriority
                     Integer32,
                 lacpActorPortOperKey    
                     Integer32,
                 lacpActorPortStatsFlag 
                      OCTET STRING,
                 lacpActorPortActivity
                     OCTET STRING,
                 lacpActorPortTimeout
                     OCTET STRING,
                 lacpActorPortAggregation
                     OCTET STRING,
                 lacpActorPortSynchronization
                     OCTET STRING,
                 lacpActorPortCollecting
                     OCTET STRING,
                 lacpActorPortDistributing
                     OCTET STRING,
                 lacpActorPortDefaulted
                     OCTET STRING,
                 lacpActorPortExpired
                     OCTET STRING
             }                                     


lacpActorGroupNum         OBJECT-TYPE
    SYNTAX          Integer32 (1..31)
    MAX-ACCESS      not-accessible
    STATUS          current
    DESCRIPTION
        "Display actor group number."
    ::= { lacpActorStateEntry 1 }  
             
lacpActorSystemId         OBJECT-TYPE
    SYNTAX          OCTET STRING (SIZE (0..255))
    MAX-ACCESS      read-only
    STATUS          current
    DESCRIPTION
        "Display actor system id."
    ::= { lacpActorStateEntry 2 }               
             

lacpActorPortNum         OBJECT-TYPE
    SYNTAX          Integer32 (1..65535)
    MAX-ACCESS      read-only
    STATUS          current
    DESCRIPTION
        "Display actor port number."
    ::= { lacpActorStateEntry 3 }                
                       
                       
lacpActorPortTransitPduType         OBJECT-TYPE
    SYNTAX          OCTET STRING (SIZE (0..4))
    MAX-ACCESS      read-only
    STATUS          current
    DESCRIPTION
        "Display actor port number. It should be 'fast' or 'slow'. "
    ::= { lacpActorStateEntry 4 }                         
                       

lacpActorPortMode         OBJECT-TYPE
    SYNTAX          OCTET STRING (SIZE (0..7))
    MAX-ACCESS      read-only
    STATUS          current
    DESCRIPTION
        "Display actor port mode. It should be 'active' or 'passive'."
    ::= { lacpActorStateEntry 5 } 

lacpActorPortPriority         OBJECT-TYPE
    SYNTAX          Integer32 (1..65535)
    MAX-ACCESS      read-only
    STATUS          current
    DESCRIPTION
        "Display actor port priority."
    ::= { lacpActorStateEntry 6 } 


lacpActorPortOperKey         OBJECT-TYPE
    SYNTAX          Integer32 (1..65535)
    MAX-ACCESS      read-only
    STATUS          current
    DESCRIPTION
        "Display actor port operate key."
    ::= { lacpActorStateEntry 7 } 

                       
             
lacpActorPortStatsFlag         OBJECT-TYPE
    SYNTAX          OCTET STRING (SIZE (0..8))
    MAX-ACCESS      read-only
    STATUS          current
    DESCRIPTION
        "Display actor port stats flag."
    ::= { lacpActorStateEntry 8 }       
             
             
             
lacpActorPortActivity         OBJECT-TYPE
    SYNTAX          OCTET STRING (SIZE (0..7))
    MAX-ACCESS      read-only
    STATUS          current
    DESCRIPTION
        "Display actor port activity. It should be 'active' or 'passive'."
    ::= { lacpActorStateEntry 9 }                    


lacpActorPortTimeout         OBJECT-TYPE
    SYNTAX          OCTET STRING (SIZE (0..5))
    MAX-ACCESS      read-only
    STATUS          current
    DESCRIPTION
        "Display actor port timeout. It should be 'short' or 'long'."
    ::= { lacpActorStateEntry 10 }   
             
             
             
lacpActorPortAggregation         OBJECT-TYPE
    SYNTAX          OCTET STRING (SIZE (0..3))
    MAX-ACCESS      read-only
    STATUS          current
    DESCRIPTION
        "Display actor port number. It should be 'yes' or 'no'."
    ::= { lacpActorStateEntry 11 } 
             
lacpActorPortSynchronization         OBJECT-TYPE
    SYNTAX          OCTET STRING (SIZE (0..3))
    MAX-ACCESS      read-only
    STATUS          current
    DESCRIPTION
        "Display actor port synchronization. It should be 'yes' or 'no'."
    ::= { lacpActorStateEntry 12 }             
             
             
lacpActorPortCollecting         OBJECT-TYPE
    SYNTAX          OCTET STRING (SIZE (0..3))
    MAX-ACCESS      read-only
    STATUS          current
    DESCRIPTION
        "Display actor port collecting. It should be 'yes' or 'no'."
    ::= { lacpActorStateEntry 13 }                        
             
lacpActorPortDistributing         OBJECT-TYPE
    SYNTAX          OCTET STRING (SIZE (0..3))
    MAX-ACCESS      read-only
    STATUS          current
    DESCRIPTION
        "Display actor port distributing. It should be 'yes' or 'no'."
    ::= { lacpActorStateEntry 14 }                
             
lacpActorPortDefaulted         OBJECT-TYPE
    SYNTAX          OCTET STRING (SIZE (0..3))
    MAX-ACCESS      read-only
    STATUS          current
    DESCRIPTION
        "Display actor port defaulted. It should be 'yes' or 'no'."
    ::= { lacpActorStateEntry 15 }                
             
             
lacpActorPortExpired         OBJECT-TYPE
    SYNTAX          OCTET STRING (SIZE (0..3))
    MAX-ACCESS      read-only
    STATUS          current
    DESCRIPTION
        "Display actor port expired . It should be 'yes' or 'no'."
    ::= { lacpActorStateEntry 16 }                 
             
             
             
             
                          
--
--  display lacp neighbor state
--
lacpNeighborStateTable         OBJECT-TYPE
    SYNTAX          SEQUENCE OF LacpNeighborStateEntry
    MAX-ACCESS      not-accessible
    STATUS          current
    DESCRIPTION
        "This table is used for displaying neighbor state."
    ::= { lacpObject 6 }    
             
             
             
lacpNeighborStateEntry         OBJECT-TYPE
    SYNTAX          LacpNeighborStateEntry
    MAX-ACCESS      not-accessible
    STATUS          current
    DESCRIPTION
        "This table is used for displaying neighbor state."
   INDEX               
             {
                 lacpNeighborGroupNum, ifIndex
             }
    ::= { lacpNeighborStateTable 1 }

LacpNeighborStateEntry    ::=
    SEQUENCE {
                 lacpNeighborGroupNum
                     Integer32,
                 lacpNeighborSystemId
                     OCTET STRING,
                 lacpNeighborPortNum
                     Integer32,
                 lacpNeighborPortTransitPduType
                     OCTET STRING,
                 lacpNeighborPortMode
                     OCTET STRING,
                 lacpNeighborPortPriority
                     Integer32,
                 lacpNeighborOperKey
                     Integer32,
                 lacpNeighborPortStatsFlag 
                      OCTET STRING,
                 lacpNeighborPortActivity
                     OCTET STRING,
                 lacpNeighborPortTimeout
                     OCTET STRING,
                 lacpNeighborPortAggregation
                     OCTET STRING,
                 lacpNeighborPortSynchronization
                     OCTET STRING,
                 lacpNeighborPortCollecting
                     OCTET STRING,
                 lacpNeighborPortDistributing
                     OCTET STRING,
                 lacpNeighborPortDefaulted
                     OCTET STRING,
                 lacpNeighborPortExpired
                     OCTET STRING                               
             }                                     
             
lacpNeighborGroupNum         OBJECT-TYPE
    SYNTAX          Integer32(1..31)
    MAX-ACCESS      not-accessible
    STATUS          current
    DESCRIPTION
        "display neighbor group number."
    ::= { lacpNeighborStateEntry 1 }              
             
             
lacpNeighborSystemId         OBJECT-TYPE
    SYNTAX          OCTET STRING (SIZE (0..255))
    MAX-ACCESS      read-only
    STATUS          current
    DESCRIPTION
        "Display neighbor system id."
    ::= { lacpNeighborStateEntry 2 }               
             

lacpNeighborPortNum         OBJECT-TYPE
    SYNTAX          Integer32 (1..65535)
    MAX-ACCESS      read-only
    STATUS          current
    DESCRIPTION
        "Display neighbor port number."
    ::= { lacpNeighborStateEntry 3 }                
                       
             
lacpNeighborPortTransitPduType         OBJECT-TYPE
    SYNTAX          OCTET STRING (SIZE (0..4))
    MAX-ACCESS      read-only
    STATUS          current
    DESCRIPTION
        "Display neighbor port transmit pdu. It should be 'fast' or 'slow'."
    ::= { lacpNeighborStateEntry 4 }       


lacpNeighborPortMode         OBJECT-TYPE
    SYNTAX          OCTET STRING (SIZE (0..7))
    MAX-ACCESS      read-only
    STATUS          current
    DESCRIPTION
        "Display neighbor port mode. It should be 'active' or 'passive'."
    ::= { lacpNeighborStateEntry 5 }   


lacpNeighborPortPriority         OBJECT-TYPE
    SYNTAX          Integer32 (1..65535)
    MAX-ACCESS      read-only
    STATUS          current
    DESCRIPTION
        "Display neighbor port number."
    ::= { lacpNeighborStateEntry 6 } 

lacpNeighborOperKey         OBJECT-TYPE
    SYNTAX          Integer32 (1..65535)
    MAX-ACCESS      read-only
    STATUS          current
    DESCRIPTION
        "Display neighbor operational key."
    ::= { lacpNeighborStateEntry 7 }

lacpNeighborPortStatsFlag         OBJECT-TYPE
    SYNTAX          OCTET STRING (SIZE (0..8))
    MAX-ACCESS      read-only
    STATUS          current
    DESCRIPTION
        "Display neighbor stats flag."
    ::= { lacpNeighborStateEntry 8 }



lacpNeighborPortActivity         OBJECT-TYPE
    SYNTAX          OCTET STRING (SIZE (0..7))
    MAX-ACCESS      read-only
    STATUS          current
    DESCRIPTION
        "Display neighbor stats flag. It should be 'active' or 'passive'."
    ::= { lacpNeighborStateEntry 9 }

lacpNeighborPortTimeout         OBJECT-TYPE
    SYNTAX          OCTET STRING (SIZE (0..5))
    MAX-ACCESS      read-only
    STATUS          current
    DESCRIPTION
        "Display neighbor stats flag. It should be 'short' or 'long'."
    ::= { lacpNeighborStateEntry 10 }

lacpNeighborPortAggregation         OBJECT-TYPE
    SYNTAX          OCTET STRING (SIZE (0..3))
    MAX-ACCESS      read-only
    STATUS          current
    DESCRIPTION
        "Display neighbor stats flag. It should be 'yes' or 'no'."
    ::= { lacpNeighborStateEntry 11 }

lacpNeighborPortSynchronization         OBJECT-TYPE
    SYNTAX          OCTET STRING (SIZE (0..3))
    MAX-ACCESS      read-only
    STATUS          current
    DESCRIPTION
        "Display neighbor stats flag. It should be 'yes' or 'no'."
    ::= { lacpNeighborStateEntry 12 }


lacpNeighborPortCollecting         OBJECT-TYPE
    SYNTAX          OCTET STRING (SIZE (0..3))
    MAX-ACCESS      read-only
    STATUS          current
    DESCRIPTION
        "Display neighbor stats flag. It should be 'yes' or 'no'."
    ::= { lacpNeighborStateEntry 13 }

lacpNeighborPortDistributing         OBJECT-TYPE
    SYNTAX          OCTET STRING (SIZE (0..3))
    MAX-ACCESS      read-only
    STATUS          current
    DESCRIPTION
        "Display neighbor stats flag. It should be 'yes' or 'no'."
    ::= { lacpNeighborStateEntry 14 }

lacpNeighborPortDefaulted         OBJECT-TYPE
    SYNTAX          OCTET STRING (SIZE (0..3))
    MAX-ACCESS      read-only
    STATUS          current
    DESCRIPTION
        "Display neighbor stats flag. It should be 'yes' or 'no'."
    ::= { lacpNeighborStateEntry 15 }

lacpNeighborPortExpired         OBJECT-TYPE
    SYNTAX          OCTET STRING (SIZE (0..3))
    MAX-ACCESS      read-only
    STATUS          current
    DESCRIPTION
        "Display neighbor stats flag. It should be 'yes' or 'no'."
    ::= { lacpNeighborStateEntry 16 }



--
--
--
lacpCounterTable       OBJECT-TYPE
    SYNTAX          SEQUENCE OF LacpCounterEntry
    MAX-ACCESS      not-accessible
    STATUS          current
    DESCRIPTION
        "This table is used for displaying neighbor state."
    ::= { lacpObject 7 }    
             
             
             
lacpCounterEntry      OBJECT-TYPE
    SYNTAX            LacpCounterEntry
    MAX-ACCESS        not-accessible
    STATUS            current
    DESCRIPTION
        "This table is used for displaying neighbor state."
    INDEX             
    {
        lacpCounterGroupNum
    }
    ::= { lacpCounterTable 1 }

     LacpCounterEntry    ::=
    SEQUENCE 
    {
         lacpCounterGroupNum
             Integer32,
         lacpCounterSendPduCnt
             Integer32,
         lacpCounterRecvPduCnt
             Integer32,
         lacpCounterSendErrPktCnt
             Integer32,
         lacpCounterRecvErrPktCnt
             Integer32
     }

lacpCounterGroupNum OBJECT-TYPE
    SYNTAX          Integer32 (0..65535)
    MAX-ACCESS      not-accessible
    STATUS          current
    DESCRIPTION
        "Display lacp group number."
    ::= { lacpCounterEntry 1 }

lacpCounterSendPduCnt         OBJECT-TYPE
    SYNTAX            Integer32
    MAX-ACCESS      read-only
    STATUS          current
    DESCRIPTION
        "Display lacp send pdu counts."
    ::= { lacpCounterEntry 2 }

lacpCounterRecvPduCnt         OBJECT-TYPE
    SYNTAX          Integer32
    MAX-ACCESS      read-only
    STATUS          current
    DESCRIPTION
        "Display neighbor receive pdu counts."
    ::= { lacpCounterEntry 3 }


lacpCounterSendErrPktCnt         OBJECT-TYPE
    SYNTAX            Integer32
    MAX-ACCESS        read-only
    STATUS            current
    DESCRIPTION
        "Display neighbor send error packet counts."
    ::= { lacpCounterEntry 4 }



lacpCounterRecvErrPktCnt         OBJECT-TYPE
    SYNTAX          Integer32
    MAX-ACCESS      read-only
    STATUS          current
    DESCRIPTION
        "Display neighbor recevie error packet counts."
    ::= { lacpCounterEntry 5 }



--
--  clear lacp counter
--
     lacpClearCntCfg   OBJECT IDENTIFIER    ::= { lacpObject 8 }
lacpClearCounter       OBJECT-TYPE
    SYNTAX             Integer32 (0..127)
    MAX-ACCESS         read-write
    STATUS             current
    DESCRIPTION
        "clear lacp counter. The system will clear all lacp's couter if the value is '0'."
    ::= { lacpClearCntCfg 1 }         
             



     staticLinkAggObject OBJECT IDENTIFIER    ::= { linkAgg 3 }
--
--
--  static link aggregation table
--     

staticLinkAggTable         OBJECT-TYPE
    SYNTAX          SEQUENCE OF StaticLinkAggEntry
    MAX-ACCESS      not-accessible
    STATUS          current
    DESCRIPTION
        "This table stores the link aggregator number, name and 
                  configure type and memberlist."
    ::= { staticLinkAggObject 1 }

staticLinkAggEntry     OBJECT-TYPE
    SYNTAX          StaticLinkAggEntry
    MAX-ACCESS      not-accessible
    STATUS          current
    DESCRIPTION
        "This table stores the link aggregator number, name and configure type
         and memberlist."
                 
   INDEX     {
                 staticLinkAggNumber,
                 ifIndex
             }
    ::= { staticLinkAggTable 1 }

StaticLinkAggEntry    ::=
    SEQUENCE {
                 staticLinkAggNumber
                       Integer32,
                 staticLinkAggIndex
                       Integer32,
                 staticLinkAggName
                       OCTET STRING,
                 staticLinkAggMemberIndex
                       Integer32,
                 staticLinkAggMemberName
                       OCTET STRING,
                 staticLinkAggMemberEnable
                       INTEGER,
                 staticLinkAggMemberRowStatus 
       RowStatus 
             }

staticLinkAggNumber         OBJECT-TYPE
    SYNTAX          Integer32 (0..31)
    MAX-ACCESS      not-accessible
    STATUS          current
    DESCRIPTION
        "The number of Link aggregator interface.This is the index of Link 
        Aggregator table."
    ::= { staticLinkAggEntry 1 }

staticLinkAggIndex         OBJECT-TYPE
    SYNTAX          Integer32 (0..65535)
    MAX-ACCESS      read-only
    STATUS          current
    DESCRIPTION
        "The index of link aggregator interface."
    ::= { staticLinkAggEntry 2 }

staticLinkAggName         OBJECT-TYPE
    SYNTAX          OCTET STRING
    MAX-ACCESS      read-only
    STATUS          current
    DESCRIPTION
        "The name of link aggregator interface."
    ::= { staticLinkAggEntry 3 }

staticLinkAggMemberIndex         OBJECT-TYPE
    SYNTAX          Integer32 (0..65535)
    MAX-ACCESS      read-only
    STATUS          current
    DESCRIPTION
        "The index of interface member added to link aggregator."
    ::= { staticLinkAggEntry 4 }
    
staticLinkAggMemberName         OBJECT-TYPE
    SYNTAX          OCTET STRING(SIZE(1..10))
    MAX-ACCESS      read-only
    STATUS          current
    DESCRIPTION
        "The name of interface member added to link aggregator."
    ::= { staticLinkAggEntry 5 }

staticLinkAggMemberEnable         OBJECT-TYPE
    SYNTAX          INTEGER
    {
        down(0),
        bundle(1),
        adminDown(2)
    }
    MAX-ACCESS      read-only
    STATUS          current
    DESCRIPTION
        "The member is Bundle when the value is 1.
        the member is down when the value is 0.
        the member is admin down when the value is 2."
    ::= { staticLinkAggEntry 6 }         
             
staticLinkAggMemberRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { staticLinkAggEntry 7 }    
             
  
-- Sub Module: QBRIDGEEXT


    VlanIndex    ::= TEXTUAL-CONVENTION
        DISPLAY-HINT        "d        "
    STATUS          current
    DESCRIPTION
        "A value used to index per-VLAN tables: values of 0 and
            4095 are not permitted.If the value is between 1 and
            4094 inclusive, it represents an IEEE 802.1Q VLAN-ID with
            global scope within a given bridged domain (see VlanId
            textual convention).If the value is greater than 4095,
    
    
            then it represents a VLAN with scope local to the
            particular agent, i.e., one without a global VLAN-ID
            assigned to it.Such VLANs are outside the scope of
            IEEE 802.1Q, but it is convenient to be able to manage them
            in the same way using this MIB."
    SYNTAX          Unsigned32
    
    VlanList    ::= TEXTUAL-CONVENTION
    STATUS          current
    DESCRIPTION
        "Each octet within this value specifies a set of eight
            VLANs."
    SYNTAX          OCTET STRING (SIZE(0..256))
    
    VlanClassRuleIndex    ::= TEXTUAL-CONVENTION
        DISPLAY-HINT        "d        "
    STATUS          current
    DESCRIPTION
        "A value used to index vlan class rule tables: values of 0 to
            4095 are  permitted."
    SYNTAX          INTEGER (0..4095)
        
    VlanClassGroupIndex    ::= TEXTUAL-CONVENTION
        DISPLAY-HINT        "d        "
    STATUS          current
    DESCRIPTION
        "A value used to index vlan class group tables: values of 0 to
            31 are  permitted."
    SYNTAX          INTEGER (0..31)     
    
    VlanClassProtocol    ::= TEXTUAL-CONVENTION
  --      DISPLAY-HINT        "d        "
    STATUS          current
    DESCRIPTION
        "A value used to index vlan class Protocols." 
    SYNTAX          INTEGER
            {
                ip(1),
                ipv4(2),
                ipv6(3),
                mpls(4),
                mplsmcast(5),
                arp(6),
                rarp(7),
                pppoe(11)
            } 
    
    VlanClassEnableBase    ::= TEXTUAL-CONVENTION
   --     DISPLAY-HINT        "d        "
    STATUS          current
    DESCRIPTION
        "A value used to index vlan class enable based." 
    SYNTAX          INTEGER
            {
                mac(1),
                ip(2),
                protocol(4)
            } 

VlanClassIpv6Address ::= TEXTUAL-CONVENTION
		DISPLAY-HINT "2x:"
		STATUS          current
		DESCRIPTION
			"This data type is used to model IPv6 addresses.
			This is a binary string of 16 octets in network  byte-order."
		SYNTAX          OCTET STRING (SIZE (16)) 
--
-- groups in the QBRIDGEEXT MIB
--

    vlanExt      OBJECT IDENTIFIER    ::= { qBridgeExt 1 }
    fdbExt       OBJECT IDENTIFIER    ::= { qBridgeExt 2 }
    vlanClass    OBJECT IDENTIFIER    ::= { qBridgeExt 3 }


--
-- vlanExt group
--


vlanTable         OBJECT-TYPE
    SYNTAX          SEQUENCE OF VlanEntry
    MAX-ACCESS      not-accessible
    STATUS          current
    DESCRIPTION
        "A table that contains information about VLAN entries
            of the device."
    ::= { vlanExt 1 }
    
vlanEntry         OBJECT-TYPE
    SYNTAX          VlanEntry
    MAX-ACCESS      not-accessible
    STATUS          current
    DESCRIPTION
        "Information about a specific VLAN of the device."
    INDEX     { vlanIndex }
    ::= { vlanTable 1 }
    
VlanEntry    ::=
    SEQUENCE {
            vlanIndex
                VlanIndex,
            vlanName
                OCTET STRING,
            vlanStatus 
                INTEGER,
            vlanRowStatus 
                RowStatus ,
            vlanIfConfig
                INTEGER                
        }
    
vlanIndex         OBJECT-TYPE
    SYNTAX          VlanIndex
    MAX-ACCESS      not-accessible
    STATUS          current
    DESCRIPTION
        "An forward ID, which may be same as VLAN ID in IVL mode."
    ::= { vlanEntry 1 }

vlanName         OBJECT-TYPE
    SYNTAX          OCTET STRING (SIZE (0..16))
    MAX-ACCESS      read-create
    STATUS          current
    DESCRIPTION
        "An administratively assigned string, which may be used to identify the VLAN."
    ::= { vlanEntry 2 }

vlanStatus        OBJECT-TYPE
    SYNTAX          INTEGER{
                      inactive(1),
                      active(2)
                      }
    MAX-ACCESS      read-create
    STATUS          current
    DESCRIPTION
        "An administratively VLANStatus .
        1 Inactive;
        2 Active(2)."
    ::= { vlanEntry 3 }

vlanRowStatus         OBJECT-TYPE
    SYNTAX          RowStatus
    MAX-ACCESS      read-create
    STATUS          current
    DESCRIPTION
        "The status of this conceptual row.Now only realize CreateAndGo(4) and Destroy(6) and Active(1)."
    ::= { vlanEntry 4 }


vlanIfConfig         OBJECT-TYPE
    SYNTAX          INTEGER
        {
            create(1),
            destroy(2)
        }
    MAX-ACCESS      read-create
    STATUS          current
    DESCRIPTION
        "This object create/destroy vlan interface.
        1 Create.
        2 Destroy."
    ::= { vlanEntry 5 }


portVlanTable         OBJECT-TYPE
    SYNTAX          SEQUENCE OF PortVlanEntry
    MAX-ACCESS      not-accessible
    STATUS          current
    DESCRIPTION
        "A table that contains information about interface's VLAN properties."
    ::= { vlanExt 2 }

portVlanEntry         OBJECT-TYPE
    SYNTAX          PortVlanEntry
    MAX-ACCESS      not-accessible
    STATUS          current
    DESCRIPTION
        "Information about a specific interface's VLAN properties."
    INDEX     { ifIndex }
    ::= { portVlanTable 1 }

PortVlanEntry    ::=
    SEQUENCE {
            vlanTagType
                INTEGER,
            pvid
                INTEGER,
            ingressFilter
                INTEGER,
            allowedVlans
                VlanList,
            allowedVlanAdd
                VlanList,
            allowedVlanDel
                VlanList
        }

vlanTagType         OBJECT-TYPE
    SYNTAX          INTEGER{
                    all(1),
                    qinq(2),
                    untagged(3)
                }
    MAX-ACCESS      read-write
    STATUS          current
    DESCRIPTION
        "all(1) -- trunk mode
         qinq(2) -- qinq mode
         untagged(3) -- access mode."
    ::= { portVlanEntry 1 }

pvid         OBJECT-TYPE
    SYNTAX          INTEGER
    MAX-ACCESS      read-write
    STATUS          current
    DESCRIPTION
        "An administratively assigned string, which may be used to identify the VLAN.
        Vid range is 2~4094."
    ::= { portVlanEntry 2 }


ingressFilter         OBJECT-TYPE
    SYNTAX          INTEGER{
                    enable(1),
                    disable(2)
                }
    MAX-ACCESS      read-write
    STATUS          current
    DESCRIPTION
        "An administratively assigned string, which may be used to identify the VLAN.
        1 Enable.
        2 Disable."
    ::= { portVlanEntry 3 }

allowedVlans         OBJECT-TYPE
    SYNTAX          VlanList
    MAX-ACCESS      read-write
    STATUS          current
    DESCRIPTION
        "VLAN list of this port, should use the 3 format below:
             all  - all VLANs in the VLAN database
             none - none VLAN
             string such as 1,3,10-20,4094
        "
    ::= { portVlanEntry 4 }

allowedVlanAdd         OBJECT-TYPE
    SYNTAX          VlanList
    MAX-ACCESS      read-write
    STATUS          current
    DESCRIPTION
        "VLAN list to add to this port, string such as 1,3,10-20,4094.
        Use for set node, when get node return meaningless."
    ::= { portVlanEntry 5 }

allowedVlanDel         OBJECT-TYPE
    SYNTAX          VlanList
    MAX-ACCESS      read-write
    STATUS          current
    DESCRIPTION
        "VLAN list to remove from this port, string such as 1,3,10-20,4094.
        Use for set node, when get node return meaningless."
    ::= { portVlanEntry 6 }

vlanReplaceDscpExpTable         OBJECT-TYPE
    SYNTAX          SEQUENCE OF VlanReplaceDscpExpEntry
    MAX-ACCESS      not-accessible
    STATUS          obsolete
    DESCRIPTION
        "A table that contains information about VLAN Replace Dscp/Exp
            of the device.
        Not support on this version"
    ::= { vlanExt 3 }

vlanReplaceDscpExpEntry         OBJECT-TYPE
    SYNTAX          VlanReplaceDscpExpEntry
    MAX-ACCESS      not-accessible
    STATUS          obsolete
    DESCRIPTION
        "Information about a specific VLAN of the device."
    INDEX     { vlanReplaceDscpExpIndex }
    ::= { vlanReplaceDscpExpTable 1 }

VlanReplaceDscpExpEntry    ::=
    SEQUENCE {
            vlanReplaceDscpExpIndex
                VlanIndex,
            vlanReplaceDscpExpEn
                INTEGER
        }

vlanReplaceDscpExpIndex         OBJECT-TYPE
    SYNTAX          VlanIndex
    MAX-ACCESS      not-accessible
    STATUS          obsolete
    DESCRIPTION
        "Index of VLAN ID in IVL mode."
    ::= { vlanReplaceDscpExpEntry 1 }

vlanReplaceDscpExpEn        OBJECT-TYPE
    SYNTAX          INTEGER{
                      enable(1),
                      disable(2)
                      }
    MAX-ACCESS      read-create
    STATUS          obsolete
    DESCRIPTION
        "Status of replace the dscp/exp field in packets on egress for specified VLAN..
        1 replace dscp/exp;
        2 do not replace dscp/exp."
    DEFVAL { disable }
    ::= { vlanReplaceDscpExpEntry 2 }


--
-- fdbExt group
--

unicastTable         OBJECT-TYPE
    SYNTAX          SEQUENCE OF UnicastEntry
    MAX-ACCESS      not-accessible
    STATUS          current
    DESCRIPTION
        "A table that contains information about unicast entries
            for which the device has forwarding and/or filtering
            information.This information is used by the
            transparent bridging function in determining how to
            propagate a received frame."
    ::= { fdbExt 1 }

unicastEntry         OBJECT-TYPE
    SYNTAX          UnicastEntry
    MAX-ACCESS      not-accessible
    STATUS          current
    DESCRIPTION
        "Information about a specific unicast MAC address for
            which the device has some forwarding and/or filtering
            information."
    INDEX           { vlanIndex, unicastAddress , fdbPort}
    ::= { unicastTable 1 }

UnicastEntry    ::=
    SEQUENCE {
            unicastVID
                VlanIndex,
            unicastAddress
                MacAddress,
            fdbPort
                INTEGER,
            fdbStatus
                INTEGER,
            fdbRowStatus
RowStatus
        }

unicastVID         OBJECT-TYPE
    SYNTAX          VlanIndex
    MAX-ACCESS      not-accessible
    STATUS          current
    DESCRIPTION
            "The VLAN identifier of this FDB entry."
    ::= { unicastEntry 1 }

unicastAddress         OBJECT-TYPE
    SYNTAX          MacAddress
    MAX-ACCESS      not-accessible
    STATUS          current
    DESCRIPTION
        "A unicast MAC address for which the device has forwarding and/or filtering information."
    ::= { unicastEntry 2 }

fdbPort         OBJECT-TYPE
    SYNTAX          INTEGER (0..65535)
    MAX-ACCESS      not-accessible
    STATUS          current
    DESCRIPTION
        "Either the value '0', or the port number."
    ::= { unicastEntry 3 }

fdbStatus        OBJECT-TYPE
    SYNTAX          INTEGER {
                        static(1),
                        learned(2),
                        self(3)
                    }
    MAX-ACCESS      read-only
    STATUS          current
    DESCRIPTION
        "This object clear the MAC address of this system theStatus of this entry.
        static(1) - the value of static configured MAC address, used for forwarding.
        dynamic(2) - the value of learnt MAC address."
    ::= { unicastEntry 4 }

fdbRowStatus        OBJECT-TYPE
    SYNTAX          RowStatus
    MAX-ACCESS      read-create
    STATUS          current
    DESCRIPTION
        "The status of this conceptual row.Now only realize CreateAndGo(4) and Destroy(6) and Active(1).
        Can't destroy a learned fdb entry. Using the node addressClearOperation can destroy learned fdb entries."
    ::= { unicastEntry 5 }

multicastTable         OBJECT-TYPE
    SYNTAX          SEQUENCE OF MulticastEntry
    MAX-ACCESS      not-accessible
    STATUS          current
    DESCRIPTION
        "A table that contains information about unicast entries
            for which the device has forwarding and/or filtering
            information.This information is used by the
            transparent bridging function in determining how to
            propagate a received frame."
    ::= { fdbExt 2 }

multicastEntry         OBJECT-TYPE
    SYNTAX          MulticastEntry
    MAX-ACCESS      not-accessible
    STATUS          current
    DESCRIPTION
        "Information about a specific multicast MAC address for
            which the device has some forwarding and/or filtering
            information."
    INDEX           { vlanIndex, multicastAddress, destinationPort}
    ::= { multicastTable 1 }

MulticastEntry    ::=
    SEQUENCE {
            multicastVID
                VlanIndex,
            multicastAddress
                MacAddress,
            destinationPort
                Integer32,
            multicastRowStatus
RowStatus
        }

multicastVID         OBJECT-TYPE
    SYNTAX          VlanIndex
    MAX-ACCESS      not-accessible
    STATUS          current
    DESCRIPTION
        "The VLAN identifier of this multicast entry."
    ::= { multicastEntry 1 }

multicastAddress         OBJECT-TYPE
    SYNTAX          MacAddress
    MAX-ACCESS      not-accessible
    STATUS          current
    DESCRIPTION
        "A multicast MAC address for which the device has
        forwarding and/or filtering information."
    ::= { multicastEntry 2 }

destinationPort         OBJECT-TYPE
    SYNTAX          Integer32 (0..65535)
    MAX-ACCESS      not-accessible
    STATUS          current
    DESCRIPTION
        "A destination port of the multicast MAC address for which the device has
            forwarding and/or filtering information."
    ::= { multicastEntry 3 }

multicastRowStatus         OBJECT-TYPE
    SYNTAX          RowStatus
    MAX-ACCESS      read-create
    STATUS          current
    DESCRIPTION
        "The status of this conceptual row.Now only realize CreateAndGo and Destroy and Active.
        Can't destroy a learned fdb entry. Using the node addressClearOperation can destroy learned fdb entries.
        1 means Active
        4 means CreateAndGo
        6 means Destroy"
    ::= { multicastEntry 4 }
    
filterTable         OBJECT-TYPE
    SYNTAX          SEQUENCE OF FilterEntry
    MAX-ACCESS      not-accessible
    STATUS          current
    DESCRIPTION
        "A table that contains information about filter entries
            for which the device has filtering information."
    ::= { fdbExt 3 }

filterEntry         OBJECT-TYPE
    SYNTAX          FilterEntry
    MAX-ACCESS      not-accessible
    STATUS          current
    DESCRIPTION
        "Information about a specific filter MAC address for
            which the device has filtering information."
    INDEX     { filterAddress }
    ::= { filterTable 1 }

FilterEntry    ::=
    SEQUENCE {
            filterAddress
                MacAddress,
            filterRowStatus
RowStatus
        }

filterAddress         OBJECT-TYPE
    SYNTAX          MacAddress
    MAX-ACCESS      not-accessible
    STATUS          current
    DESCRIPTION
        "A unicast MAC address for which the device has filtering information."
    ::= { filterEntry 1 }

filterRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { filterEntry 2 }
    
addressClearOperation         OBJECT-TYPE
    SYNTAX          INTEGER{
                    static(1),
                    dynamic(2),
                    filter(3),
                    multicast(4)
                }                           
    MAX-ACCESS      read-write
    STATUS          current
    DESCRIPTION
        "This object clear the MAC address of this system theStatus of this entry.
                static(1) - clear those entris which are created by management.
                dynamic(2) - clear those entris which are created by learning.
                filter(3) - clear those MAC filter entris.
                multicast(4) - clear all multicast entries configured through management."
    ::= { fdbExt 4 }

addressAgingTime            OBJECT-TYPE
    SYNTAX          INTEGER (10..1000000)
    MAX-ACCESS      read-write
    STATUS          current
    DESCRIPTION
        " Dynamic mac address aging time, the unit of which is second.
        Ageing-time range 10~1000000"
    ::= { fdbExt 5 }

fdbExtTrap OBJECT IDENTIFIER ::= {   fdbExt 10  }

fdbExtDbFull NOTIFICATION-TYPE
    OBJECTS      { vlanIndex }
    STATUS          current
    DESCRIPTION
        "Fdb DB full."
    ::= { fdbExtTrap 1 }

--
-- vlanClass
--

--VlanClassRuleIp
vlanClassRuleIpTable         OBJECT-TYPE
    SYNTAX          SEQUENCE OF VlanClassRuleIpEntry
    MAX-ACCESS      not-accessible
    STATUS          current
    DESCRIPTION
        "A table that contains information about filter entries
            for which the device has filtering information."
    ::= { vlanClass 1 }

vlanClassRuleIpEntry         OBJECT-TYPE
    SYNTAX          VlanClassRuleIpEntry
    MAX-ACCESS      not-accessible
    STATUS          current
    DESCRIPTION
        "Information about a specific filter IP address for which the device has
         filtering information."
    INDEX            { vlanClassRuleIpIndex, vlanClassRuleIpAddress,vlanClassRuleIpAddressLen, vlanClassIpVlanID}
    ::= { vlanClassRuleIpTable 1 }

VlanClassRuleIpEntry    ::=
    SEQUENCE {
        vlanClassRuleIpIndex
            VlanClassRuleIndex,
        vlanClassRuleIpAddress
            IpAddress,
        vlanClassRuleIpAddressLen
            Integer32,
        vlanClassIpVlanID
            VlanIndex,
        vlanClassRuleIpRowStatus
            RowStatus
        }
vlanClassRuleIpIndex         OBJECT-TYPE
    SYNTAX          VlanClassRuleIndex
    MAX-ACCESS      not-accessible
    STATUS          current
    DESCRIPTION
        "An Vlan Class rule ID."
    ::= { vlanClassRuleIpEntry 1 }

vlanClassRuleIpAddress         OBJECT-TYPE
    SYNTAX          IpAddress
    MAX-ACCESS      not-accessible
    STATUS          current
    DESCRIPTION
        "A unicast IP address for which the device has filtering information."
    ::= { vlanClassRuleIpEntry 2 }

vlanClassRuleIpAddressLen         OBJECT-TYPE
    SYNTAX          Integer32 (0..32)
    MAX-ACCESS      not-accessible
    STATUS          current
    DESCRIPTION
        "This object indicates the mask lenghth of ip."
    ::= { vlanClassRuleIpEntry 3 }

vlanClassIpVlanID         OBJECT-TYPE
    SYNTAX          VlanIndex
    MAX-ACCESS      not-accessible
    STATUS          current
    DESCRIPTION
        "Vlan ID which is mapped for the entry."
    ::= { vlanClassRuleIpEntry 4 }

vlanClassRuleIpRowStatus         OBJECT-TYPE
    SYNTAX          RowStatus
    MAX-ACCESS      read-create
    STATUS          current
    DESCRIPTION
        "The status of this conceptual row.Now only realize CreateAndGo
        and Destroy and Active.
        1 means Active
        4 means CreateAndGo
        6 means Destroy"
    ::= { vlanClassRuleIpEntry 5 }
    
    --VlanClassRuleMac
vlanClassRuleMacTable         OBJECT-TYPE
    SYNTAX          SEQUENCE OF VlanClassRuleMacEntry
    MAX-ACCESS      not-accessible
    STATUS          current
    DESCRIPTION
        "A table that contains information about filter entries
            for which the device has filtering information."
    ::= { vlanClass 2 }

vlanClassRuleMacEntry         OBJECT-TYPE
    SYNTAX          VlanClassRuleMacEntry
    MAX-ACCESS      not-accessible
    STATUS          current
    DESCRIPTION
        "Information about a specific filter MAC address for
         which the device has filtering information."
    INDEX            { vlanClassRuleMacIndex, vlanClassRuleMacAddress,vlanClassMacVlanID}
    ::= { vlanClassRuleMacTable 1 }

VlanClassRuleMacEntry    ::=
    SEQUENCE {
            vlanClassRuleMacIndex
                VlanClassRuleIndex,
            vlanClassRuleMacAddress
                MacAddress,
            vlanClassMacVlanID
                VlanIndex,
            vlanClassRuleMacRowStatus
RowStatus
        }
vlanClassRuleMacIndex         OBJECT-TYPE
    SYNTAX          VlanClassRuleIndex
    MAX-ACCESS      not-accessible
    STATUS          current
    DESCRIPTION
        "An Vlan Class rule ID."
    ::= { vlanClassRuleMacEntry 1 }

vlanClassRuleMacAddress         OBJECT-TYPE
    SYNTAX          MacAddress
    MAX-ACCESS      not-accessible
    STATUS          current
    DESCRIPTION
        "A unicast MAC address for which the device has filtering information."
    ::= { vlanClassRuleMacEntry 2 }

vlanClassMacVlanID         OBJECT-TYPE
    SYNTAX          VlanIndex
    MAX-ACCESS      not-accessible
    STATUS          current
    DESCRIPTION
        "Vlan ID which is mapped for the entry."
    ::= { vlanClassRuleMacEntry 3 }

vlanClassRuleMacRowStatus         OBJECT-TYPE
    SYNTAX          RowStatus
    MAX-ACCESS      read-create
    STATUS          current
    DESCRIPTION
        "The status of this conceptual row.Now only realize CreateAndGo
        and Destroy and Active.
        1 means Active
        4 means CreateAndGo
        6 means Destroy"
    ::= { vlanClassRuleMacEntry 4 }
    
    --VlanClassRuleProtocol
vlanClassRuleProtocolTable         OBJECT-TYPE
    SYNTAX          SEQUENCE OF VlanClassRuleProtocolEntry
    MAX-ACCESS      not-accessible
    STATUS          current
    DESCRIPTION
        "A table that contains information about filter entries
            for which the device has filtering information."
    ::= { vlanClass 3 }

vlanClassRuleProtocolEntry         OBJECT-TYPE
    SYNTAX          VlanClassRuleProtocolEntry
    MAX-ACCESS      not-accessible
    STATUS          current
    DESCRIPTION
        "Information about a specific filter Protocol for
            which the device has filtering information."
     INDEX          { vlanClassRuleProtocolIndex, vlanClassRuleProtocol,vlanClassProtocolVlanID}
    ::= { vlanClassRuleProtocolTable 1 }

VlanClassRuleProtocolEntry    ::=
    SEQUENCE {
            vlanClassRuleProtocolIndex
                VlanClassRuleIndex,
            vlanClassRuleProtocol
                VlanClassProtocol,
            vlanClassProtocolVlanID
                VlanIndex,
            vlanClassRuleProtocolRowStatus
RowStatus
        }
vlanClassRuleProtocolIndex         OBJECT-TYPE
    SYNTAX          VlanClassRuleIndex
    MAX-ACCESS      not-accessible
    STATUS          current
    DESCRIPTION
        "An Vlan Class rule ID."
    ::= { vlanClassRuleProtocolEntry 1 }

vlanClassRuleProtocol         OBJECT-TYPE
    SYNTAX          VlanClassProtocol
    MAX-ACCESS      not-accessible
    STATUS          current
    DESCRIPTION
        "The protocol for which the device has filtering information.
        2504 means ARP
        32821 means RARP
        2048 means IPv4
        34525 means IPv6
        34887 means MPLS
        34888 means MPLS Multicast
        13 means PPPOE
        "
    ::= { vlanClassRuleProtocolEntry 2 }

vlanClassProtocolVlanID         OBJECT-TYPE
    SYNTAX          VlanIndex
    MAX-ACCESS      not-accessible
    STATUS          current
    DESCRIPTION
        "Vlan ID which is mapped for the entry."
    ::= { vlanClassRuleProtocolEntry 3 }

vlanClassRuleProtocolRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { vlanClassRuleProtocolEntry 4 }
    
    --VlanClassRuleIpv6    
--vlanClassRuleIpv6Table         OBJECT-TYPE
--    SYNTAX          SEQUENCE OF VlanClassRuleIpv6Entry
--    MAX-ACCESS      not-accessible
--    STATUS          current
--    DESCRIPTION
--        "A table that contains information about filter entries
--            for which the device has filtering information."
--    ::= { vlanClass 4 }

--vlanClassRuleIpv6Entry         OBJECT-TYPE
--    SYNTAX          VlanClassRuleIpv6Entry
--    MAX-ACCESS      not-accessible
--    STATUS          current
--    DESCRIPTION
--        "Information about a specific filter IPv6 address for which the device
--         has filtering information."
--    INDEX  { vlanClassRuleIpv6Index, vlanClassRuleIpv6Address,vlanClassRuleIpv6AddressLen, vlanClassIpv6VlanID}
--    ::= { vlanClassRuleIpv6Table 1 }
--
--VlanClassRuleIpv6Entry    ::=
--    SEQUENCE {
--            vlanClassRuleIpv6Index
--                VlanClassRuleIndex,
--            vlanClassRuleIpv6Address
--                VlanClassIpv6Address,
--            vlanClassRuleIpv6AddressLen
--                Integer32,
--            vlanClassIpv6VlanID
--                VlanIndex,
--            vlanClassRuleIpv6RowStatus
--RowStatus
--        }
--vlanClassRuleIpv6Index         OBJECT-TYPE
--    SYNTAX          VlanClassRuleIndex
--    MAX-ACCESS      read-only
--    STATUS          current
--    DESCRIPTION
--        "An Vlan Class rule ID."
--    ::= { vlanClassRuleIpv6Entry 1 }
--
--vlanClassRuleIpv6Address         OBJECT-TYPE
--    SYNTAX          VlanClassIpv6Address
--    MAX-ACCESS      read-only
--    STATUS          current
--    DESCRIPTION
--        "A unicast IP address for which the device has filtering information."
--    ::= { vlanClassRuleIpv6Entry 2 }
--
--vlanClassRuleIpv6AddressLen         OBJECT-TYPE
--    SYNTAX          Integer32  (0..65535)
--    MAX-ACCESS      read-only
--    STATUS          current
--    DESCRIPTION
--        "This object indicates the mask lenghth of ip."
--    ::= { vlanClassRuleIpv6Entry 3 }
--
--vlanClassIpv6VlanID         OBJECT-TYPE
--    SYNTAX          VlanIndex
--    MAX-ACCESS      read-only
--    STATUS          current
--    DESCRIPTION
--        "Vlan ID which is mapped for the entry."
--    ::= { vlanClassRuleIpv6Entry 4 }
--
--vlanClassRuleIpv6RowStatus         OBJECT-TYPE
--    SYNTAX          RowStatus
--    MAX-ACCESS      read-create
--    STATUS          current
--    DESCRIPTION
--        "The status of this conceptual row.Now only realize CreateAndGo
--        and Destroy and Active."
--    ::= { vlanClassRuleIpv6Entry 5 }
--

--VlanClassGroup
vlanClassGroupTable         OBJECT-TYPE
    SYNTAX          SEQUENCE OF VlanClassGroupEntry
    MAX-ACCESS      not-accessible
    STATUS          current
    DESCRIPTION
        "A table that contains information about filter entries
            for which the device has filtering information."
    ::= { vlanClass 5 }

vlanClassGroupEntry         OBJECT-TYPE
    SYNTAX          VlanClassGroupEntry
    MAX-ACCESS      not-accessible
    STATUS          current
    DESCRIPTION
        "Information about a specific filter group for
         which the device has filtering information."
    INDEX     { vlanClassGroupIndex,vlanClassRuleIndex }
    ::= { vlanClassGroupTable 1 }

VlanClassGroupEntry    ::=
    SEQUENCE {
            vlanClassGroupIndex
                VlanClassGroupIndex,
            vlanClassRuleIndex
                VlanClassRuleIndex,
            vlanClassGroupRowStatus
RowStatus
        }
vlanClassGroupIndex         OBJECT-TYPE
    SYNTAX          VlanClassGroupIndex
    MAX-ACCESS      not-accessible
    STATUS          current
    DESCRIPTION
        "An Vlan Class group ID."
    ::= { vlanClassGroupEntry 1 }

vlanClassRuleIndex         OBJECT-TYPE
    SYNTAX          VlanClassRuleIndex
    MAX-ACCESS      not-accessible
    STATUS          current
    DESCRIPTION
        "The Vlan Class rule index."
    ::= { vlanClassGroupEntry 2 }

vlanClassGroupRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { vlanClassGroupEntry 3 }
        
--VlanClass Enable inteface
vlanClassEnableTable         OBJECT-TYPE
    SYNTAX          SEQUENCE OF VlanClassEnableEntry
    MAX-ACCESS      not-accessible
    STATUS          current
    DESCRIPTION
        "A table that contains information about filter entries
        for which the device has filtering information."
    ::= { vlanClass 6 }

vlanClassEnableEntry         OBJECT-TYPE
    SYNTAX          VlanClassEnableEntry
    MAX-ACCESS      not-accessible
    STATUS          current
    DESCRIPTION
        "Information about a specific filter for
         which the device has filtering information."
    INDEX     { vlanClassEnableIfIndex}
    ::= { vlanClassEnableTable 1 }

VlanClassEnableEntry    ::=
    SEQUENCE {
        vlanClassEnableIfIndex
            Integer32,
        vlanClassEnableGroup
            VlanClassGroupIndex,
        vlanClassEnableBase
            VlanClassEnableBase,
        vlanClassEnableRowStatus
            RowStatus
        }
vlanClassEnableIfIndex         OBJECT-TYPE
    SYNTAX          Integer32 (0..65535)
    MAX-ACCESS      not-accessible
    STATUS          current
    DESCRIPTION
        "Interface index which is enabled for Vlan Class ."
    ::= { vlanClassEnableEntry 1 }

vlanClassEnableGroup         OBJECT-TYPE
    SYNTAX          VlanClassGroupIndex
    MAX-ACCESS      read-create
    STATUS          current
    DESCRIPTION
        "The Vlan Class group ID.
        Group ID range is 0~31."
    ::= { vlanClassEnableEntry 2 }

vlanClassEnableBase         OBJECT-TYPE
    SYNTAX          VlanClassEnableBase
    MAX-ACCESS      read-create
    STATUS          current
    DESCRIPTION
        "Vlan ID which is mapped for the entry."
    ::= { vlanClassEnableEntry 3 }

vlanClassEnableRowStatus         OBJECT-TYPE
    SYNTAX          RowStatus
    MAX-ACCESS      read-create
    STATUS          current
    DESCRIPTION
        "The status of this conceptual row.Now only realize CreateAndGo
         and Destroy and Active.
        1 means Active
        4 means CreateAndGo
        6 means Destroy"
    ::= { vlanClassEnableEntry 5 }       
        

-- Sub Module: DOT1XEXT


-- ==================================================================
--
-- =====================object definition begin======================
--
-- ==================================================================


    dot1xExtMaxReauthReqTable OBJECT-TYPE
            SYNTAX SEQUENCE OF Dot1xExtMaxReauthReqEntry
            MAX-ACCESS not-accessible
            STATUS current
            DESCRIPTION
                "table of login entry."
            ::= { dot1xExt 1 }

    dot1xExtMaxReauthReqEntry OBJECT-TYPE
        SYNTAX Dot1xExtMaxReauthReqEntry
        MAX-ACCESS not-accessible
        STATUS current
        DESCRIPTION
            "Login entry"
        INDEX { dot1xExtMaxReauthReqIndex}
        ::= { dot1xExtMaxReauthReqTable 1 }

    Dot1xExtMaxReauthReqEntry ::=
        SEQUENCE
        {
            dot1xExtMaxReauthReqIndex
                Integer32,
            dot1xExtMaxReauthReqVersion
                INTEGER,
            dot1xExtMaxReauthReqNum
                Integer32,
            dot1xExtMaxReqNum
                Integer32
        }

    dot1xExtMaxReauthReqIndex OBJECT-TYPE
        SYNTAX Integer32    (1..2147483647)
        MAX-ACCESS not-accessible
        STATUS current
        DESCRIPTION "Index."
        ::= { dot1xExtMaxReauthReqEntry 1 }

    dot1xExtMaxReauthReqVersion OBJECT-TYPE
        SYNTAX INTEGER
        {
            version1(1),
            version2(2)
        }
        MAX-ACCESS read-write
        STATUS current
        DESCRIPTION
              "Set the protocol version and the default number is 2.The range is 1 to 2. "
        DEFVAL {version2}
        ::= { dot1xExtMaxReauthReqEntry 2 }

    dot1xExtMaxReauthReqNum OBJECT-TYPE
        SYNTAX Integer32
        MAX-ACCESS not-accessible
        STATUS current
        DESCRIPTION "Number of reauthentication attempts before becoming unauthorized. The range is 1 to 10. Not supported now"
        ::= { dot1xExtMaxReauthReqEntry 3 }

    dot1xExtMaxReqNum OBJECT-TYPE
        SYNTAX Integer32 (1..10)
        MAX-ACCESS read-write
        STATUS current
        DESCRIPTION "Number of times that the switch sends an EAP-request/identity frame to the client. The range is 1 to 10."
        DEFVAL {2}
        ::= { dot1xExtMaxReauthReqEntry 4 }

 -- IEEE 802.1X VLAN policy
    dot1xExtVlanPolicyTable OBJECT-TYPE
            SYNTAX SEQUENCE OF Dot1xExtVlanPolicyEntry
            MAX-ACCESS not-accessible
            STATUS current
            DESCRIPTION
                "Table of dot1x guest vlan configuration."
            ::= { dot1xExt 2 }

    dot1xExtVlanPolicyEntry OBJECT-TYPE
        SYNTAX Dot1xExtVlanPolicyEntry
        MAX-ACCESS not-accessible
        STATUS current
        DESCRIPTION
            "Entry of dot1x guest vlan configuration."
        INDEX { dot1xExtVlanPolicyIndex}
        ::= { dot1xExtVlanPolicyTable 1 }

    Dot1xExtVlanPolicyEntry ::=
        SEQUENCE
        {
            dot1xExtVlanPolicyIndex
                Integer32,
            dot1xExtGuestVlan
                Integer32
         }

    dot1xExtVlanPolicyIndex OBJECT-TYPE
        SYNTAX Integer32    (1..2147483647)
        MAX-ACCESS not-accessible
        STATUS current
        DESCRIPTION "Index."
        ::= { dot1xExtVlanPolicyEntry 1 }

    dot1xExtGuestVlan OBJECT-TYPE
        SYNTAX Integer32 (0|2..4094)
        MAX-ACCESS read-only
        STATUS current
        DESCRIPTION "When you configure a guest VLAN, clients that are not IEEE 802.1x-capable
                     are put into the guest VLAN when the server does not receive a response to
                     its EAP request/identity frame. Clients that are IEEE 802.1x-capable but
                     fail authentication not granted network access.The vlan range is
                     between [2-4094], 0 means guest vlan is not configured."
        DEFVAL {0}
        ::= { dot1xExtVlanPolicyEntry 2 }


-- IEEE 802.1X global resource
dot1xExtMacBasedResource     OBJECT IDENTIFIER ::= { dot1xExt 3 }
dot1xExtMacBasedResourceMaxInterface OBJECT-TYPE
    SYNTAX          Integer32
    MAX-ACCESS      read-only
    STATUS          current
    DESCRIPTION
        "Max count of dot1x mac based interface. "
    ::= { dot1xExtMacBasedResource 1 }

dot1xExtMacBasedResourceCurrentInterface OBJECT-TYPE
    SYNTAX          Integer32
    MAX-ACCESS      read-only
    STATUS          current
    DESCRIPTION
        "Current count of dot1x mac based interface. "
    ::= { dot1xExtMacBasedResource 2 }

dot1xExtMacBasedResourceMaxUser OBJECT-TYPE
    SYNTAX          Integer32
    MAX-ACCESS      read-only
    STATUS          current
    DESCRIPTION
        "Max count of dot1x mac based users (only include hardware accept or reject entries). "
    ::= { dot1xExtMacBasedResource 3 }

dot1xExtMacBasedResourceCurrentUser OBJECT-TYPE
    SYNTAX          Integer32
    MAX-ACCESS      read-only
    STATUS          current
    DESCRIPTION
        "Current count of dot1x mac based users (only include hardware accept or reject entries). "
    ::= { dot1xExtMacBasedResource 4 }

dot1xExtMacBasedResourceMaxUserAll OBJECT-TYPE
    SYNTAX          Integer32
    MAX-ACCESS      read-only
    STATUS          current
    DESCRIPTION
        "Max count of all dot1x mac based users (include waiting entries). "
    ::= { dot1xExtMacBasedResource 5 }

dot1xExtMacBasedResourceCurrentUserAll OBJECT-TYPE
    SYNTAX          Integer32
    MAX-ACCESS      read-only
    STATUS          current
    DESCRIPTION
        "Current count of all dot1x mac based users (include waiting entries). "
    ::= { dot1xExtMacBasedResource 6 }

-- IEEE 802.1X Mac based config
dot1xExtMacBasedConfigTable OBJECT-TYPE
    SYNTAX SEQUENCE OF Dot1xExtMacBasedConfigEntry
    MAX-ACCESS not-accessible
    STATUS current
    DESCRIPTION
        "table of dot1x mac based interface."
    ::= { dot1xExt 4 }
 
dot1xExtMacBasedConfigEntry OBJECT-TYPE
    SYNTAX Dot1xExtMacBasedConfigEntry
    MAX-ACCESS not-accessible
    STATUS current
    DESCRIPTION
        "Dot1x mac based interface entry"
    INDEX { dot1xExtMacBasedConfigIndex}
    ::= { dot1xExtMacBasedConfigTable 1 }

Dot1xExtMacBasedConfigEntry ::=
    SEQUENCE
    {
       dot1xExtMacBasedConfigIndex
           Integer32,
       dot1xExtMacBasedConfigMode
           INTEGER,
       dot1xExtMacBasedConfigBypassEn
           INTEGER,
       dot1xExtMacBasedConfigMaxUser
           Integer32,
       dot1xExtMacBasedConfigCurrentUser
           Integer32, 
       dot1xExtMacBasedConfigMaxUserAll
           Integer32,
       dot1xExtMacBasedConfigCurrentUserAll
           Integer32
    }
         
dot1xExtMacBasedConfigIndex OBJECT-TYPE
    SYNTAX Integer32    (1..2147483647)
    MAX-ACCESS not-accessible
    STATUS current
    DESCRIPTION "Index of interface."
    ::= { dot1xExtMacBasedConfigEntry 1 }
         
dot1xExtMacBasedConfigMode OBJECT-TYPE
    SYNTAX INTEGER
    {
        port(0),
        mac(1)
    }
    MAX-ACCESS read-write
    STATUS current
    DESCRIPTION "Dot1x port mode. 0: dot1x port based mode. 1: dot1x mac based mode."
    DEFVAL{port}
    ::= { dot1xExtMacBasedConfigEntry 2 }

dot1xExtMacBasedConfigBypassEn OBJECT-TYPE
    SYNTAX INTEGER
    {
        disable(0),
        enable(1)
    }
    MAX-ACCESS read-write
    STATUS current
    DESCRIPTION "Dot1x mac auth bypass function. 0: disable. 1: enable"
    DEFVAL{disable}    
    ::= { dot1xExtMacBasedConfigEntry 3 }
    
dot1xExtMacBasedConfigMaxUser OBJECT-TYPE
    SYNTAX Integer32    (1..255)
    MAX-ACCESS read-write
    STATUS current
    DESCRIPTION "Max user number of the port (only include hardware accept or reject entries).
        Default: by default the max user number of the port is same as the max user number of the system. Different TCAM proflies have different default values."
    ::= { dot1xExtMacBasedConfigEntry 4 }
    
dot1xExtMacBasedConfigCurrentUser OBJECT-TYPE
    SYNTAX Integer32    (0..255)
    MAX-ACCESS read-only
    STATUS current
    DESCRIPTION "Current user number of the port (only include hardware accept or reject entries)"
    DEFVAL{0}   
    ::= { dot1xExtMacBasedConfigEntry 5 }
    
dot1xExtMacBasedConfigMaxUserAll OBJECT-TYPE
    SYNTAX Integer32    (1..510)
    MAX-ACCESS read-only
    STATUS current
    DESCRIPTION "Max user number of the port (include waiting entries)"
    ::= { dot1xExtMacBasedConfigEntry 6 }
    
dot1xExtMacBasedConfigCurrentUserAll OBJECT-TYPE
    SYNTAX Integer32    (0..510)
    MAX-ACCESS read-only
    STATUS current
    DESCRIPTION "Current user number of the port (include waiting entries)
        Default: by default the max user number of the port is same as the max user number of the system. Different TCAM proflies have different default values.
        It should be 2 times large as the max hardware entries number, please reference to  dot1xExtMacBasedConfigCurrentUser."
    DEFVAL{0}  
    ::= { dot1xExtMacBasedConfigEntry 7 }  

-- IEEE 802.1X Mac based user entry
dot1xExtMacBasedUserTable OBJECT-TYPE
    SYNTAX SEQUENCE OF Dot1xExtMacBasedUserEntry
    MAX-ACCESS not-accessible
    STATUS current
    DESCRIPTION
        "table of dot1x mac based users."
    ::= { dot1xExt 5 }
 
dot1xExtMacBasedUserEntry OBJECT-TYPE
    SYNTAX Dot1xExtMacBasedUserEntry
    MAX-ACCESS not-accessible
    STATUS current
    DESCRIPTION
        "Dot1x mac based user entry"
    INDEX { dot1xExtMacBasedUserIndex, dot1xExtMacBasedUserMac}
    ::= { dot1xExtMacBasedUserTable 1 }

Dot1xExtMacBasedUserEntry ::=
    SEQUENCE
    {
       dot1xExtMacBasedUserIndex
           Integer32,
       dot1xExtMacBasedUserMac
           MacAddress,
       dot1xExtMacBasedUserState
           INTEGER,
       dot1xExtMacBasedUserTimer
           Integer32,
       dot1xExtMacBasedUserIsBypass
           INTEGER,
       dot1xExtMacBasedUserInGuestVlan
           INTEGER,
       dot1xExtMacBasedUserGuestVlanID
           Integer32,
       dot1xExtMacBasedUserOffLine
           INTEGER
    }

dot1xExtMacBasedUserIndex OBJECT-TYPE
    SYNTAX Integer32    (1..2147483647)
    MAX-ACCESS not-accessible
    STATUS current
    DESCRIPTION "Index of interface."
    ::= { dot1xExtMacBasedUserEntry 1 }
    
dot1xExtMacBasedUserMac OBJECT-TYPE
    SYNTAX MacAddress
    MAX-ACCESS not-accessible
    STATUS current
    DESCRIPTION "Mac address of user"
    ::= { dot1xExtMacBasedUserEntry 2 }
    
dot1xExtMacBasedUserState OBJECT-TYPE
    SYNTAX INTEGER
    {
        waiting(0),
        accept(1),
        reject(2),
        reauth(3)
    }
    MAX-ACCESS read-only
    STATUS current
    DESCRIPTION "State of the mac based user entry."
    ::= { dot1xExtMacBasedUserEntry 3 }    

dot1xExtMacBasedUserTimer OBJECT-TYPE
    SYNTAX Integer32    (1..2147483647)
    MAX-ACCESS read-only
    STATUS current
    DESCRIPTION "Time (seconds) before state changed. "
    ::= { dot1xExtMacBasedUserEntry 4 }

dot1xExtMacBasedUserIsBypass OBJECT-TYPE
    SYNTAX INTEGER
    {
        eapolUser(0),
        bypassUser(1)
    }
    MAX-ACCESS read-only
    STATUS current
    DESCRIPTION "Log on Method of the user."
    ::= { dot1xExtMacBasedUserEntry 5 }

dot1xExtMacBasedUserInGuestVlan OBJECT-TYPE
    SYNTAX INTEGER
    {
        no(0),
        yes(1)
    }
    MAX-ACCESS read-only
    STATUS current
    DESCRIPTION "If user is in guest vlan."
    ::= { dot1xExtMacBasedUserEntry 6 }   

dot1xExtMacBasedUserGuestVlanID OBJECT-TYPE
    SYNTAX          Integer32(0|2..4094)
    MAX-ACCESS read-only
    STATUS current
    DESCRIPTION "The guest vlan id. If the user is not authenticated by guest vlan, the id should be 0."
    ::= { dot1xExtMacBasedUserEntry 7 } 

dot1xExtMacBasedUserOffLine OBJECT-TYPE
    SYNTAX          INTEGER
    {
        none(0),
        offLine(1)
    }
    MAX-ACCESS      read-write
    STATUS          current
    DESCRIPTION
        "Use this node to force a MAC user off line.
        The default value is 0.
        If this node's value is set to 1, the user should be forced offline and this entry should be deleted. 
        "
    DEFVAL {none}
    ::= { dot1xExtMacBasedUserEntry 8 }


dot1xExtMacBasedClear     OBJECT IDENTIFIER ::= { dot1xExt 6 }
dot1xExtMacBasedClearInterface OBJECT-TYPE
    SYNTAX          Integer32
    MAX-ACCESS      read-write
    STATUS          current
    DESCRIPTION
        "Specify a interface to clear all mac users. "
    ::= { dot1xExtMacBasedClear 1 }

-- Sub Module: TRNG


--
-- Node definitions
--

trngMibObjects OBJECT IDENTIFIER    ::= { timeRange 1 }


trngCreateTimerangeTable         OBJECT-TYPE
    SYNTAX          SEQUENCE OF TrngCreateTimerangeEntry
    MAX-ACCESS      not-accessible
    STATUS          current
    DESCRIPTION
        "Creat TimeRange."
    ::= { trngMibObjects 1 }


trngCreateTimerangeEntry         OBJECT-TYPE
    SYNTAX          TrngCreateTimerangeEntry
    MAX-ACCESS      not-accessible
    STATUS          current
    DESCRIPTION
        "Define the entry of trngCreateTimerangeTable."
    INDEX     { trngIndex }
    ::= { trngCreateTimerangeTable 1 }


TrngCreateTimerangeEntry    ::=
    SEQUENCE
    {
        trngIndex
            Integer32,
        trngName
            OCTET STRING,
        trngValidFlag
            TruthValue,
        trngCreateRowStatus
            RowStatus
    }

trngIndex         OBJECT-TYPE
    SYNTAX          Integer32 (1..256)
    MAX-ACCESS      not-accessible
    STATUS          current
    DESCRIPTION
        "TimeRange's index."
    ::= { trngCreateTimerangeEntry 1 }


trngName         OBJECT-TYPE
    SYNTAX          OCTET STRING (SIZE (1..20))
    MAX-ACCESS      read-create
    STATUS          current
    DESCRIPTION
        "TimeRange's name        "
    ::= { trngCreateTimerangeEntry 2 }


trngValidFlag         OBJECT-TYPE
    SYNTAX          TruthValue
    MAX-ACCESS      read-only
    STATUS          current
    DESCRIPTION
        "Valid or invalid flag."
    ::= { trngCreateTimerangeEntry 3 }


trngCreateRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { trngCreateTimerangeEntry 4 }


trngAbsoluteTable         OBJECT-TYPE
    SYNTAX          SEQUENCE OF TrngAbsoluteEntry
    MAX-ACCESS      not-accessible
    STATUS          current
    DESCRIPTION
        "Creat absoluteness time item of the TimeRange."
    ::= { trngMibObjects 2 }


trngAbsoluteEntry         OBJECT-TYPE
    SYNTAX          TrngAbsoluteEntry
    MAX-ACCESS      not-accessible
    STATUS          current
    DESCRIPTION
        "Define the entry of trngAbsoluteTable."
    INDEX     { trngAbsoluteNameIndex }
    ::= { trngAbsoluteTable 1 }


TrngAbsoluteEntry    ::=
    SEQUENCE {
            trngAbsoluteNameIndex
                Integer32,
            timerangeAbsoluteStartTime
                OCTET STRING,
            timerangeAbsoluteEndTime
                OCTET STRING,
            timerangeAbsolueRowStatus 
                RowStatus 
         }

trngAbsoluteNameIndex         OBJECT-TYPE
    SYNTAX          Integer32 (1..256)
    MAX-ACCESS      not-accessible
    STATUS          current
    DESCRIPTION
        "TimeRange's index."
    ::= { trngAbsoluteEntry 1 }

timerangeAbsoluteStartTime         OBJECT-TYPE
    SYNTAX          OCTET STRING (SIZE (1..128))
    MAX-ACCESS      read-create
    STATUS          current
    DESCRIPTION
        "Start point of the timerange.The format defined like 'hh:mm:ss,Mon/D/YYYY'.
        The Month of the year should be First three letters of the month."
    ::= { trngAbsoluteEntry 2 }


timerangeAbsoluteEndTime         OBJECT-TYPE
    SYNTAX          OCTET STRING (SIZE (1..128))
    MAX-ACCESS      read-create
    STATUS          current
    DESCRIPTION
        "End point of the timerange.The format defined like 'hh:mm:ss,Mon/D/YYYY'.
        The Month of the year should be First three letters of the month."
    ::= { trngAbsoluteEntry 3 }


timerangeAbsolueRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { trngAbsoluteEntry 4 }


trngPeriodicTable         OBJECT-TYPE
    SYNTAX          SEQUENCE OF TrngPeriodicEntry
    MAX-ACCESS      not-accessible
    STATUS          current
    DESCRIPTION
        "Creat periodic time item of the TimeRange."
    ::= { trngMibObjects 3 }


trngPeriodicEntry         OBJECT-TYPE
    SYNTAX          TrngPeriodicEntry
    MAX-ACCESS      not-accessible
    STATUS          current
    DESCRIPTION
        "Define the index of trngPeriodicTable."
    INDEX     { trngPeriodicNameIndex }
    ::= { trngPeriodicTable 1 }


TrngPeriodicEntry    ::=
    SEQUENCE {
            trngPeriodicNameIndex
                Integer32,
            trngPeriodicStartDayOfWeek
                Integer32,
            trngPeriodicEndDayOfWeek
                Integer32,
            timerangePeriodicStartTime
                OCTET STRING,
            timerangePeriodicEndTime
                OCTET STRING,
            timerangePeriodicRowStatus 
                RowStatus 
         }

trngPeriodicNameIndex         OBJECT-TYPE
    SYNTAX          Integer32 (1..256)
    MAX-ACCESS      not-accessible
    STATUS          current
    DESCRIPTION
        "TimeRange's index."
    ::= { trngPeriodicEntry 1 }

trngPeriodicStartDayOfWeek         OBJECT-TYPE
    SYNTAX          Integer32 (1..10)
    MAX-ACCESS      read-create
    STATUS          current
    DESCRIPTION
        "The start day of week.
            1        monday                 
            2        tuesday                
            3        wednesday              
            4        thursday               
            5        friday                 
            6        saturday               
            7        sunday
            8        daily
            9        weekday
            10        weekend
        "
    ::= { trngPeriodicEntry 2 }

trngPeriodicEndDayOfWeek         OBJECT-TYPE
    SYNTAX          Integer32 (1..7)
    MAX-ACCESS      read-create
    STATUS          current
    DESCRIPTION
        " The end day of week.
            1        monday                 
            2        tuesday                
            3        wednesday              
            4        thursday               
            5        friday                 
            6        saturday               
            7        sunday
        "
    ::= { trngPeriodicEntry 3 }

timerangePeriodicStartTime         OBJECT-TYPE
    SYNTAX          OCTET STRING (SIZE (1..128))
    MAX-ACCESS      read-create
    STATUS          current
    DESCRIPTION
        "Start point of this timerange,The format defined like 'hh:mm'."
    ::= { trngPeriodicEntry 4 }


timerangePeriodicEndTime         OBJECT-TYPE
    SYNTAX          OCTET STRING (SIZE (1..128))
    MAX-ACCESS      read-create
    STATUS          current
    DESCRIPTION
        "End point of this timerange.The format defined like 'hh:mm'."
    ::= { trngPeriodicEntry 5 }


timerangePeriodicRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { trngPeriodicEntry 6 }

-- Sub Module: STPEXTENSIONS


BridgeId    ::= TEXTUAL-CONVENTION
    STATUS          current
    DESCRIPTION
        "The Bridge-Identifier, as used in the Spanning Tree
        Protocol, to uniquely identify a bridge.Its first two
        octets (in network byte order) contain a priority value,
        and its last 6 octets contain the MAC address used to
        refer to a bridge in a unique fashion (typically, the
        numerically smallest MAC address of all ports on the
        bridge)."
    SYNTAX          OCTET STRING (SIZE (8))

                  
stpExtStpEnable     OBJECT-TYPE
    SYNTAX          INTEGER {enabled(1),disabled(2)}
    MAX-ACCESS      read-write
    STATUS          current
    DESCRIPTION
        "An indication of whether spanning tree protocol is  enabled on the device or not.
        The meanings of the values are:
        enabled(1) -  Enable spanning tree protocol;
        disabled(2) - Disable spanning tree protocol."  
    ::= { stpExt 1 }
           
           
stpExtPathcostStandard         OBJECT-TYPE
    SYNTAX          INTEGER { dot1d1998(1), dot1t(2)}
    MAX-ACCESS      read-write
    STATUS          current
    DESCRIPTION
        "Indicates the administrative spanning tree path cost mode configured on device.
        The meanings of the values are:
        dot1d1998(1) -  the standard of path cost is IEEE 802.1D-1998 standard;
        dot1t(2)      -  the standard of path cost is IEEE 802.1T standard."
     
    ::= { stpExt 2 }
           
           
stpExtBpduGuard     OBJECT-TYPE
    SYNTAX          INTEGER {enabled(1),disabled(2)}
    MAX-ACCESS      read-write
    STATUS          current
    DESCRIPTION
        "An indication of whether the BpduGuard is enabled on the device or not.
        The meanings of the values are:
        enable(1) - Enable bpdu-guard globally;  
        disabled(2) - Disable bpdu-guard globally." 
    ::= { stpExt 3 }       
           
stpExtBpduFilter    OBJECT-TYPE
    SYNTAX          INTEGER {enabled(1),disabled(2)}
    MAX-ACCESS      read-write
    STATUS          current
    DESCRIPTION
        "An indication of whether the BpduFilter is enabled on the device or not.
        The meanings of the values are:
        enable(1) - Enable bpdu-filter globally;  
        disabled(2) - Disable bpdu-filter globally." 
    ::= { stpExt 4 }
    
           
stpExtBpduTransparent         OBJECT-TYPE
    SYNTAX          INTEGER {enabled(1),disabled(2)}
    MAX-ACCESS      read-write
    STATUS          obsolete
    DESCRIPTION
        "An indication of whether the BpduTransparent is enabled on the device or not.
        If BPDU transparent is enabled(1), Bridge should forward BPDUs as common data 
        packets; If BPDU transparent is disabled(2), Bridge should send BPDUs to CPU 
        and discard BPDUs.The default value is disabled(2)."
    ::= { stpExt 5 }
           
stpExtPortTable     OBJECT-TYPE
    SYNTAX          SEQUENCE OF StpExtPortEntry
    MAX-ACCESS      not-accessible
    STATUS          current
    DESCRIPTION
        "A table that contains extended stp information."   
    ::= { stpExt 6 }
           
stpExtPortEntry     OBJECT-TYPE
    SYNTAX          StpExtPortEntry
    MAX-ACCESS      not-accessible
    STATUS          current
    DESCRIPTION
        "A list of extended stp information maintained by each port."
    INDEX     { stpxpPortIndex  }
    ::= { stpExtPortTable 1 }
           
StpExtPortEntry    ::=
    SEQUENCE 
    {
       stpxpPortIndex
           InterfaceIndex,               
       stpxRootGuardObjects 
           INTEGER,
       stpxRestrictedTcnObjects
           INTEGER,
       stpxRestrictedRoleObjects
           INTEGER,
       stpxEdgePortAdminBpduGuardObjects
           INTEGER,
       stpxEdgePortOperBpduGuardObjects
           INTEGER,
       stpxEdgePortAdminBpduFilterObjects
           INTEGER,
       stpxEdgePortOperBpduFilterObjects
           INTEGER,
       stpxForceVersionObjects
           INTEGER,
       stpxLoopGuardObjects 
           INTEGER
    }
    
stpxpPortIndex      OBJECT-TYPE
    SYNTAX          InterfaceIndex
    MAX-ACCESS      not-accessible
    STATUS          current
    DESCRIPTION
        "The port number of the port for which this entry contains bridge 
        management information."    
    ::= { stpExtPortEntry 1 }
                   
stpxRootGuardObjects         OBJECT-TYPE
    SYNTAX          INTEGER {enabled(1),disabled(2)}
    MAX-ACCESS      read-write
    STATUS          current
    DESCRIPTION
        "An indication of whether the RootGuard capability is enabled 
        on this port or not.
        When a port's root guard is  enabled(1) , if this port receives 
        a superior BPDU, this port should be set to discarding state.
        The default value is disabled(2)."   
    ::= { stpExtPortEntry 2 }
           
stpxRestrictedTcnObjects         OBJECT-TYPE
    SYNTAX          INTEGER {enabled(1),disabled(2)}
    MAX-ACCESS      read-write
    STATUS          current
    DESCRIPTION
        "An indication of whether the RestrictedTcn capability is 
        enabled on this port or not.
        If restricted TCN is enabled(1) on a port , this port should 
        not propagate received topology change notifications and topology 
        changes to other Ports.The default value is disabled(2)."
    ::= { stpExtPortEntry 3 }
           
stpxRestrictedRoleObjects         OBJECT-TYPE
    SYNTAX          INTEGER {enabled(1),disabled(2)}
    MAX-ACCESS      read-write
    STATUS          current
    DESCRIPTION
        "An indication of whether the RestrictedRole capability is enabled on 
        this port or not. If restricted Role is enabled(1) on a port,
        this Port should not to be selected as Root Port ; 
        even it has the best spanning tree priority vector.The default value 
        is disabled(2)."
    ::= { stpExtPortEntry 4 }
           
stpxEdgePortAdminBpduGuardObjects         OBJECT-TYPE
    SYNTAX          INTEGER 
    {
        default(0),
        enabled(1),
        disabled(2)
    }
    MAX-ACCESS      read-write
    STATUS          current
    DESCRIPTION
        "An indication of whether the administrative BpduGuard capability is 
        enabled on this port or not.
        If an edge port's bpdu guard is enable(1) ,when this port receives 
        a BPDU, this port should be set into error-disabled state; 
        If an edge port's bpdu guard is default(0) , this port's 
        stpxEdgePortOperBpduGuardObjects determined in accordance with  
        stpExtBpduGuard.The default value is default(0)."     
    ::= { stpExtPortEntry 5 } 
         
stpxEdgePortOperBpduGuardObjects         OBJECT-TYPE
    SYNTAX          INTEGER {enabled(1),disabled(2)}
    MAX-ACCESS      read-only
    STATUS          current
    DESCRIPTION
        "The operational value of the edge port's bpdu guard parameter.
        If stpxEdgePortAdminBpduGuardObjects is set to default(0), 
        then the value of stpxEdgePortOperBpduGuardObjects is determined in 
        accordance with stpExtBpduGuard."    
    ::= { stpExtPortEntry 6 }
    
stpxEdgePortAdminBpduFilterObjects         OBJECT-TYPE
    SYNTAX          INTEGER {default(0),enabled(1),disabled(2)}
    MAX-ACCESS      read-write
    STATUS          current
    DESCRIPTION
        "An indication of whether the administrative BpduFilter capability 
        is enabled on this port or not.
        If an edge port's bpdu filter is disabled(2) , this port should 
        transmit and receive BPDUs; 
        if an edge port's bpdu filter is enabled(1) , this port should 
        not transmit and receive any BPDU.
        if an edge port's bpdu filter is default(0) , this port's 
        stpxEdgePortOperBpduFilterObjectsisdetermined in accordance with 
        stpExtBpduFilter.The default value is default(0)."          
    ::= { stpExtPortEntry 7 }       
           
stpxEdgePortOperBpduFilterObjects         OBJECT-TYPE
    SYNTAX          INTEGER {enabled(1),disabled(2)}
    MAX-ACCESS      read-only
    STATUS          current
    DESCRIPTION
        "The operational value of the edge port's bpdu filter parameter.
        If stpxEdgePortAdminBpduFilterObjects is set to default(0), 
        then the value  of stpxEdgePortOperBpduFilterObjects is determined in 
        accordance with stpExtBpduFilter."    
    ::= { stpExtPortEntry 8 }

    
stpxForceVersionObjects         OBJECT-TYPE
    SYNTAX          INTEGER {stp(0),rstp(2),mstp(3)}
    MAX-ACCESS      read-write
    STATUS          current
    DESCRIPTION
        "A Force Protocol Version parameter, controlled by management, 
        instructs MSTP to emulate additional aspects of the behavior of 
        earlier versions of spanning tree protocol that are not strictly 
        required for interoperability.The value of this parameter applies 
        to all Ports of the Bridge."    
    ::= { stpExtPortEntry 9 }
    
stpxLoopGuardObjects         OBJECT-TYPE
    SYNTAX          INTEGER {enabled(1),disabled(2)}
    MAX-ACCESS      read-write
    STATUS          current
    DESCRIPTION
        "An indication of whether the LoopGuard capability is enabled 
        on this port or not.
        When a port's loop guard is  enabled(1) , and BPDUs are not received
        on a non-designated port after max_age, that port should move into
        the STP loop-inconsistent blocking state and should not pass user traffic.
        The default value is disabled(2)."   
    ::= { stpExtPortEntry 10 } 
    
stpExtTrapEnable         OBJECT-TYPE
    SYNTAX          INTEGER {enabled(1),disabled(2)}
    MAX-ACCESS      read-write
    STATUS          obsolete
    DESCRIPTION
        "An indication of whether spanning tree protocol trap is enabled 
        on the device or not. The meanings of the values are:
        enabled(1) -  Enable spanning tree protocol trap;
        disabled(2) - Disable spanning tree protocol trap." 
    ::= { stpExt 7 }       
           
stpExtMaxhops OBJECT-TYPE
    SYNTAX          INTEGER
    MAX-ACCESS      read-write
    STATUS          current
    DESCRIPTION 
        "The max hops of spanning tree protocol, 
        its range is <1-40> and default value is 20"
    ::= {stpExt 8 }

--
-- MIB for IEEE 802.1s Multiple Spanning Tree Protocol
--
    
mstpExt OBJECT IDENTIFIER    ::= { stpExt 10 }
        
        
        
stpVersion         OBJECT-TYPE
    SYNTAX          INTEGER 
    {
        stp(1),
        rstp(2),
        mstp(3)
    }
    MAX-ACCESS      read-write
    STATUS          current
    
    DESCRIPTION
        "The version of Spanning Tree Protocol the bridge is
        currently running.The value 'stpCompatible(1)'
        indicates the Spanning Tree Protocol specified in
        IEEE 802.1D-1998 ,'rstp(2)' indicates the Rapid
        Spanning Tree Protocol specified in IEEE 802.1w and
        clause 17 of 802.1D-2004,'mstp(3)'indicates the Multiple
        Spanning Tree Protocol specified in IEEE 802.1s 
        .The values are directly from the IEEE standard.
        New values may be defined as future versions of
        the protocol become available."          
--  DEFVAL    INDEX     { rstp }
    ::= { mstpExt 1 }
           
        
stpRegionName         OBJECT-TYPE
    SYNTAX          OCTET STRING (SIZE (0..32))
    MAX-ACCESS      read-write
    STATUS          current
    DESCRIPTION
        "The configuration name that identifies the MST
        region and is used as one of the inputs in the 
        computation of the MST Configuration Identifier.
        This object does not have any default value."
    REFERENCE
        "IEEE 802.1s clause 13.7"
    ::= { mstpExt 2 }   
             
stpRevision         OBJECT-TYPE
    SYNTAX          Integer32 (0..255)
    MAX-ACCESS      read-write
    STATUS          current
    DESCRIPTION
        "This object identifies the MST revision that 
        identifies the MST region and is used as one
        of the inputs in the computation of the MST 
        configuration Identifier.This object does not
        have any default value."
    REFERENCE
        "IEEE 802.1s: Section 13.7"
    ::= { mstpExt 3 }       
        
stpVlanTable        OBJECT-TYPE
    SYNTAX          SEQUENCE OF StpVlanEntry
    MAX-ACCESS      not-accessible
    STATUS          current
    DESCRIPTION
        "A table that contains MSTI-VLAN mapping.
        This release supports up to 16 instances;
        each spanning tree instance is identified
        by an instance ID that ranges from 0 to 4094.
        Instance 0 is mandatory and is always present."
    ::= { mstpExt  4 }
                  
stpVlanEntry        OBJECT-TYPE
    SYNTAX          StpVlanEntry
    MAX-ACCESS      not-accessible
    STATUS          current
    DESCRIPTION
        "A list of information maintained by every MST instance 
        about the VLANs mapped to that instance."
    INDEX     { stpVlanInstId }
    ::= { stpVlanTable 1 }
    
StpVlanEntry    ::=
    SEQUENCE 
    {
        stpVlanId 
            Integer32, 
        stpVlanInstId
            Integer32
    }
            
stpVlanId           OBJECT-TYPE
    SYNTAX          Integer32 (1..4094)
    MAX-ACCESS      not-accessible
    STATUS          current
    DESCRIPTION
        "This is the index to the MSTI-VLAN Table."
    REFERENCE
        "IEEE 802.1s"
    ::= { stpVlanEntry 1 }
     
stpVlanInstId       OBJECT-TYPE
    SYNTAX          Integer32 (0..4094)
    MAX-ACCESS      read-write
    STATUS          current
    DESCRIPTION
        "Identifier of this MST Instance."
    REFERENCE
        "IEEE 802.1s"
    ::= { stpVlanEntry 2 }
    
    
stpInstTable        OBJECT-TYPE
    SYNTAX          SEQUENCE OF StpInstEntry 
    MAX-ACCESS      not-accessible
    STATUS          current
    DESCRIPTION
        "A table that contains MST instance-specific
        configuration and operational information."
    ::= { mstpExt 5 }
     
stpInstEntry        OBJECT-TYPE
    SYNTAX          StpInstEntry
    MAX-ACCESS      not-accessible
    STATUS          current
    DESCRIPTION
        "A list of information maintained by every mst instance
        about the STP topology for that instance."
    INDEX     { stpInstId }    
    ::= { stpInstTable 1 }
        
StpInstEntry    ::=
    SEQUENCE 
    {
        stpInstId
            Integer32, 
        stpPriority                     
            Integer32,        
        stpInstDesignatedRoot           
            BridgeId,
        stpInstRootCost                 
            Integer32,
        stpInstRootPort                 
            Integer32
    }
    
stpInstId           OBJECT-TYPE
    SYNTAX          Integer32 (1..4094)
    MAX-ACCESS      not-accessible
    STATUS          current
    DESCRIPTION
        "Identifier of this MST Instance.
         MST establishes and maintains additional
         spanning trees withineach MST region.
         These spanning trees are referred to as
         MST instances (MSTIs)."
    REFERENCE
        "IEEE 802.1s"
    ::= { stpInstEntry 1 }
        
stpPriority         OBJECT-TYPE
    SYNTAX          Integer32 (0..61440)
    MAX-ACCESS      read-write
    STATUS          current
    DESCRIPTION
        "The lower the priority of the bridge, the higher likelihood of the bridge becoming a root bridge or a designated bridge for the LAN. The permitted range of values is 0-61440. The priority values must be in multiples of 4096."
    
    REFERENCE        
        "IEEE 802.1s: Section 13.23.2"
--  DEFVAL      { 32768 }
    ::= { stpInstEntry 2 }
    
stpInstDesignatedRoot         OBJECT-TYPE
    SYNTAX          BridgeId
    MAX-ACCESS      read-only
    STATUS          current
    DESCRIPTION
        "The bridge identifier of the root of the 
         corresponding spanning tree instance as determined
         by the Spanning Tree Protocol for that instance.
         This value is used as the CIST Root Identifier or MSTI
         regional root identifier parameter in all MST BPDUs 
         originated by this node."
    REFERENCE
        "IEEE 802.1s: Section 13.23.6, 13.23.12"
    ::= { stpInstEntry 3 }
stpInstRootCost         OBJECT-TYPE
    SYNTAX          Integer32
    MAX-ACCESS      read-only
    STATUS          current
    DESCRIPTION
        "The cost of the path to the root as seen from
        this bridge for this instance."
    REFERENCE
        "IEEE 802.1s: Section 13.23.6, 13.23.12"
    ::= { stpInstEntry 4 }
        
stpInstRootPort     OBJECT-TYPE
    SYNTAX          Integer32
    MAX-ACCESS      read-only
    STATUS          current
    DESCRIPTION
        "The port number of the port which offers the
        lowest cost path from this bridge to the root
        bridge for this instance."
    REFERENCE
        "IEEE 802.1s: Section 13.23.6, 13.23.12"
    ::= { stpInstEntry 5 } 
        
        
stpInstPortTable    OBJECT-TYPE
    SYNTAX          SEQUENCE OF StpInstPortEntry
    MAX-ACCESS      not-accessible
    STATUS          current
    DESCRIPTION
        "A table that contains MST port and instance information."
    ::= { mstpExt 6 }
    
stpInstPortEntry    OBJECT-TYPE
    SYNTAX          StpInstPortEntry
    MAX-ACCESS      not-accessible
    STATUS          current
    DESCRIPTION
        "A list of information maintained by every MST port 
        for each MST instance it belongs to about the Spanning 
        Tree Protocol state for that port."
    INDEX           { stpInstId, stpxpPortIndex }
    ::= { stpInstPortTable 1 }
    
StpInstPortEntry    ::=
    SEQUENCE 
    {     
        stpInstPortPriority
            Integer32,
        stpInstPortState
            INTEGER,
        stpInstPortPathCost
            Integer32,
        stpInstPortDesignatedRoot
            BridgeId,
        stpInstPortDesignatedCost
            Integer32,
        stpInstPortDesignatedBridge
            BridgeId,
        stpInstPortDesignatedPort
            InterfaceIndex,     
        stpInstPortRole
            INTEGER,
       stpInstRestrictedRole
            INTEGER,
       stpInstRestrictedTcn
            INTEGER
        }
        
stpInstPortPriority         OBJECT-TYPE
    SYNTAX          Integer32 (0..240)
    MAX-ACCESS      read-write
    STATUS          current
    DESCRIPTION
        "The value of the priority field which is
        contained in the most significant 4 bits 
        of the first (in network byte order)
        octet of the (2 octet long) Port ID.As it is
        contained only in 4 bits, the value has to be 
        a multiple of 16.The other octet of the Port 
        ID is given by the value of stpInstPortIndex."
    REFERENCE
        "IEEE 802.1s: Section 13.24.21        "
    ::= { stpInstPortEntry 1 }
        
stpInstPortState         OBJECT-TYPE
    SYNTAX          INTEGER 
    {
        disabled(1),
        discarding(2),
        learning(3),
        forwarding(4)
    }
    MAX-ACCESS      read-only
    STATUS          current
    DESCRIPTION
        "The port'scurrent state as defined by
        application of the Spanning Tree Protocol.This
        state controls what action a port takes on
        reception of a frame.For ports which
        are disabled (see dot1dStpPortEnable), this object
        will have a value of disabled(1)."
    REFERENCE
        "IEEE 802.1s: Section 13.16"
    ::= { stpInstPortEntry 2 }
    
stpInstPortPathCost         OBJECT-TYPE
    SYNTAX          Integer32 (1..200000000)
    MAX-ACCESS      read-write
    STATUS          current
    DESCRIPTION
        "The contribution of this port to the path cost of
        paths towards the spanning tree root which include
        this port.802.1D-1990 recommends that the
        default value of this parameter be in inverse
        proportion to the speed of the attached LAN.
        Path cost in range .(802.1t:1-200000000, 802.1d-1998:1-65535)."
    REFERENCE
        "IEEE 802.1s: Section 13.24.8, 13.24.17"
    ::= { stpInstPortEntry 3 }
    
stpInstPortDesignatedRoot         OBJECT-TYPE
    SYNTAX          BridgeId
    MAX-ACCESS      read-only
    STATUS          current
    DESCRIPTION
        "The unique Bridge Identifier of the Bridge
        recorded as the Root in the Configuration BPDUs
        transmitted by the Designated Bridge for the
        segment to which the port is attached."
    REFERENCE
        "IEEE 802.1s: Section 13.24.4, 13.24.11"
    ::= { stpInstPortEntry 4 }
    
stpInstPortDesignatedCost         OBJECT-TYPE
    SYNTAX          Integer32
    MAX-ACCESS      read-only
    STATUS          current
    DESCRIPTION
        "The path cost of the Designated Port of the
        segment connected to this port.This value is
        compared to the Root Path Cost field in received
        bridge PDUs."
    REFERENCE
        "IEEE 802.1s: Section 13.24.4, 13.24.11"
    ::= { stpInstPortEntry 5 }
        
stpInstPortDesignatedBridge         OBJECT-TYPE
    SYNTAX          BridgeId
    MAX-ACCESS      read-only
    STATUS          current
    DESCRIPTION
        "The Bridge Identifier of the bridge which this
         port considers to be the Designated Bridge for
         this port's segment."
    REFERENCE
        "IEEE 802.1s: Section 13.24.4, 13.24.11"
    ::= { stpInstPortEntry 6 }
    
stpInstPortDesignatedPort         OBJECT-TYPE
    SYNTAX          InterfaceIndex
    MAX-ACCESS      read-only
    STATUS          current
    DESCRIPTION
        "The Port Identifier of the port on the Designated
        Bridge for this port's segment."
    REFERENCE
        "IEEE 802.1s: Section 13.24.4, 13.24.11"
    ::= { stpInstPortEntry 7 }
    
    
stpInstPortRole         OBJECT-TYPE
    SYNTAX          INTEGER 
    {
        master(0),
        alternate(1),
        root(2),
        designated(3),
        disabled(4),
        backup(5)
    }
    MAX-ACCESS      read-only
    STATUS          current
    DESCRIPTION
        "The role of the port.As per IEEE 802.1s, the 
        port can have any of the following roles:
        Disabled, Root, Designated, Alternate, Backup,
        Master."
    REFERENCE
        "IEEE 802.1s: Section 13.24.25"
    ::= { stpInstPortEntry 8 }
        
stpInstRestrictedRole         OBJECT-TYPE
    SYNTAX          INTEGER {enabled(1),disabled(2)}
    MAX-ACCESS      read-write
    STATUS          current
    DESCRIPTION
        "An indication of whether the RestrictedRole capability is 
        enabled on this port or not.
        If restricted Role is enabled(1) on a port,this Port should 
        not to be selected as Root Port ; even it has the best spanning 
        tree priority vector.The default value is disabled(2)."
    ::= { stpInstPortEntry 9 }   
           
stpInstRestrictedTcn         OBJECT-TYPE
    SYNTAX          INTEGER {enabled(1),disabled(2)}
    MAX-ACCESS      read-write
    STATUS          current
    DESCRIPTION
        "An indication of whether the RestrictedTcn capability is enabled 
        on this port or not.
        If restricted TCN is enabled(1) on a port , this port should 
        not propagate received topology change notifications and topology 
        changes to other Ports.The default value is disabled(2)."
    ::= { stpInstPortEntry 10 } 
           
stpInstNum          OBJECT-TYPE
    SYNTAX          Integer32 (0..15)
    MAX-ACCESS      read-only
    STATUS          current
    DESCRIPTION
        "This object identifies the number of mst configured instances."
    ::= { mstpExt 7 }          
     
stpDigests          OBJECT-TYPE
    SYNTAX          OCTET STRING (SIZE (0..32))
    MAX-ACCESS      read-only
    STATUS          current
    DESCRIPTION
        "This object identifies the number of MST Configuration Identification."
    ::= { mstpExt 8 }    
    
-- Sub Module: IGMPEXT

      
igmpRouterInterfaceExtTable         OBJECT-TYPE
    SYNTAX          SEQUENCE OF IgmpRouterInterfaceExtEntry
    MAX-ACCESS      not-accessible
    STATUS          current
    DESCRIPTION
        "table of interface entry."
    ::= { igmpExt 1 }
        
igmpRouterInterfaceExtEntry         OBJECT-TYPE
    SYNTAX          IgmpRouterInterfaceExtEntry
    MAX-ACCESS      not-accessible
    STATUS          current
    DESCRIPTION
        "igmp router interface entry."
    INDEX        { igmpRouterIfIndex, igmpRouterQuerierType}
    ::= { igmpRouterInterfaceExtTable 1 }
        
IgmpRouterInterfaceExtEntry    ::=
    SEQUENCE
    {
        igmpRouterIfIndex
            Integer32,
        igmpRouterQuerierType
            Integer32,
        igmpRouterIfGroupLimit
            Integer32,
        igmpRouterIfImmediateLeaveAccess
            OCTET STRING,     
        igmpRouterIfProxyService 
            TruthValue,
        igmpRouterIfAccess 
            OCTET STRING,                                    
        igmpRouterIfQuerierTimeout
            Integer32,
        igmpRouterIfGroupLimitExceptAccess 
            OCTET STRING,   
         igmpRouterIfClearGrp
            INTEGER
     }

igmpRouterIfIndex   OBJECT-TYPE
    SYNTAX          Integer32 (0..65535)
    MAX-ACCESS      not-accessible
    STATUS          current
    DESCRIPTION    
        "igmp router Interface index."
    ::= { igmpRouterInterfaceExtEntry 1 }

igmpRouterQuerierType         OBJECT-TYPE
    SYNTAX          Integer32 (0..65535)
    MAX-ACCESS      not-accessible
    STATUS          current
    DESCRIPTION        
        "igmp router Interface querier type: ipv4 or ipv6."
    ::= { igmpRouterInterfaceExtEntry 2 }
        
igmpRouterIfGroupLimit         OBJECT-TYPE
    SYNTAX          Integer32(1..8192)
    MAX-ACCESS      read-write
    STATUS          current
    DESCRIPTION        
        "igmp router Interface group limit."
    ::= { igmpRouterInterfaceExtEntry 3 }

igmpRouterIfImmediateLeaveAccess         OBJECT-TYPE
    SYNTAX          OCTET STRING (SIZE(0..256))
    MAX-ACCESS      read-write
    STATUS          current
    DESCRIPTION        
        "Leave groups immediately without sending last member query, 
        use for one host network only."
    ::= { igmpRouterInterfaceExtEntry 4 }

igmpRouterIfProxyService         OBJECT-TYPE
    SYNTAX          TruthValue
    MAX-ACCESS      read-write
    STATUS          current
    DESCRIPTION        
        "Igmp router Interface proxy service .
         True(1),False(2)."
    ::= { igmpRouterInterfaceExtEntry 5 }

igmpRouterIfAccess         OBJECT-TYPE
    SYNTAX          OCTET STRING (SIZE(0..256))
    MAX-ACCESS      read-write
    STATUS          current
    DESCRIPTION        
        "igmp router Interface IGMP group access group."
    ::= { igmpRouterInterfaceExtEntry 6 }
                                            
igmpRouterIfQuerierTimeout         OBJECT-TYPE
    SYNTAX          Integer32(60..300)
    MAX-ACCESS      read-write
    STATUS          current
    DESCRIPTION        
        "igmp router Interface IGMP previous querier timeout."
    DEFVAL { 255 }
    ::= { igmpRouterInterfaceExtEntry 7 }    

igmpRouterIfGroupLimitExceptAccess         OBJECT-TYPE
    SYNTAX          OCTET STRING (SIZE(0..256))
    MAX-ACCESS      read-write
    STATUS          current
    DESCRIPTION        
        "igmp router Interface IGMP group access group, Groups 
        not to be counted."
    ::= { igmpRouterInterfaceExtEntry 8 }

igmpRouterIfClearGrp         OBJECT-TYPE
    SYNTAX          INTEGER
    {
      noUse(0),
      clear(1)
    }
    MAX-ACCESS      read-write
    STATUS          current
    DESCRIPTION        
        "Delete IGMP group cache entries."
    ::= { igmpRouterInterfaceExtEntry 9 }   
        
igmpRouterGobalGrpLimit         OBJECT-TYPE
    SYNTAX          Integer32(1..8192)
    MAX-ACCESS      read-write
    STATUS          current
    DESCRIPTION
        "Igmp router global group limit."
    ::= { igmpExt 2 }

igmpRouterSsmMappingEnable        OBJECT-TYPE
    SYNTAX          INTEGER
    {
        disable(2),
	enable(1)
    }
    MAX-ACCESS      read-write
    STATUS          current
    DESCRIPTION
        "The state of ssm mapping .enable(1), disable(2). Default setting is disable(2)."
    DEFVAL { disable }
    ::= { igmpExt 3 }  

igmpRouterSsmMappingTable OBJECT-TYPE
    SYNTAX  SEQUENCE OF IgmpRouterSsmMappingEntry
    MAX-ACCESS not-accessible
    STATUS   current
    DESCRIPTION 
    	"Configure ssm mapping list. using acl to map to specified source"
    ::= { igmpExt 4 }

igmpRouterSsmMappingEntry OBJECT-TYPE
    SYNTAX  IgmpRouterSsmMappingEntry
    MAX-ACCESS not-accessible
    STATUS current
    DESCRIPTION 
    	"Entry of igmpRouterSsmMappingTable."
    INDEX   { igmpRouterSsmMappingAclName, igmpRouterSsmMappingSourceAddress}
    ::= { igmpRouterSsmMappingTable 1 }

IgmpRouterSsmMappingEntry   ::=
    SEQUENCE {
        igmpRouterSsmMappingIndex 	INTEGER,    
        igmpRouterSsmMappingSourceAddress 	IpAddress,
        igmpRouterSsmMappingAclName   OCTET STRING,
        igmpRouterSsmMappingRowStatus	RowStatus
        }

igmpRouterSsmMappingIndex OBJECT-TYPE
    SYNTAX  INTEGER
    MAX-ACCESS not-accessible
    STATUS current
    DESCRIPTION 
    	"index of  group list mapping (1~32)"
    ::= { igmpRouterSsmMappingEntry 1 }	

igmpRouterSsmMappingSourceAddress OBJECT-TYPE
    SYNTAX  IpAddress
    MAX-ACCESS read-create
    STATUS current
    DESCRIPTION 
    	"source address which group list mapping to"
    ::= { igmpRouterSsmMappingEntry 2 }	

igmpRouterSsmMappingAclName OBJECT-TYPE
    SYNTAX  OCTET STRING (SIZE(1..20))
    MAX-ACCESS read-create
    STATUS current
    DESCRIPTION 
    	"acl name of group list "
    ::= { igmpRouterSsmMappingEntry 3 }

igmpRouterSsmMappingRowStatus OBJECT-TYPE
    SYNTAX  RowStatus
    MAX-ACCESS read-create
    STATUS current
    DESCRIPTION 
    	"The status of this conceptual row.Now only realize CreateAndGo 
            and Destroy and Active.
        1 means Active
        4 means CreateAndGo
        6 means Destroy"
    ::= { igmpRouterSsmMappingEntry 4 }
	
	
-- Sub Module: BOARDHEALTHYMONITOR

--
-- Textual conventions
--
SysmonBootType    ::= TEXTUAL-CONVENTION
    STATUS          current
    DESCRIPTION
        "Specify the place to boot to."
    SYNTAX          INTEGER
    {
        hold(0),
        reload(1)
    }

HBMReactivateType    ::= TEXTUAL-CONVENTION
    STATUS          current
    DESCRIPTION
        "Specify the type to reactive."
    SYNTAX          INTEGER
    {
        warning(0),
        shutdown(1),
        reload(2)
    }

--
-- Node definitions
--
--sysmon OBJECT IDENTIFIER    ::= { boardHealthyMonitor 1 }
            
sysmonEnable        OBJECT-TYPE
    SYNTAX          TruthValue
    MAX-ACCESS      read-write
    STATUS          current
    DESCRIPTION
        "The state of sysmon .enable(1), disable(2). Default setting is enable(1)."
    DEFVAL { enable }
    ::= { boardHealthyMonitor 1 }

heartBeatMonitor OBJECT IDENTIFIER    ::= { boardHealthyMonitor 2 }
     
             
heartBeatMonitorEnable         OBJECT-TYPE
    SYNTAX          TruthValue
    MAX-ACCESS      read-write
    STATUS          current
    DESCRIPTION
        "The state of heart-beat-monitor. enable(1), disable(2). Default setting is enable(1)"
    DEFVAL { enable }
    ::= { heartBeatMonitor 1 }

heartBeatMonitorReactivate         OBJECT-TYPE
    SYNTAX             HBMReactivateType
    MAX-ACCESS         read-write
    STATUS             current
    DESCRIPTION
        "The reactive type of heart-beat-monitor.warning(0), shutdown(1), reload(2). Default setting is reload(2). "
    DEFVAL { reload }
    ::= { heartBeatMonitor 2 }


lastDumpedProcess         OBJECT-TYPE
    SYNTAX             INTEGER(1..65536)
    MAX-ACCESS         read-only 
    STATUS             current
    DESCRIPTION
        "The process id of last dumped process."
    ::= { boardHealthyMonitor 3 }


-- Sub Module: ARPINSP

            
-- arp type value
    ArpType    ::= TEXTUAL-CONVENTION
    STATUS          current
    DESCRIPTION
        "arp's type, request or response."
    SYNTAX          INTEGER
    {    
        request(1),
        response(2),
        all(3)
    }
            
--
-- Node of arpAclGroupTable
--
arpAclGroupTable    OBJECT-TYPE
    SYNTAX          SEQUENCE OF ArpAclGroupEntry
    MAX-ACCESS      not-accessible
    STATUS          current
    DESCRIPTION
        "Configure arp access list."
    ::= { arpInsp 1 }
        

arpAclGroupEntry    OBJECT-TYPE
    SYNTAX          ArpAclGroupEntry
    MAX-ACCESS      not-accessible
    STATUS          current
    DESCRIPTION
        "Define the index of arpAclGroupTable."
    INDEX     { arpAclGroupIndex }
    ::= { arpAclGroupTable 1 }

ArpAclGroupEntry    ::=
    SEQUENCE
    {
        arpAclGroupIndex
            Integer32,
        arpAclGroupName
            OCTET STRING,
        arpAclGroupRowStatus 
            RowStatus 
    }
         

arpAclGroupIndex    OBJECT-TYPE
    SYNTAX          Integer32 (30001..40000)
    MAX-ACCESS      not-accessible
    STATUS          current
    DESCRIPTION
        "The index of arp acl group."
    ::= { arpAclGroupEntry 1 }

arpAclGroupName     OBJECT-TYPE
    SYNTAX          OCTET STRING (SIZE (0..20))
    MAX-ACCESS      read-create
    STATUS          current
    DESCRIPTION
        "The name of arp acl group."
    ::= { arpAclGroupEntry 2 }
        
arpAclGroupRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { arpAclGroupEntry 3 }
        
--
-- Nodes of arpAclRuleTable
--
arpAclRuleTable         OBJECT-TYPE
    SYNTAX          SEQUENCE OF ArpAclRuleEntry
    MAX-ACCESS      not-accessible
    STATUS          current
    DESCRIPTION
        "A table of ARP acl rules."
    ::= { arpInsp 2 }
        
arpAclRuleEntry         OBJECT-TYPE
    SYNTAX          ArpAclRuleEntry
    MAX-ACCESS      not-accessible
    STATUS          current
    DESCRIPTION
        "Arp acl rules information."
    INDEX         { arpAclIndex, arpAclRuleIndex }
    ::= { arpAclRuleTable 1 }
        
    ArpAclRuleEntry    ::=
    SEQUENCE
    {
        arpAclIndex
            Integer32,
        arpAclRuleIndex
            Integer32,
        arpAclAct
            RuleAction,
        arpType
            ArpType,
        arpSenderIp
            IpAddress,
        arpSenderIpWild
            IpAddress,                    
        arpSenderMac
            OCTET STRING,
        arpSenderMacWild
            OCTET STRING,
        arpAclLog
            TruthValue,                
        arpAclRowStatus 
            RowStatus 
     }


arpAclIndex         OBJECT-TYPE
    SYNTAX          Integer32 (30001..40000)
    MAX-ACCESS      not-accessible
    STATUS          current
    DESCRIPTION
        "The index of arp acl group."
    ::= { arpAclRuleEntry 1 }
        
arpAclRuleIndex     OBJECT-TYPE
    SYNTAX          Integer32 (1..131071)
    MAX-ACCESS      not-accessible
    STATUS          current
    DESCRIPTION
        "The rule index of arp acl rule."
    ::= { arpAclRuleEntry 2 }            

arpAclAct           OBJECT-TYPE
    SYNTAX          RuleAction
    MAX-ACCESS      read-create
    STATUS          current
    DESCRIPTION
        "The action of arp acl rule.
        permit(1), deny(2)."
    ::= { arpAclRuleEntry 3 }

arpType             OBJECT-TYPE
    SYNTAX          ArpType
    MAX-ACCESS      read-create
    STATUS          current
    DESCRIPTION
        "The type of arp: request or response or all.
        request(1), response(2), all(3)."       
    ::= { arpAclRuleEntry 4 }            
        
arpSenderIp         OBJECT-TYPE
    SYNTAX          IpAddress
    MAX-ACCESS      read-create
    STATUS          current
    DESCRIPTION
        "The ARP sender IP adress."
    ::= { arpAclRuleEntry 5 } 
        
arpSenderIpWild     OBJECT-TYPE
    SYNTAX          IpAddress
    MAX-ACCESS      read-create
    STATUS          current
    DESCRIPTION
        "The ARP sender IP adress's wild."
    ::= { arpAclRuleEntry 6 }    
        
arpSenderMac        OBJECT-TYPE
    SYNTAX          OCTET STRING
    MAX-ACCESS      read-create
    STATUS          current
    DESCRIPTION
        "The ARP sender mac adress."
    ::= { arpAclRuleEntry 7 }    

arpSenderMacWild    OBJECT-TYPE
    SYNTAX          OCTET STRING
    MAX-ACCESS      read-create
    STATUS          current
    DESCRIPTION
        "The ARP sender mac adress's wild ."
    ::= { arpAclRuleEntry 8 }        
        
arpAclLog           OBJECT-TYPE
    SYNTAX          TruthValue
    MAX-ACCESS      read-create
    STATUS          current
    DESCRIPTION
        "record the log when being matched.
        true(1), false(2)."
    ::= { arpAclRuleEntry 9 }        
        
arpAclRowStatus     OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { arpAclRuleEntry 10 } 

--
-- Nodes of arpAclApplyTable
--
arpAclApplyTable    OBJECT-TYPE
    SYNTAX          SEQUENCE OF ArpAclApplyEntry
    MAX-ACCESS      not-accessible
    STATUS          current
    DESCRIPTION
        "A table of ARP acl applying."
    ::= { arpInsp 3 }         
        
arpAclApplyEntry    OBJECT-TYPE
    SYNTAX          ArpAclApplyEntry
    MAX-ACCESS      not-accessible
    STATUS          current
    DESCRIPTION
        "Arp acl applying information."
    INDEX     { arpAclApplyVid }
    ::= { arpAclApplyTable 1 }        
        
    ArpAclApplyEntry    ::=
    SEQUENCE
    {
        arpAclApplyVid
            Integer32,
        arpAclApplyName
            OCTET STRING,
        arpAclApplyStatic
            TruthValue,
        arpAclApplyRowStatus 
            RowStatus 
     }
         
arpAclApplyVid      OBJECT-TYPE
    SYNTAX          Integer32 (1..4094)
    MAX-ACCESS      not-accessible
    STATUS          current
    DESCRIPTION
        "The vlan id of arp acl applied."
    ::= { arpAclApplyEntry 1 }       

arpAclApplyName     OBJECT-TYPE
    SYNTAX          OCTET STRING (SIZE (0..256))
    MAX-ACCESS      read-create
    STATUS          current
    DESCRIPTION
        "The applied arp acl name."
    ::= { arpAclApplyEntry 2 }     

arpAclApplyStatic      OBJECT-TYPE
    SYNTAX          TruthValue
    MAX-ACCESS      read-create
    STATUS          current
    DESCRIPTION
        "The arp acl applied type is static.
        true(1), false(2)."
    DEFVAL{false}
    ::= { arpAclApplyEntry 3 }  

arpAclApplyRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { arpAclApplyEntry 4 }   
            
--
-- Nodes of arpInspValidateDestMac
--
arpInspValidateDestMac         OBJECT-TYPE
    SYNTAX          TruthValue
    MAX-ACCESS      read-write
    STATUS          current
    DESCRIPTION
        "whether do Validation of arp's dest-mac.
        true(1), false(2)."
    ::= { arpInsp 4 }  

--
-- Nodes of arpInspValidateIP
--
arpInspValidateIP   OBJECT-TYPE
    SYNTAX          TruthValue
    MAX-ACCESS      read-write
    STATUS          current
    DESCRIPTION
        "whether do Validation of arp's IP.
        true(1), false(2)."
    ::= { arpInsp 5 }  

--
-- Nodes of arpInspValidateSrcMac
--
arpInspValidateSrcMac         OBJECT-TYPE
    SYNTAX          TruthValue
    MAX-ACCESS      read-write
    STATUS          current
    DESCRIPTION
        "whether do Validation of arp's src-mac.
        true(1), false(2)."
    ::= { arpInsp 6 }
            
--
-- Nodes of arpInspEnableTable
--
arpInspEnableTable         OBJECT-TYPE
    SYNTAX          SEQUENCE OF ArpInspEnableEntry
    MAX-ACCESS      not-accessible
    STATUS          current
    DESCRIPTION
        "A table of ARP Inspection Enable."
    ::= { arpInsp 7 }         
        
arpInspEnableEntry         OBJECT-TYPE
    SYNTAX          ArpInspEnableEntry
    MAX-ACCESS      not-accessible
    STATUS          current
    DESCRIPTION
        "Arp inspection enable information."
    INDEX     { arpInspEnVid }
    ::= { arpInspEnableTable 1 }        
        
ArpInspEnableEntry    ::=
    SEQUENCE
    {
        arpInspEnVid
            Integer32,
        arpInspEnableRowStatus 
            RowStatus 
     }
         
arpInspEnVid         OBJECT-TYPE
    SYNTAX          Integer32 (0..65535)
    MAX-ACCESS      not-accessible
    STATUS          current
    DESCRIPTION
        "The vlan id, which enables arp inspection."
    ::= { arpInspEnableEntry 1 }       

arpInspEnableRowStatus        OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { arpInspEnableEntry 2 }   

--
-- Nodes of arpInspIfTrustTable
--
arpInspIfTrustTable OBJECT-TYPE
    SYNTAX          SEQUENCE OF ArpInspIfTrustEntry
    MAX-ACCESS      not-accessible
    STATUS          current
    DESCRIPTION
        "A table of ARP trust interface."
    ::= { arpInsp 8 }         
        
arpInspIfTrustEntry OBJECT-TYPE
    SYNTAX          ArpInspIfTrustEntry
    MAX-ACCESS      not-accessible
    STATUS          current
    DESCRIPTION
        "ARP trust interface information."
    INDEX     { arpInspTrustIfindex }
    ::= { arpInspIfTrustTable 1 }        
        
ArpInspIfTrustEntry    ::=
    SEQUENCE
    {
        arpInspTrustIfindex
            Integer32,
        arpInspTrustRowStatus 
            RowStatus 
     }
         
arpInspTrustIfindex         OBJECT-TYPE
    SYNTAX          Integer32 (0..65535)
    MAX-ACCESS      not-accessible
    STATUS          current
    DESCRIPTION
        "The ifindex."
    ::= { arpInspIfTrustEntry 1 }       

arpInspTrustRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { arpInspIfTrustEntry 2 }   

--
-- Nodes of arpInspLogbuffEntries
--
arpInspLogbuffEntries         OBJECT-TYPE
    SYNTAX          Integer32 (10..1024)
    MAX-ACCESS      read-write
    STATUS          current
    DESCRIPTION
        "Number of entries for log buffer. Range 10~1024. Default value is 32."
    DEFVAL         { 32 }
    ::= { arpInsp 9 }  

--
-- Nodes of arpInspLogbuffLogsTable
--
arpInspLogbuffLogsTable         OBJECT-TYPE
    SYNTAX          SEQUENCE OF ArpInspLogbuffLogsEntry
    MAX-ACCESS      not-accessible
    STATUS          current
    DESCRIPTION
        "A table of ARP Inspection log buff logs."
    ::= { arpInsp 10 }         
        
arpInspLogbuffLogsEntry         OBJECT-TYPE
    SYNTAX          ArpInspLogbuffLogsEntry
    MAX-ACCESS      not-accessible
    STATUS          current
    DESCRIPTION
        "ARP log buff logs information."
    INDEX     { arpInspLogbuffLogs }
    ::= { arpInspLogbuffLogsTable 1 }        
        
ArpInspLogbuffLogsEntry    ::=
    SEQUENCE
    {
        arpInspLogbuffLogs
            Integer32,
        arpInspLogbuffInterval 
            Integer32, 
        arpInspLogbuffRowStatus 
            RowStatus 
     }
     
arpInspLogbuffLogs         OBJECT-TYPE
    SYNTAX          Integer32 (0..1024)
    MAX-ACCESS      not-accessible
    STATUS          current
    DESCRIPTION
        "Number of logs per interval. Range 0~1024. Default value is 5."
    DEFVAL         { 5 }
    ::= { arpInspLogbuffLogsEntry 1 }       

arpInspLogbuffInterval        OBJECT-TYPE
    SYNTAX          Integer32 (0..86400)
    MAX-ACCESS      read-create
    STATUS          current
    DESCRIPTION
        "Interval for controlling logging rate. Range 0~86400. Default value is 1."
    DEFVAL         { 1 }
    ::= { arpInspLogbuffLogsEntry 2 }   

arpInspLogbuffRowStatus        OBJECT-TYPE
    SYNTAX          RowStatus
    MAX-ACCESS      read-create
    STATUS          current
    DESCRIPTION
        "The status of this conceptual row.Now only realize CreateAndGo(4) and Destroy(6) and Active(1)."
    ::= { arpInspLogbuffLogsEntry 3 }  



-- Sub Module: USER

--
-- Textual conventions 
--
LoginType    ::= TEXTUAL-CONVENTION
    STATUS          current
    DESCRIPTION
        "Specify severity level of message."
    SYNTAX          INTEGER
    {
        nologin(1),
        login(2),
        loginlocal(3)
    }
--
-- Node definitions
--

lineTable           OBJECT-TYPE
    SYNTAX          SEQUENCE OF LineEntry
    MAX-ACCESS      not-accessible
    STATUS          current
    DESCRIPTION        
        "describe the login line property."
    ::= { user 1 }

lineEntry              OBJECT-TYPE
    SYNTAX          LineEntry
    MAX-ACCESS      not-accessible
    STATUS          current
    DESCRIPTION 
        "describe the login property."
    INDEX    { lineType, lineIndex }
    ::= { lineTable 1 }
    
LineEntry    ::= 
    SEQUENCE 
    {
        lineType        
            INTEGER,
        lineIndex       
            INTEGER,
        lineLoginMode   
            LoginType,
        linePassword    
            OCTET STRING ,
        linePriviledge  
            INTEGER,
        lineExecTimeoutmin 
            INTEGER,
        lineExecTimeoutsec 
            INTEGER,
        lineAccessInName   
            OCTET STRING,
        lineTransportType 
            INTEGER,
        linePasswordType   
            INTEGER
    }

lineType         OBJECT-TYPE
    SYNTAX          INTEGER
    {
        console(0),
        vty(1)
    }
    MAX-ACCESS      not-accessible
    STATUS          current
    DESCRIPTION 
        "The line type.
        0 console.
        1 vty."
    ::= { lineEntry 1 }

lineIndex         OBJECT-TYPE
    SYNTAX          INTEGER(0..7)
    MAX-ACCESS      not-accessible
    STATUS          current
    DESCRIPTION 
        "The line number.index range 0~7."
    ::= { lineEntry 2 }

lineLoginMode          OBJECT-TYPE
    SYNTAX          LoginType
    MAX-ACCESS      read-write
    STATUS          current
    DESCRIPTION
        "The line login mode.
        1 no login.
        2 login.
        3 login local."
    ::= { lineEntry 3 }

linePassword          OBJECT-TYPE
    SYNTAX          OCTET STRING (SIZE (0..63))
    MAX-ACCESS      read-write
    STATUS          current
    DESCRIPTION
        "The line password."
    ::= { lineEntry 4 }

linePriviledge         OBJECT-TYPE
    SYNTAX          INTEGER(1..4)
    MAX-ACCESS      read-write
    STATUS          current
    DESCRIPTION 
        "The line priviledge. The valid range is [1, 4]."
    ::= { lineEntry 5 }

lineExecTimeoutmin     OBJECT-TYPE
    SYNTAX          INTEGER(0..35791)
    MAX-ACCESS      read-write
    STATUS          current
    DESCRIPTION 
        "The exec mode timeout minute value."
    ::= { lineEntry 6 }

lineExecTimeoutsec         OBJECT-TYPE
    SYNTAX          INTEGER(0..2147483)
    MAX-ACCESS      read-write
    STATUS          current
    DESCRIPTION
        "The exec mode timeout second value."
    ::= { lineEntry 7 }
    
lineAccessInName         OBJECT-TYPE
    SYNTAX          OCTET STRING (SIZE (0..255))
    MAX-ACCESS      read-write
    STATUS          current
    DESCRIPTION
        "The access name applied for vty."
    ::= { lineEntry 8 }

lineTransportType         OBJECT-TYPE
    SYNTAX          INTEGER
    {
        all(0),
        ssh(1),
        telnet(2),
        none(3)        
    }
    MAX-ACCESS      read-write
    STATUS          current
    DESCRIPTION
        "The vty line Transport type.
        0 all.
        1 ssh.
        2 telnet.
        3 none."
    ::= { lineEntry 9 }

linePasswordType         OBJECT-TYPE
    SYNTAX          INTEGER(0..2)
    MAX-ACCESS      read-only
    STATUS          current
    DESCRIPTION 
        "The Password type.
        0 not set password.
        1 not encrypted password.
        2 encrypted password."
    ::= { lineEntry 10 }
	
usernameTable         OBJECT-TYPE
    SYNTAX          SEQUENCE OF UsernameEntry
    MAX-ACCESS      not-accessible
    STATUS          current
    DESCRIPTION
        "The table of loghost."
    ::= { user 2 }

usernameEntry          OBJECT-TYPE
    SYNTAX          UsernameEntry
    MAX-ACCESS      not-accessible
    STATUS          current
    DESCRIPTION
        "The entry of user."
    INDEX           { usernameIndex }
    ::= { usernameTable 1 }

UsernameEntry    ::=
    SEQUENCE 
    {
         usernameIndex
            Integer32,
         username
            OCTET STRING,
         password
            OCTET STRING,
         userPrivilege
            Integer32,
         userPwdType
            INTEGER,
         usernameRowStatus 
            RowStatus 
     }

usernameIndex         OBJECT-TYPE
    SYNTAX          Integer32 (1..32)
    MAX-ACCESS      not-accessible
    STATUS          current
    DESCRIPTION
        "The username table index."
    ::= { usernameEntry 1 }

username            OBJECT-TYPE
    SYNTAX          OCTET STRING (SIZE (0..255))
    MAX-ACCESS      read-create
    STATUS          current
    DESCRIPTION
        "The username. Can only include [0-9a-zA-Z.-_], and must starting with alphanumeric. Its length range is [1, 32)"

    ::= { usernameEntry 2 }

password             OBJECT-TYPE
    SYNTAX          OCTET STRING (SIZE (0..128))
    MAX-ACCESS      read-create
    STATUS          current
    DESCRIPTION
        "The password.
        If type is secretForUser or normalPwd, the valid range of length is [1,64).
        If type is hiddenPwd, the valid range of length is [1,128]."
    ::= { usernameEntry 3 }
     
userPrivilege         OBJECT-TYPE
    SYNTAX          Integer32
    MAX-ACCESS      read-create
    STATUS          current
    DESCRIPTION
        "The user privilege <1-4>."
    ::= { usernameEntry 4 }
     

userPwdType     OBJECT-TYPE
    SYNTAX          INTEGER
     {
         secretForUser(1),
         hiddenPwd(2),
         normalPwd(3),
         notsetPwd(4)        
     }
    MAX-ACCESS      read-create
    STATUS          current
    DESCRIPTION
        "The user password type.
        1 secretForUser.
        2 hiddenPwd.
        3 normalPwd.
        4 notsetPwd."
    ::= { usernameEntry 5 }         
     
     
usernameRowStatus       OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { usernameEntry 6 }      



enablePasswordTable         OBJECT-TYPE ---{{{1
    SYNTAX          SEQUENCE OF EnablePasswordEntry
    MAX-ACCESS      not-accessible
    STATUS          current
    DESCRIPTION
        "The table of enable password."
    ::= { user 3 }
     
enablePasswordEntry         OBJECT-TYPE
    SYNTAX          EnablePasswordEntry
    MAX-ACCESS      not-accessible
    STATUS          current
    DESCRIPTION
        "The entry of enable password."
    INDEX          { privilegeIndex }
    ::= { enablePasswordTable 1 }

EnablePasswordEntry    ::=
    SEQUENCE {
         privilegeIndex
            Integer32,
         passwordType
            INTEGER,
         enablePassword
            OCTET STRING,
         enableRowStatus 
RowStatus 
     }     
 
privilegeIndex         OBJECT-TYPE
    SYNTAX          Integer32 (1..4)
    MAX-ACCESS      not-accessible
    STATUS          current
    DESCRIPTION
        "The enable password table index."
    ::= { enablePasswordEntry 1 }    

passwordType     OBJECT-TYPE
    SYNTAX          INTEGER
     {
         secretForUser(1),
         hiddenPwd(2),
         normalPwd(3),
         notsetPwd(4)        
     }
    MAX-ACCESS      read-create
    STATUS          current
    DESCRIPTION
        "The password type.
        1 secretForUser.
        2 hiddenPwd.
        3 normalPwd.
        The value notsetPwd(4) is only for the return value and not support
        configured."
    ::= { enablePasswordEntry 2 }   

enablePassword         OBJECT-TYPE
    SYNTAX          OCTET STRING (SIZE (0..128))
    MAX-ACCESS      read-create
    STATUS          current
    DESCRIPTION
        "The enable password.
        If type is secretForUser or normalPwd, the valid range of length is [1,64).
        If type is hiddenPwd, the valid range of length is [1,128]."
    ::= { enablePasswordEntry 3 }

enableRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { enablePasswordEntry 4 }  

serviceTerminalLength         OBJECT-TYPE
    SYNTAX          INTEGER(-1..512)
    MAX-ACCESS      read-write
    STATUS          current
    DESCRIPTION
        "Describe the terminal length.
        0  means system doesn't limit the line numbers displayed. 
        -1 means system doesn't control terminal length."
    ::= { user 4 }

serviceCipherDetect         OBJECT-TYPE
    SYNTAX          INTEGER
        {
            none(1),
            normal(2),
            strong(3)
        }
    MAX-ACCESS      read-write
    STATUS          current
    DESCRIPTION 
        "Describe the cipher detect.
        1 Disable security check
        2 Cipher must contain digital and normal char
        3 Cipher must contain digital, normal char and special char"
    ::= { user 5 }


--
--  Users table
--
usersTable         OBJECT-TYPE 
    SYNTAX          SEQUENCE OF UsersEntry
    MAX-ACCESS      not-accessible
    STATUS          current
    DESCRIPTION
        "The table of users."
    ::= { user 6 }

usersEntry         OBJECT-TYPE
    SYNTAX          UsersEntry
    MAX-ACCESS      not-accessible
    STATUS          current
    DESCRIPTION
        "The entry of users."
    INDEX         { usersLineType, usersLineIndex }
    ::= { usersTable 1 }

UsersEntry    ::=
    SEQUENCE {
        usersLineType
            Integer32,
        usersLineIndex
            Integer32,
        usersname
            OCTET STRING,
        usersIdleTime
            OCTET STRING,
        usersLocation
            OCTET STRING 
     }

usersLineType         OBJECT-TYPE
    SYNTAX          Integer32 (0..65535)
    MAX-ACCESS      not-accessible
    STATUS          current
    DESCRIPTION
        "The Users line Type. 0 means console,and 1 means vty."
    ::= { usersEntry 1 }
    
usersLineIndex         OBJECT-TYPE
    SYNTAX          Integer32 (0..65535)
    MAX-ACCESS      not-accessible
    STATUS          current
    DESCRIPTION
        "The Users line index."
    ::= { usersEntry 2 }

usersname         OBJECT-TYPE
    SYNTAX          OCTET STRING (SIZE (0..255))
    MAX-ACCESS      read-only
    STATUS          current
    DESCRIPTION
        "The Users name."
    ::= { usersEntry 3 }

usersIdleTime         OBJECT-TYPE
    SYNTAX          OCTET STRING
    MAX-ACCESS      read-only
    STATUS          current
    DESCRIPTION
        "The idle time."
    ::= { usersEntry 4 }
     
usersLocation         OBJECT-TYPE
    SYNTAX          OCTET STRING (SIZE (0..255))
    MAX-ACCESS      read-only
    STATUS          current
    DESCRIPTION
        "The user location."
    ::= { usersEntry 5 }

lineMaxVTY         OBJECT-TYPE
    SYNTAX          Integer32 (0..8)
    MAX-ACCESS      read-write
    STATUS          current
    DESCRIPTION 
        "Set max vty number and the default value is 8."
    ::= { user 7 }

-- Sub Module: SNMPEXT

         
snmpExtMibObject OBJECT IDENTIFIER    ::= {  snmpExt 1  }
                                     
snmpVersion         OBJECT-TYPE
    SYNTAX          INTEGER
    {
        v1(1),
        v2c(2),
        v3(3),
        all(4)
    }
    MAX-ACCESS      read-only
    STATUS          current
    DESCRIPTION        
        "Snmp agent's snmp version.v1(1),v2c(2),v3(3),all(4).
        Default value is all(4)."
        -- DEFVAL    INDEX     { all }
    ::= { snmpExtMibObject 1 }

snmpEngineID        OBJECT-TYPE
    SYNTAX          OCTET STRING (SIZE (10..64))
    MAX-ACCESS      read-only
    STATUS          current
    DESCRIPTION        
        "Engine ID in hexadecimal format.If the value is not set use the default value.Range 10~64.
        Default value 30383038303830383038."
       -- DEFVAL    INDEX     { all }
    ::= { snmpExtMibObject 2 }
        
snmpCommunityTable  OBJECT-TYPE
    SYNTAX          SEQUENCE OF SnmpCommunityEntry
    MAX-ACCESS      not-accessible
    STATUS          current
    DESCRIPTION
        "Snmp community configure."
    ::= { snmpExtMibObject 3 }


snmpCommunityEntry  OBJECT-TYPE
    SYNTAX          SnmpCommunityEntry
    MAX-ACCESS      not-accessible
    STATUS          current
    DESCRIPTION
        "The entry of snmpcommunityTable."
    INDEX     { snmpcommIndex }
    ::= { snmpCommunityTable 1 }                         
                          
    SnmpCommunityEntry    ::=
    SEQUENCE 
    {
        snmpcommIndex
            Integer32,
        snmpcommName
            OCTET STRING,
        snmpcommType
            Integer32,
        snmpcommView
            OCTET STRING,
        snmpcommRowStatus 
            RowStatus 
     }
         
snmpcommIndex       OBJECT-TYPE
    SYNTAX          Integer32 (0..31)
    MAX-ACCESS      not-accessible
    STATUS          current
    DESCRIPTION
        "Snmp community's index.Range 0~31."
    ::= { snmpCommunityEntry 1 }

snmpcommName        OBJECT-TYPE
    SYNTAX          OCTET STRING (SIZE (1..255))
    MAX-ACCESS      read-only
    STATUS          current
    DESCRIPTION
        "Snmp community's name. Starting with alphabetic and can only include [0-9a-zA-Z.-_]. Its length range is [1, 256)."
    ::= { snmpCommunityEntry 2 }

     
snmpcommType        OBJECT-TYPE
    SYNTAX          Integer32 (1..2)
    MAX-ACCESS      read-only
    STATUS          current
    DESCRIPTION
        "Snmp community type's index.read-only(1) read-write(2)."
    ::= { snmpCommunityEntry 3 }
        
snmpcommView        OBJECT-TYPE
    SYNTAX          OCTET STRING (SIZE (1..31))
    MAX-ACCESS      read-only
    STATUS          current
    DESCRIPTION
        "Snmp community's View. Starting with alphabetic and can only include [0-9a-zA-Z.-_]. Its length range is [1, 32)."
    ::= { snmpCommunityEntry 4 }             
        
snmpcommRowStatus   OBJECT-TYPE
    SYNTAX          RowStatus
    MAX-ACCESS      read-only
    STATUS          current
    DESCRIPTION
        "The status of this conceptual row.Now only realize CreateAndGo 
        and Destroy and Active.
        1 means Active
        4 means CreateAndGo
        6 means Destroy"
    ::= { snmpCommunityEntry 5 }            
        

--  Snmp View Table
snmpViewTable         OBJECT-TYPE
    SYNTAX          SEQUENCE OF SnmpViewEntry
    MAX-ACCESS      not-accessible
    STATUS          current
    DESCRIPTION
        "Snmp view configure."
    ::= { snmpExtMibObject 4 }


snmpViewEntry       OBJECT-TYPE
    SYNTAX          SnmpViewEntry
    MAX-ACCESS      not-accessible
    STATUS          current
    DESCRIPTION
        "The entry of snmpViewTable."
    INDEX     { snmpviewIndex}
    ::= { snmpViewTable 1 }                         
                          
SnmpViewEntry    ::=
    SEQUENCE 
    {
        snmpviewIndex
            Integer32,
        snmpviewName
            OCTET STRING,
        snmpviewType
            Integer32,
        snmpviewcldOID
            OCTET STRING,
        snmpviewMask
            OCTET STRING,
        snmpviewRowStatus 
            RowStatus 
     }

snmpviewIndex       OBJECT-TYPE
    SYNTAX          Integer32 (0..31)
    MAX-ACCESS      not-accessible
    STATUS          current
    DESCRIPTION
        "Snmp View's index. Range is 0~31."
    ::= { snmpViewEntry 1 }
        
snmpviewName        OBJECT-TYPE
    SYNTAX          OCTET STRING (SIZE (1..31))
    MAX-ACCESS      read-only
    STATUS          current
    DESCRIPTION
        "Snmp View's name. Range is 1~31."
    ::= { snmpViewEntry 2 }

     
snmpviewType        OBJECT-TYPE
    SYNTAX          Integer32 (1..2)
    MAX-ACCESS      read-only
    STATUS          current
    DESCRIPTION
        "View type 1: include a subtree.View type 2: exclude a subtree."
    ::= { snmpViewEntry 3 }
        
snmpviewcldOID         OBJECT-TYPE
    SYNTAX          OCTET STRING (SIZE (1..60))
    MAX-ACCESS      read-only
    STATUS          current
    DESCRIPTION
        "Subtree name. Format is '.A.B.C..' ."
    ::= { snmpViewEntry 4 }             

snmpviewMask         OBJECT-TYPE
    SYNTAX          OCTET STRING (SIZE (1..32))
    MAX-ACCESS      read-only
    STATUS          current
    DESCRIPTION
        "Define the subtree mask."
    ::= { snmpViewEntry 5 }   
                    
snmpviewRowStatus   OBJECT-TYPE
    SYNTAX          RowStatus
    MAX-ACCESS      read-only
    STATUS          current
    DESCRIPTION
        "The status of this conceptual row.Now only realize CreateAndGo 
        and Destroy and Active.
        1 means Active
        4 means CreateAndGo
        6 means Destroy"
    ::= { snmpViewEntry 6 }                        
        
            
--            
--  Snmp Usm-user Table
--
snmpUsmuserTable    OBJECT-TYPE
    SYNTAX          SEQUENCE OF SnmpUsmuserEntry
    MAX-ACCESS      not-accessible
    STATUS          current
    DESCRIPTION
        "Snmp Usm-user configure."
    ::= { snmpExtMibObject 5 }


snmpUsmuserEntry    OBJECT-TYPE
    SYNTAX          SnmpUsmuserEntry
    MAX-ACCESS      not-accessible
    STATUS          current
    DESCRIPTION
        "The entry of snmpUsmuserTable."
    INDEX     { snmpUsmuserIndex }
    ::= { snmpUsmuserTable 1 }                         
                          
    SnmpUsmuserEntry    ::=
    SEQUENCE {
        snmpUsmuserIndex
            Integer32,
        snmpUsmuserName
            OCTET STRING,
        snmpUsmuserRemote 
            OCTET STRING,
        snmpUsmuserAuth
            INTEGER,
        snmpUsmuserAuthHid
            INTEGER,
        snmpUsmuserAuthPWD
            OCTET STRING,
        snmpUsmuserPrivacy 
            INTEGER,
        snmpUsmuserPrivacyHid 
            INTEGER,
        snmpUsmuserPrivacyPWD
            OCTET STRING,
        snmpUsmuserRowStatus 
            RowStatus 
     }

snmpUsmuserIndex         OBJECT-TYPE
    SYNTAX          Integer32 (0..31)
    MAX-ACCESS      not-accessible
    STATUS          current
    DESCRIPTION
        "Snmp usm-user's index.Range 0~31."
    ::= { snmpUsmuserEntry 1 }
            
snmpUsmuserName         OBJECT-TYPE
    SYNTAX          OCTET STRING (SIZE (1..31))
    MAX-ACCESS      read-only
    STATUS          current
    DESCRIPTION
        "Snmp usm-user's name.Range 1~31."
    ::= { snmpUsmuserEntry 2 }

         
snmpUsmuserRemote         OBJECT-TYPE
    SYNTAX          OCTET STRING (SIZE (10..64))
    MAX-ACCESS      read-only
    STATUS          current
    DESCRIPTION
        "Snmp usm-user's Remote.Range 10~64."
    ::= { snmpUsmuserEntry 3 }
            
snmpUsmuserAuth         OBJECT-TYPE
    SYNTAX          INTEGER
        {
            none(1),
            md5(2),
            sha(3)
        }
    MAX-ACCESS      read-only
    STATUS          current
    DESCRIPTION
        "Authentication parameters for the user. none(1),md5(2),sha(3)."
      -- DEFVAL { md5 }
    ::= { snmpUsmuserEntry 4 }   

snmpUsmuserAuthHid         OBJECT-TYPE
    SYNTAX          INTEGER
        {
            unhidden(1),
            hidden(2)
        }
    MAX-ACCESS      read-only
    STATUS          current
    DESCRIPTION
        "pecifies a HIDDEN password will follow. unhidden(1),hidden(2)."
     -- DEFVAL { md5 }
    ::= { snmpUsmuserEntry 5 } 
            
snmpUsmuserAuthPWD         OBJECT-TYPE
    SYNTAX          OCTET STRING (SIZE (1..128))
    MAX-ACCESS      read-only
    STATUS          current
    DESCRIPTION
        "Specify an authentication password.Password length depends on:
         snmpUsmuserAuthHid(5) is unhidden(1), password Range is 8~64, otherwise 1~128."
    ::= { snmpUsmuserEntry 6 }   
                        
snmpUsmuserPrivacy         OBJECT-TYPE
    SYNTAX          INTEGER
        {
            none(1),
            des(2),
            aes(3)
        }
    MAX-ACCESS      read-only
    STATUS          current
    DESCRIPTION
        "Privacy parameters for the user. none(1),des(2),aes(3)."
     -- DEFVAL { des }
    ::= { snmpUsmuserEntry 7 }                                
            
snmpUsmuserPrivacyHid         OBJECT-TYPE
    SYNTAX          INTEGER
        {
            unhidden(1),
            hidden(2)
        }
    MAX-ACCESS      read-only
    STATUS          current
    DESCRIPTION
        "Specifies a HIDDEN password will follow. unhidden(1), hidden(2)."
   --   DEFVAL { md5 }
    ::= { snmpUsmuserEntry 8 } 
            
snmpUsmuserPrivacyPWD         OBJECT-TYPE
    SYNTAX          OCTET STRING (SIZE (8..64))
    MAX-ACCESS      read-only
    STATUS          current
    DESCRIPTION
        "Specify a privacy password.Password length depends on:
         snmpUsmuserPrivacyHid(8)is unhidden(1), password Range is 8~64, otherwise 1~128."
    ::= { snmpUsmuserEntry 9 }  
            
snmpUsmuserRowStatus         OBJECT-TYPE
    SYNTAX          RowStatus
    MAX-ACCESS      read-only
    STATUS          current
    DESCRIPTION
        "The status of this conceptual row.Now only realize CreateAndGo 
        and Destroy and Active.
        1 means Active
        4 means CreateAndGo
        6 means Destroy"
    ::= { snmpUsmuserEntry 10 }                        
            

--            
--  Snmp server group Table
--
snmpGrpTable        OBJECT-TYPE
    SYNTAX          SEQUENCE OF SnmpGrpEntry
    MAX-ACCESS      not-accessible
    STATUS          current
    DESCRIPTION
        "Snmp server group configure."
    ::= { snmpExtMibObject 6 }


snmpGrpEntry        OBJECT-TYPE
    SYNTAX          SnmpGrpEntry
    MAX-ACCESS      not-accessible
    STATUS          current
    DESCRIPTION
        "The entry of snmpGrpTable."
    INDEX     { snmpGrpIndex }
    ::= { snmpGrpTable 1 }                         
                          
    SnmpGrpEntry    ::=
    SEQUENCE 
    {
        snmpGrpIndex
            Integer32,
        snmpGrpName
            OCTET STRING,
        snmpGrpUser 
            OCTET STRING,
        snmpGrpSecMode
            INTEGER,
        snmpGrpRowStatus 
            RowStatus 
    }
         
snmpGrpIndex        OBJECT-TYPE
    SYNTAX          Integer32 (0..31)
    MAX-ACCESS      not-accessible
    STATUS          current
    DESCRIPTION
        "Snmp group's index. Range is 0~31."
    ::= { snmpGrpEntry 1 }
            
snmpGrpName         OBJECT-TYPE
    SYNTAX          OCTET STRING (SIZE (1..31))
    MAX-ACCESS      read-only
    STATUS          current
    DESCRIPTION
        "The name of the group. Starting with alphabetic and can only include [0-9a-zA-Z.-_]. Its length range is [1, 31)."
    ::= { snmpGrpEntry 2 }

snmpGrpUser         OBJECT-TYPE
    SYNTAX          OCTET STRING (SIZE (1..31))
    MAX-ACCESS      read-only
    STATUS          current
    DESCRIPTION
        "Define a user security name belongs to the group. Range is 1~31."
    ::= { snmpGrpEntry 3 }
            
snmpGrpSecMode        OBJECT-TYPE
     SYNTAX          INTEGER
        {
            any(0),
            v1(1),
            v2c(2),
            usm(3)
        }
    MAX-ACCESS      read-only
    STATUS          current
    DESCRIPTION
        "Define the group security model.
        0 any
        1 v1
        2 v2c
        3 usm(default)
        Only support set 3(usm) now."
    ::= { snmpGrpEntry 4 }
    
snmpGrpRowStatus    OBJECT-TYPE
    SYNTAX          RowStatus
    MAX-ACCESS      read-only
    STATUS          current
    DESCRIPTION
        "The status of this conceptual row.Now only realize CreateAndGo 
        and Destroy and Active.
        1 means Active
        4 means CreateAndGo
        6 means Destroy"
    ::= { snmpGrpEntry 10 }                        
            
            
--            
--  Snmp server access Table
--
snmpAccessTable     OBJECT-TYPE
    SYNTAX          SEQUENCE OF SnmpAccessEntry
    MAX-ACCESS      not-accessible
    STATUS          current
    DESCRIPTION
        "Define the access for a exact group."
    ::= { snmpExtMibObject 7 }


snmpAccessEntry     OBJECT-TYPE
    SYNTAX          SnmpAccessEntry
    MAX-ACCESS      not-accessible
    STATUS          current
    DESCRIPTION
        "The entry of snmpAccessTable."
    INDEX     { snmpAccessIndex }
    ::= { snmpAccessTable 1 }                         
                          
    SnmpAccessEntry    ::=
    SEQUENCE {
        snmpAccessIndex
            Integer32,
        snmpAccessName
            OCTET STRING,
        snmpAccessUsm 
            INTEGER,
        snmpAccessRead
            OCTET STRING,
        snmpAccessWrite
            OCTET STRING,
        snmpAccessNotify
            OCTET STRING,
        snmpAccessContext
            OCTET STRING,
        snmpAccessContextType
            INTEGER,
        snmpAccessSecuMode
            INTEGER,
        snmpAccessRowStatus 
            RowStatus 
    }

snmpAccessIndex         OBJECT-TYPE
    SYNTAX          Integer32 (1..31)
    MAX-ACCESS      not-accessible
    STATUS          current
    DESCRIPTION
        "Snmp access's index.Range 1~31."
    ::= { snmpAccessEntry 1 }
            
snmpAccessName         OBJECT-TYPE
    SYNTAX          OCTET STRING (SIZE (1..31))
    MAX-ACCESS      read-only
    STATUS          current
    DESCRIPTION
        "Snmp Access's name.Range 1~31."
    ::= { snmpAccessEntry 2 }

snmpAccessUsm         OBJECT-TYPE
    SYNTAX          INTEGER
    {
        noauth(1),
        auth(2),
        priv(3)
    }
    MAX-ACCESS      read-only
    STATUS          current
    DESCRIPTION
        "Snmp usm security model
        noauth(1): Set security level to no authentication
        auth(2): Set security level to authentication but with no privacy
        priv(3): Set security level to authentication with privacy"
    ::= { snmpAccessEntry 3 }
            
snmpAccessRead      OBJECT-TYPE
    SYNTAX          OCTET STRING (SIZE (0..64))
    MAX-ACCESS      read-only
    STATUS          current
    DESCRIPTION
        "Restrict this access read area to a named MIB view."
    ::= { snmpAccessEntry 4 }
            
snmpAccessWrite     OBJECT-TYPE
    SYNTAX          OCTET STRING (SIZE (0..64))
    MAX-ACCESS      read-only
    STATUS          current
    DESCRIPTION
        "Restrict this access write area to a named MIB view."
    ::= { snmpAccessEntry 5 }
            
snmpAccessNotify    OBJECT-TYPE
    SYNTAX          OCTET STRING (SIZE (0..64))
    MAX-ACCESS      read-only
    STATUS          current
    DESCRIPTION
        "Restrict this access notify area to a named MIB view."
    ::= { snmpAccessEntry 6 }
        
snmpAccessContext   OBJECT-TYPE
    SYNTAX          OCTET STRING (SIZE (0..31))
    MAX-ACCESS      read-only
    STATUS          current
    DESCRIPTION
        "Set the access's context name. Range is 0~31. "
    ::= { snmpAccessEntry 7 }
            
snmpAccessContextType         OBJECT-TYPE
    SYNTAX          INTEGER
    {
        none(1),
        exact(2),
        prefix(3)
    }
    MAX-ACCESS      read-only
    STATUS          current
    DESCRIPTION
        "Snmp usm security model
        none(1): none
        exact(2): Context match(default is exact) type specification: exact
        prefix(3): Context match(default is exact) type specification: prefix."
    ::= { snmpAccessEntry 8 }

snmpAccessSecuMode         OBJECT-TYPE
     SYNTAX          INTEGER
        {
            any(0),
            v1(1),
            v2c(2),
            usm(3)
        }
    MAX-ACCESS      read-only
    STATUS          current
    DESCRIPTION
        "Define the access security model.
        0 any
        1 v1
        2 v2c
        3 usm(default)
        Only support set 3(usm) now."
    ::= { snmpAccessEntry 9 }
                
snmpAccessRowStatus OBJECT-TYPE
    SYNTAX          RowStatus
    MAX-ACCESS      read-only
    STATUS          current
    DESCRIPTION
        "The status of this conceptual row.Now only realize CreateAndGo 
        and Destroy and Active.
        1 means Active
        4 means CreateAndGo
        6 means Destroy"
    ::= { snmpAccessEntry 10 }                        
                                    
            

--            
--  Snmp server notify Table
--
snmpNotifyTable     OBJECT-TYPE
    SYNTAX          SEQUENCE OF SnmpNotifyEntry
    MAX-ACCESS      not-accessible
    STATUS          current
    DESCRIPTION
        " Define a notify name which related to send SNMP notification."
    ::= { snmpExtMibObject 8 }


snmpNotifyEntry     OBJECT-TYPE
    SYNTAX          SnmpNotifyEntry
    MAX-ACCESS      not-accessible
    STATUS          current
    DESCRIPTION
        "The entry of snmpNotifyTable."
    INDEX     { snmpNotifyIndex }
    ::= { snmpNotifyTable 1 }                         
                          
SnmpNotifyEntry    ::=
    SEQUENCE 
    {
        snmpNotifyIndex
            Integer32,
        snmpNotifyName
            OCTET STRING,
        snmpNotifyTag 
            OCTET STRING,
        snmpNotifyOption 
            INTEGER,
        snmpNotifyRowStatus 
            RowStatus 
     }
snmpNotifyIndex     OBJECT-TYPE
    SYNTAX          Integer32 (0..31)
    MAX-ACCESS      not-accessible
    STATUS          current
    DESCRIPTION
        "Snmp notify's index. Range is 0~31."
    ::= { snmpNotifyEntry 1 }
            
snmpNotifyName      OBJECT-TYPE
    SYNTAX          OCTET STRING (SIZE (1..31))
    MAX-ACCESS      read-only
    STATUS          current
    DESCRIPTION
        "The name of the notify. Range is 1~31. "
    ::= { snmpNotifyEntry 2 }

snmpNotifyTag       OBJECT-TYPE
    SYNTAX          OCTET STRING (SIZE (1..255))
    MAX-ACCESS      read-only
    STATUS          current
    DESCRIPTION
        " The name of the tag."
    ::= { snmpNotifyEntry 3 }

snmpNotifyOption    OBJECT-TYPE
    SYNTAX          INTEGER
    {
        trap(1),
        inform(2)
    }
    MAX-ACCESS      read-only
    STATUS          current
    DESCRIPTION
        "snmpNotifyOption
        trap(1): Set notify type(default is trap) to TRAP
        inform(2): Set notify type(default is trap) to INFORM."
    ::= { snmpNotifyEntry 4 }            
            
snmpNotifyRowStatus OBJECT-TYPE
    SYNTAX          RowStatus
    MAX-ACCESS      read-only
    STATUS          current
    DESCRIPTION
        "The status of this conceptual row.Now only realize CreateAndGo 
        and Destroy and Active.
        1 means Active
        4 means CreateAndGo
        6 means Destroy"
    ::= { snmpNotifyEntry 5 }                        
                                    


--            
--  Snmp server target address Table
--
snmpTargetAddrTable OBJECT-TYPE
    SYNTAX          SEQUENCE OF SnmpTargetAddrEntry
    MAX-ACCESS      not-accessible
    STATUS          current
    DESCRIPTION
        "Define a target address name which related to send SNMP notifications."
    ::= { snmpExtMibObject 9 }


snmpTargetAddrEntry         OBJECT-TYPE
    SYNTAX          SnmpTargetAddrEntry
    MAX-ACCESS      not-accessible
    STATUS          current
    DESCRIPTION
        "The entry of snmpTargetAddrTable."
    INDEX     { snmpTargetAddrIndex }
    ::= { snmpTargetAddrTable 1 }

    SnmpTargetAddrEntry    ::=
    SEQUENCE {
        snmpTargetAddrIndex
            Integer32,
        snmpTargetAddrName
            OCTET STRING,
        snmpTargetAddrPara
            OCTET STRING,
        snmpTargetAddrMgmtIf
            INTEGER,
        snmpTargetAddrIpType
                InetAddressType,
        snmpTargetAddrIp
                InetAddress,
        snmpTargetAddrPort
            Integer32,
        snmpTargetAddrTimeout
            Integer32,
        snmpTargetAddrRetry
            Integer32,
        snmpTargetAddrTag
            OCTET STRING,
        snmpTargetAddrRowStatus
            RowStatus
    }

snmpTargetAddrIndex OBJECT-TYPE
    SYNTAX          Integer32 (0..31)
    MAX-ACCESS      not-accessible
    STATUS          current
    DESCRIPTION
        "Snmp target address's index. Range is 0~31."
    ::= { snmpTargetAddrEntry 1 }

snmpTargetAddrName  OBJECT-TYPE
    SYNTAX          OCTET STRING (SIZE (1..31))
    MAX-ACCESS      read-only
    STATUS          current
    DESCRIPTION
        "The name of the target address. Range is 1~31. "
    ::= { snmpTargetAddrEntry 2 }

snmpTargetAddrPara  OBJECT-TYPE
    SYNTAX          OCTET STRING (SIZE (1..60))
    MAX-ACCESS      read-only
    STATUS          current
    DESCRIPTION
        " The name of the param."
    ::= { snmpTargetAddrEntry 3 }

snmpTargetAddrMgmtIf         OBJECT-TYPE
    SYNTAX          INTEGER
    {
        noUse(1),
        setMgmtIf(2)
    }
    MAX-ACCESS      read-only
    STATUS          current
    DESCRIPTION
        "configuraion mgmt if.
        1 noUse.
        2 setMgmtIf."
    ::= { snmpTargetAddrEntry 4 }

snmpTargetAddrIpType         OBJECT-TYPE
    SYNTAX          InetAddressType
    MAX-ACCESS      read-only
    STATUS          current
    DESCRIPTION
        "The IP addresses type,IPv4(1) or IPv6(2)."
    ::= { snmpTargetAddrEntry 5 }

snmpTargetAddrIp           OBJECT-TYPE
    SYNTAX          InetAddress
    MAX-ACCESS      read-only
    STATUS          current
    DESCRIPTION
        "The IP address."
    ::= { snmpTargetAddrEntry 6 }

snmpTargetAddrPort           OBJECT-TYPE
    SYNTAX          Integer32(0..65535)
    MAX-ACCESS      read-only
    STATUS          current
    DESCRIPTION
        "The IP address udp port 0-65535.Default value is 162."
    ::= { snmpTargetAddrEntry 7 }

snmpTargetAddrTimeout           OBJECT-TYPE
    SYNTAX          Integer32(0..65535)
    MAX-ACCESS      read-only
    STATUS          current
    DESCRIPTION
        "The timeout which detemine when to resend the notification 0-65535.
        Default value is 1500."
    ::= { snmpTargetAddrEntry 8 }

snmpTargetAddrRetry OBJECT-TYPE
    SYNTAX          Integer32(0..255)
    MAX-ACCESS      read-only
    STATUS          current
    DESCRIPTION
        "The timeout which detemine when to resend the notification 0-255.
        Default value is 3."
    ::= { snmpTargetAddrEntry 9 }

snmpTargetAddrTag   OBJECT-TYPE
    SYNTAX          OCTET STRING (SIZE (1..128))
    MAX-ACCESS      read-only
    STATUS          current
    DESCRIPTION
        "Define taglist which related to notify table.Range 1~128."
    ::= { snmpTargetAddrEntry 10 }

snmpTargetAddrRowStatus         OBJECT-TYPE
    SYNTAX          RowStatus
    MAX-ACCESS      read-only
    STATUS          current
    DESCRIPTION
        "The status of this conceptual row.Now only realize CreateAndGo 
        and Destroy and Active.
        1 means Active
        4 means CreateAndGo
        6 means Destroy"
    ::= { snmpTargetAddrEntry 11 }                                        


--            
--  Snmp server target params Table
--
snmpTargetParaTable OBJECT-TYPE
    SYNTAX          SEQUENCE OF SnmpTargetParaEntry
    MAX-ACCESS      not-accessible
    STATUS          current
    DESCRIPTION
        "Define the target params name which related to send SNMP notifications."
    ::= { snmpExtMibObject 10 }


snmpTargetParaEntry         OBJECT-TYPE
    SYNTAX          SnmpTargetParaEntry
    MAX-ACCESS      not-accessible
    STATUS          current
    DESCRIPTION
        "The entry of snmpTargetParaTable."
    INDEX     { snmpTargetParaIndex }
    ::= { snmpTargetParaTable 1 }                         
                          
SnmpTargetParaEntry    ::=
    SEQUENCE {
        snmpTargetParaIndex
            Integer32,
        snmpTargetParaName
            OCTET STRING,
        snmpTargetParaUser 
            OCTET STRING,
        snmpTargetParaSecLvl 
            INTEGER,
        snmpTargetParaRowStatus 
            RowStatus 
    }
    
snmpTargetParaIndex         OBJECT-TYPE
    SYNTAX          Integer32 (0..31)
    MAX-ACCESS      not-accessible
    STATUS          current
    DESCRIPTION
        "Snmp target params's index. Range is 0~31."
    ::= { snmpTargetParaEntry 1 }
            
snmpTargetParaName         OBJECT-TYPE
    SYNTAX          OCTET STRING (SIZE (1..31))
    MAX-ACCESS      read-only
    STATUS          current
    DESCRIPTION
        "The name of the target params. Range is 1~31. "
    ::= { snmpTargetParaEntry 2 }

snmpTargetParaUser         OBJECT-TYPE
    SYNTAX          OCTET STRING (SIZE (1..60))
    MAX-ACCESS      read-only
    STATUS          current
    DESCRIPTION
        "The name of the user."
    ::= { snmpTargetParaEntry 3 }

snmpTargetParaSecLvl         OBJECT-TYPE
    SYNTAX          INTEGER
    {
        noauth(1),
        auth(2),
        priv(3)
    }
    MAX-ACCESS      read-only
    STATUS          current
    DESCRIPTION
        "Snmp security model
        noauth(1): Set security level to no authentication
        auth(2): Set security level to authentication but with no privacy
        priv(3): Set security level to authentication with privacy"
    ::= { snmpTargetParaEntry 4 }            
            
snmpTargetParaRowStatus         OBJECT-TYPE
    SYNTAX          RowStatus
    MAX-ACCESS      read-only
    STATUS          current
    DESCRIPTION
        "The status of this conceptual row.Now only realize CreateAndGo 
        and Destroy and Active.
        1 means Active
        4 means CreateAndGo
        6 means Destroy"
    ::= { snmpTargetParaEntry 5 }                                        
            

--            
--  Snmp server trap target-address Table
--
snmpTrapAddrTable   OBJECT-TYPE
    SYNTAX          SEQUENCE OF SnmpTrapAddrEntry
    MAX-ACCESS      not-accessible
    STATUS          current
    DESCRIPTION
        "Define the trap remote receiver address."
    ::= { snmpExtMibObject 11 }


snmpTrapAddrEntry   OBJECT-TYPE
    SYNTAX          SnmpTrapAddrEntry
    MAX-ACCESS      not-accessible
    STATUS          current
    DESCRIPTION
        "The entry of snmpTrapAddrTable."
    INDEX     { snmpTrapIndex}
    ::= { snmpTrapAddrTable 1 }                         
                          
    SnmpTrapAddrEntry    ::=
    SEQUENCE {
        snmpTrapIndex
            Integer32,
        snmpTrapType
            INTEGER,
        snmpTrapMgmtIf
            INTEGER,
        snmpTrapAddrIptype
            InetAddressType,
        snmpTrapAddrIpAddr
            InetAddress,
        snmpTrapAddrCommunity 
            OCTET STRING,
        snmpTrapAddrVersion
            OCTET STRING,
        snmpTrapAddrPort 
            INTEGER,
        snmpTrapAddrRowStatus 
            RowStatus 
         }

snmpTrapIndex         OBJECT-TYPE
    SYNTAX          Integer32 (0..95)
    MAX-ACCESS      not-accessible
    STATUS          current
    DESCRIPTION
        "Snmp trap's index."
    ::= { snmpTrapAddrEntry 1 }
            
snmpTrapType         OBJECT-TYPE
    SYNTAX          INTEGER(0..1)
    MAX-ACCESS      read-only
    STATUS          current
    DESCRIPTION
        "configuraion type (trap:0 inform:1)."
    ::= { snmpTrapAddrEntry 2 }
            
            
snmpTrapMgmtIf         OBJECT-TYPE
    SYNTAX          INTEGER
      {
          noUse(1),
          setMgmtIf(2)
      }
    MAX-ACCESS      read-only
    STATUS          current
    DESCRIPTION
        "configuraion mgmt if.
        1 noUse.
        2 setMgmtIf."
    ::= { snmpTrapAddrEntry 3 }            
            
            
            
            
snmpTrapAddrIptype         OBJECT-TYPE
    SYNTAX          InetAddressType
    MAX-ACCESS      read-only
    STATUS          current
    DESCRIPTION
        "The IP addresses type : IPv4(1) or IPv6(2)."
    ::= { snmpTrapAddrEntry 4 }

snmpTrapAddrIpAddr           OBJECT-TYPE
    SYNTAX          InetAddress
    MAX-ACCESS      read-only
    STATUS          current
    DESCRIPTION
        "The IP address."
    ::= { snmpTrapAddrEntry 5 }            
        
snmpTrapAddrCommunity         OBJECT-TYPE
    SYNTAX          OCTET STRING (SIZE (1..255))
    MAX-ACCESS      read-only
    STATUS          current
    DESCRIPTION
        "The name of the community string.Range 1~255."
    ::= { snmpTrapAddrEntry 6 }        
        
snmpTrapAddrVersion         OBJECT-TYPE
    SYNTAX          OCTET STRING (SIZE (1..60))
    MAX-ACCESS      read-only
    STATUS          current
    DESCRIPTION
        "The version of the remote receiver."
    ::= { snmpTrapAddrEntry 7 }
            
snmpTrapAddrPort    OBJECT-TYPE
    SYNTAX          INTEGER(0..65535)
    MAX-ACCESS      read-only
    STATUS          current
    DESCRIPTION
        "The trap value which area is 0 to 65535, The default is 162."
    ::= { snmpTrapAddrEntry 8 }            
            
snmpTrapAddrRowStatus         OBJECT-TYPE
    SYNTAX          RowStatus
    MAX-ACCESS      read-only
    STATUS          current
    DESCRIPTION
        "The status of this conceptual row.Now only realize CreateAndGo 
        and Destroy and Active.
        1 means Active
        4 means CreateAndGo
        6 means Destroy"
    ::= { snmpTrapAddrEntry 9 }                                        
                        
            
            
--            
--  Snmp server trap enable Table
--

snmpEnableTable OBJECT IDENTIFIER    ::= {  snmpExtMibObject 12  }

snmpTrapColdstart         OBJECT-TYPE
    SYNTAX          INTEGER
    {
        enable(1),
        disable(2)
    }
    MAX-ACCESS      read-only
    STATUS          current
    DESCRIPTION        
        "Enable cold start trap. Enable(1), disable(2)."
    DEFVAL { disable }
    ::= { snmpEnableTable 1 }        

snmpTrapWarmstart         OBJECT-TYPE
    SYNTAX          INTEGER
    {
        enable(1),
        disable(2)
    }
    MAX-ACCESS      read-only
    STATUS          current
    DESCRIPTION        
        "Enable warm start trap. Enable(1), disable(2)."
    DEFVAL   { disable }
    ::= { snmpEnableTable 2 }  
    
snmpTrapLinkdown         OBJECT-TYPE
    SYNTAX          INTEGER
    {
        enable(1),
        disable(2)
    }
    MAX-ACCESS      read-only
    STATUS          current
    DESCRIPTION        
        "Enable linkdown trap. Enable(1), disable(2)."
    DEFVAL         { disable }
    ::= { snmpEnableTable 3 }    
    
snmpTrapLinkup         OBJECT-TYPE
    SYNTAX          INTEGER
    {
        enable(1),
        disable(2)
    }
    MAX-ACCESS      read-only
    STATUS          current
    DESCRIPTION        
        "Enable linkup trap. Enable(1), disable(2)."
    DEFVAL         { disable }
    ::= { snmpEnableTable 4 }

snmpTrapAll         OBJECT-TYPE
    SYNTAX          INTEGER
    {
        enable(1),
        disable(2)
    }
    MAX-ACCESS      read-only
    STATUS          obsolete
    DESCRIPTION
        "Enable all snmp trap. Enable(1), disable(2)."
    DEFVAL         { disable }
    ::= { snmpEnableTable 5 }

snmpTrapGeneralEvents         OBJECT-TYPE
    SYNTAX          INTEGER
    {
        enable(1),
        disable(2)
    }
    MAX-ACCESS      read-only
    STATUS          obsolete
    DESCRIPTION
        "Enable all general event traps. Enable(1), disable(2)."
    DEFVAL         { enable }
    ::= { snmpEnableTable 6 }

    snmpLock OBJECT-TYPE
        SYNTAX INTEGER
        {
            lock(1),
            unlocked(2)
        }
        MAX-ACCESS read-only
        STATUS current
        DESCRIPTION   "
            Setting this to lock(1) will only succeed when the CLI is
            NOT in configuration mode otherwise a badValue(3) in SNMPv1 and an inconsistentValue(12) in
            SNMPv2 and SNMPv3 will be returned indicating that the CLI is in configuration mode.
            If the CLI is NOT in configuration mode, the SNMP processing
            will be performed and the value of this object will immediately return to unlocked(2) state as soon
            as the SNMP processing takes place.
            Retrieving this object through SNMP will always returned unlocked(2).
            A typical usage will be to include this object as the first variable binding in all SET requests.
            If the SET request will fail because the CLI is in configuration mode, the GET-RESPONSE
            will contain an error with the first variable binding which indicates
            that the CLI is in configuration mode."
        ::= { snmpExtMibObject 13 }

snmpAccessGroup        OBJECT-TYPE
    SYNTAX          OCTET STRING (SIZE (0..20))
    MAX-ACCESS      read-only
    STATUS          current
    DESCRIPTION
        "The applied SNMP acl name."
    ::= { snmpExtMibObject 14 }

snmpSysContact        OBJECT-TYPE
    SYNTAX          OCTET STRING (SIZE (0..255))
    MAX-ACCESS      read-only
    STATUS          current
    DESCRIPTION
        "Specify SNMP system contact parameter. Range 0~255.
        0 is No command."
    ::= { snmpExtMibObject 15 }

snmpSysLocation        OBJECT-TYPE
    SYNTAX          OCTET STRING (SIZE (0..255))
    MAX-ACCESS      read-only
    STATUS          current
    DESCRIPTION
        "Specity SNMP system location parameter. Range 0~255.
        0 is No command."
    ::= { snmpExtMibObject 16 }

snmpInformReties    OBJECT-TYPE
    SYNTAX          INTEGER(0..100)
    MAX-ACCESS      read-only
    STATUS          current
    DESCRIPTION
        "Number of times to retry an Inform request. <0~100>."
    ::= { snmpExtMibObject 18 }

snmpInformTimeout    OBJECT-TYPE
    SYNTAX          INTEGER(1..1800)
    MAX-ACCESS      read-only
    STATUS          current
    DESCRIPTION
        "Snmp inform Timeout value, in seconds. <1~1800>."
    ::= { snmpExtMibObject 19 }
-- Sub Module: STM


    stmMibObject OBJECT IDENTIFIER    ::= {  stm 1  }


--
--current profile
--
stmCurrentType OBJECT-TYPE
    SYNTAX          INTEGER
    {
        default(0),
        ipv4(1),
        vlan(2),
        ipv6(3)
    }
    MAX-ACCESS      read-only
    STATUS          current
    DESCRIPTION
            "STM type:
        default(0)   provide balance to all features.
        ipv4(1)      provide maximum system utilization for unicast routing. You would typically use this profile for a router or aggregator in the middle of a network.
        vlan(2)      provide maximum system utilization for VLANs. This proflie maximizes system memory for use as a Layer 2 switch.
        ipv6(3)      provide maximum system utilization for IPv6 unicast routing.
        hardware(50) provide default hardware configure."
    DEFVAL         { default }
    ::= { stmMibObject 1 }

--
--Next profile
--

stmNextType         OBJECT-TYPE
    SYNTAX          INTEGER
    {
        default(0),
        ipv4(1),
        vlan(2),
        ipv6(3)

    }
    MAX-ACCESS      read-write
    STATUS          current
    DESCRIPTION
            "STM type:
        default(0)  provide balance to all features.
        ipv4(1)   provide maximum system utilization for unicast routing. You would typically use this profile for a router or aggregator in the middle of a network.
        vlan(2)      provide maximum system utilization for VLANs. This proflie maximizes system memory for use as a Layer 2 switch.
        ipv6(3)      provide maximum system utilization for IPv6 unicast routing.
        hardware(50) provide default hardware configure."
    DEFVAL         { default }
    ::= { stmMibObject 2 }

--
--  Show STM profile Table
--
stmShowTable OBJECT-TYPE
    SYNTAX          SEQUENCE OF StmShowEntry
    MAX-ACCESS      not-accessible
    STATUS          current
    DESCRIPTION
        "Show switch table Management profile."
    ::= { stmMibObject 3 }

stmShowEntry OBJECT-TYPE
    SYNTAX          StmShowEntry
    MAX-ACCESS      not-accessible
    STATUS          current
    DESCRIPTION
        "The entry of stmShowTable by kilo."
    INDEX    { stmShowProfileType }
    ::= { stmShowTable 1 }

StmShowEntry     ::=
    SEQUENCE {
        stmShowProfileType
            INTEGER,
        stmShowVlanNumber
            Integer32,
        stmShowVlanForwardingInstances
            Integer32,
        stmShowUcastMacAddresses
            Integer32,
        stmShowMcastMacAddresses
            Integer32,
        stmShowBlackholeMacAddresses
            Integer32,
        stmShowMaxAppliedVlanMapping
            Integer32,
        stmShowCfmLocalAndRemoteMeps
            Integer32,
        stmShowG8031Groups
            Integer32,
        stmShowG8032Rings
            Integer32,
        stmShowMacBasedVlanClassification
            Integer32,
        stmShowIpv4BasedVlanClassification
            Integer32,
        stmShowIpv6BasedVlanClassification
            Integer32,
        stmShowIpv4HostRoutes
            Integer32,
        stmShowIndirectIpv4Routes
            Integer32,
        stmShowIpv4EcmpGroups
            Integer32,
        stmShowIpv6HostRoutes
            Integer32,
        stmShowIndirectIpv6Routes
            Integer32,
        stmShowIpv6EcmpGroups
            Integer32,
        stmShowIpTunnelPeers
            Integer32,
        stmShowNatForIviPeers
            Integer32,
        stmShowIpv4McastRoutes
            Integer32,
        stmShowIpv4McastTotalMembers
            Integer32,
        stmShowIpv6McastRoutes
            Integer32,
        stmShowIpv6McastTotalMembers
            Integer32,
        stmShowIpv4SourceGuardEntries
            Integer32,
        stmShowIpv6SourceGuardEntries
            Integer32,
        stmShowIpv4AclAndQosFlowEntries
            Integer32,
        stmShowIpv6AclAndQosFlowEntries
            Integer32,
        stmShowFtn
            Integer32,
        stmShowIncomingLabelMap
            Integer32,
        stmShowVpws
            Integer32,
        stmShowLspPe
            Integer32,
        stmShowLspP
            Integer32,
        stmShowVplsPeer
            Integer32,
        stmShowVplsAc
            Integer32,
        stmShowVplsInstance
            Integer32,
        stmShowLspOam
            Integer32,
        stmShowOamForPseudoWrie
            Integer32,
        stmShowMplsApsTunnel
            Integer32,
        stmShowVlanMappingEntryAppliedPort
            Integer32,
        stmShowVlanMemberPorts
            Integer32,
        stmShowVlanMappingDefaultEntry
            Integer32,
        stmShowL2mcMemberPorts
            Integer32,
        stmShowL2mcv6Entries
            Integer32,
        stmShowL2mcv6MemberPorts
            Integer32,
        stmShowPBREntries
            Integer32,
        stmShowPBRv6Entries
            Integer32,
        stmShowVoiceVlan
            Integer32,
        stmShowG8032MemberPortsPerRing
            Integer32,
        stmShowMPLSLables
            Integer32,
        stmShowBFDSessions
            Integer32
    }

stmShowProfileType  OBJECT-TYPE
    SYNTAX          INTEGER
        {
            default(1),
            access(2),
            ipucv4(3),
            vlan(4),
            l2vpn(5),
            route(6),
            v4acl(7),
            v6acl(8),
            ipucv6(9)

        }
    MAX-ACCESS      read-only
    STATUS          current
    DESCRIPTION
            "STM type:
        default(1)  provide balance to all features.
        access(2)   provide maximum system utilization for QoS classification ACEs, and security ACEs. You would typically use this profile for an access switch at the network edge.
        ipvuc4(3)   provide maximum system utilization for unicast routing. You would typically use this profile for a router or aggregator in the middle of a network.
        vlan(4)     provide maximum system utilization for VLANs. This proflie maximizes system memory for use as a Layer 2 switch.
        l2vpn(5)    provide maximum system utilization for Layer2 VPN. This profile is only existed on metro advanced image.
        ipv6(6)     provide maximum system utilization for IPv6 unicast routing.
        route(7)    provide maximum system utilization for Ucast Routes.
        v4acl(8)    provide maximum system utilization for IPv4 ACL.
        v6acl(9)    provide maximum system utilization for IPv6 ACL.
        hardware(50) provide default hardware configure."
    ::= { stmShowEntry 1 }

stmShowVlanNumber  OBJECT-TYPE
    SYNTAX          Integer32 (0..4094)
    MAX-ACCESS      read-only
    STATUS          current
    DESCRIPTION
        "VLAN number"
    DEFVAL          { 0 }
    ::= { stmShowEntry 2 }

stmShowVlanForwardingInstances  OBJECT-TYPE
    SYNTAX          Integer32 (0..65535)
    MAX-ACCESS      read-only
    STATUS          current
    DESCRIPTION
        "VLAN forwarding instances"
    DEFVAL          { 0 }
    ::= { stmShowEntry 3 }

stmShowUcastMacAddresses  OBJECT-TYPE
    SYNTAX          Integer32 (0..65535)
    MAX-ACCESS      read-only
    STATUS          current
    DESCRIPTION
        "Ucast MAC addresses"
    DEFVAL          { 0 }
    ::= { stmShowEntry 4 }

stmShowMcastMacAddresses  OBJECT-TYPE
    SYNTAX          Integer32 (0..65535)
    MAX-ACCESS      read-only
    STATUS          current
    DESCRIPTION
        "Mcast MAC addresses"
    DEFVAL          { 0 }
    ::= { stmShowEntry 5 }

stmShowBlackholeMacAddresses  OBJECT-TYPE
    SYNTAX          Integer32 (0..65535)
    MAX-ACCESS      read-only
    STATUS          current
    DESCRIPTION
        "Blackhole MAC addresses"
    DEFVAL          { 0 }
    ::= { stmShowEntry 6 }

stmShowMaxAppliedVlanMapping  OBJECT-TYPE
    SYNTAX          Integer32 (0..65535)
    MAX-ACCESS      read-only
    STATUS          current
    DESCRIPTION
        "Max applied VLAN mapping"
    DEFVAL          { 0 }
    ::= { stmShowEntry 7 }

stmShowCfmLocalAndRemoteMeps  OBJECT-TYPE
    SYNTAX          Integer32 (0..65535)
    MAX-ACCESS      read-only
    STATUS          current
    DESCRIPTION
        "CFM local and remote MEPs"
    DEFVAL          { 0 }
    ::= { stmShowEntry 8 }

stmShowG8031Groups  OBJECT-TYPE
    SYNTAX          Integer32 (0..65535)
    MAX-ACCESS      read-only
    STATUS          current
    DESCRIPTION
        "G.8031 groups"
    DEFVAL          { 0 }
    ::= { stmShowEntry 9 }

stmShowG8032Rings  OBJECT-TYPE
    SYNTAX          Integer32 (0..65535)
    MAX-ACCESS      read-only
    STATUS          current
    DESCRIPTION
        "G.8032 rings"
    DEFVAL          { 0 }
    ::= { stmShowEntry 10 }

stmShowMacBasedVlanClassification  OBJECT-TYPE
    SYNTAX          Integer32 (0..65535)
    MAX-ACCESS      read-only
    STATUS          current
    DESCRIPTION
        "MAC based VLAN classification"
    DEFVAL          { 0 }
    ::= { stmShowEntry 11 }

stmShowIpv4BasedVlanClassification  OBJECT-TYPE
    SYNTAX          Integer32 (0..65535)
    MAX-ACCESS      read-only
    STATUS          current
    DESCRIPTION
        "IPv4 based VLAN classification"
    DEFVAL          { 0 }
    ::= { stmShowEntry 12 }

stmShowIpv6BasedVlanClassification  OBJECT-TYPE
    SYNTAX          Integer32 (0..65535)
    MAX-ACCESS      read-only
    STATUS          current
    DESCRIPTION
        "IPv6 based VLAN classification"
    DEFVAL          { 0 }
    ::= { stmShowEntry 13 }

stmShowIpv4HostRoutes  OBJECT-TYPE
    SYNTAX          Integer32 (0..65535)
    MAX-ACCESS      read-only
    STATUS          current
    DESCRIPTION
        "IPv4 host routes"
    DEFVAL          { 0 }
    ::= { stmShowEntry 14 }

stmShowIndirectIpv4Routes  OBJECT-TYPE
    SYNTAX          Integer32 (0..65535)
    MAX-ACCESS      read-only
    STATUS          current
    DESCRIPTION
        "Indirect IPv4 routes"
    DEFVAL          { 0 }
    ::= { stmShowEntry 15 }

stmShowIpv4EcmpGroups  OBJECT-TYPE
    SYNTAX          Integer32 (0..65535)
    MAX-ACCESS      read-only
    STATUS          current
    DESCRIPTION
        "IPv4 ECMP groups"
    DEFVAL          { 0 }
    ::= { stmShowEntry 16 }

stmShowIpv6HostRoutes  OBJECT-TYPE
    SYNTAX          Integer32 (0..65535)
    MAX-ACCESS      read-only
    STATUS          current
    DESCRIPTION
        "IPv6 host routes"
    DEFVAL          { 0 }
    ::= { stmShowEntry 17 }

stmShowIndirectIpv6Routes  OBJECT-TYPE
    SYNTAX          Integer32 (0..65535)
    MAX-ACCESS      read-only
    STATUS          current
    DESCRIPTION
        "Indirect IPv6 routes"
    DEFVAL          { 0 }
    ::= { stmShowEntry 18 }

stmShowIpv6EcmpGroups  OBJECT-TYPE
    SYNTAX          Integer32 (0..65535)
    MAX-ACCESS      read-only
    STATUS          current
    DESCRIPTION
        "IPv6 ECMP groups"
    DEFVAL          { 0 }
    ::= { stmShowEntry 19 }

stmShowIpTunnelPeers  OBJECT-TYPE
    SYNTAX          Integer32 (0..65535)
    MAX-ACCESS      read-only
    STATUS          current
    DESCRIPTION
        "IP Tunnel Peers"
    DEFVAL          { 0 }
    ::= { stmShowEntry 20 }

stmShowNatForIviPeers  OBJECT-TYPE
    SYNTAX          Integer32 (0..65535)
    MAX-ACCESS      read-only
    STATUS          current
    DESCRIPTION
        "NAT For IVI Peers"
    DEFVAL          { 0 }
    ::= { stmShowEntry 21 }

stmShowIpv4McastRoutes  OBJECT-TYPE
    SYNTAX          Integer32 (0..65535)
    MAX-ACCESS      read-only
    STATUS          current
    DESCRIPTION
        "IPv4 Mcast routes"
    DEFVAL          { 0 }
    ::= { stmShowEntry 22 }

stmShowIpv4McastTotalMembers  OBJECT-TYPE
    SYNTAX          Integer32 (0..65535)
    MAX-ACCESS      read-only
    STATUS          current
    DESCRIPTION
        "IPv4 Mcast total members"
    DEFVAL          { 0 }
    ::= { stmShowEntry 23 }

stmShowIpv6McastRoutes  OBJECT-TYPE
    SYNTAX          Integer32 (0..65535)
    MAX-ACCESS      read-only
    STATUS          current
    DESCRIPTION
        "IPv6 Mcast routes"
    DEFVAL          { 0 }
    ::= { stmShowEntry 24 }

stmShowIpv6McastTotalMembers  OBJECT-TYPE
    SYNTAX          Integer32 (0..65535)
    MAX-ACCESS      read-only
    STATUS          current
    DESCRIPTION
        "IPv6 Mcast total members"
    DEFVAL          { 0 }
    ::= { stmShowEntry 25 }

stmShowIpv4SourceGuardEntries  OBJECT-TYPE
    SYNTAX          Integer32 (0..65535)
    MAX-ACCESS      read-only
    STATUS          current
    DESCRIPTION
        "IPv4 source guard entries"
    DEFVAL          { 0 }
    ::= { stmShowEntry 26 }

stmShowIpv6SourceGuardEntries  OBJECT-TYPE
    SYNTAX          Integer32 (0..65535)
    MAX-ACCESS      read-only
    STATUS          current
    DESCRIPTION
        "IPv6 source guard entries"
    DEFVAL          { 0 }
    ::= { stmShowEntry 27 }

stmShowIpv4AclAndQosFlowEntries  OBJECT-TYPE
    SYNTAX          Integer32 (0..65535)
    MAX-ACCESS      read-only
    STATUS          current
    DESCRIPTION
        "IPv4 ACL/QOS flow entries"
    DEFVAL          { 0 }
    ::= { stmShowEntry 28 }

stmShowIpv6AclAndQosFlowEntries  OBJECT-TYPE
    SYNTAX          Integer32 (0..65535)
    MAX-ACCESS      read-only
    STATUS          current
    DESCRIPTION
        "IPv6 ACL/QOS flow entries"
    DEFVAL          { 0 }
    ::= { stmShowEntry 29 }

stmShowFtn  OBJECT-TYPE
    SYNTAX          Integer32 (0..65535)
    MAX-ACCESS      read-only
    STATUS          current
    DESCRIPTION
        "FTN"
    DEFVAL          { 0 }
    ::= { stmShowEntry 30 }

stmShowIncomingLabelMap  OBJECT-TYPE
    SYNTAX          Integer32 (0..65535)
    MAX-ACCESS      read-only
    STATUS          current
    DESCRIPTION
        "Incoming Label Map"
    DEFVAL          { 0 }
    ::= { stmShowEntry 31 }

stmShowVpws  OBJECT-TYPE
    SYNTAX          Integer32 (0..65535)
    MAX-ACCESS      read-only
    STATUS          current
    DESCRIPTION
        "vpws"
    DEFVAL          { 0 }
    ::= { stmShowEntry 32 }

stmShowLspPe  OBJECT-TYPE
    SYNTAX          Integer32 (0..65535)
    MAX-ACCESS      read-only
    STATUS          current
    DESCRIPTION
        "LSP PE"
    DEFVAL          { 0 }
    ::= { stmShowEntry 33 }

stmShowLspP  OBJECT-TYPE
    SYNTAX          Integer32 (0..65535)
    MAX-ACCESS      read-only
    STATUS          current
    DESCRIPTION
        "LSP P"
    DEFVAL          { 0 }
    ::= { stmShowEntry 34 }

stmShowVplsPeer  OBJECT-TYPE
    SYNTAX          Integer32 (0..65535)
    MAX-ACCESS      read-only
    STATUS          current
    DESCRIPTION
        "VPLS PEER"
    DEFVAL          { 0 }
    ::= { stmShowEntry 35 }

stmShowVplsAc  OBJECT-TYPE
    SYNTAX          Integer32 (0..65535)
    MAX-ACCESS      read-only
    STATUS          current
    DESCRIPTION
        "VPLS AC"
    DEFVAL          { 0 }
    ::= { stmShowEntry 36 }

stmShowVplsInstance  OBJECT-TYPE
    SYNTAX          Integer32 (0..65535)
    MAX-ACCESS      read-only
    STATUS          current
    DESCRIPTION
        "VPLS Instance"
    DEFVAL          { 0 }
    ::= { stmShowEntry 37 }

stmShowLspOam  OBJECT-TYPE
    SYNTAX          Integer32 (0..65535)
    MAX-ACCESS      read-only
    STATUS          current
    DESCRIPTION
        "LSP OAM"
    DEFVAL          { 0 }
    ::= { stmShowEntry 38 }

stmShowOamForPseudoWrie  OBJECT-TYPE
    SYNTAX          Integer32 (0..65535)
    MAX-ACCESS      read-only
    STATUS          current
    DESCRIPTION
        "OAM for Pseudo Wrie"
    DEFVAL          { 0 }
    ::= { stmShowEntry 39 }

stmShowMplsApsTunnel  OBJECT-TYPE
    SYNTAX          Integer32 (0..65535)
    MAX-ACCESS      read-only
    STATUS          current
    DESCRIPTION
        "MPLS APS Tunnel"
    DEFVAL          { 0 }
    ::= { stmShowEntry 40 }

stmShowVlanMappingEntryAppliedPort  OBJECT-TYPE
    SYNTAX          Integer32 (0..65535)
    MAX-ACCESS      read-only
    STATUS          current
    DESCRIPTION
        "Vlan Mapping Entry Applied Port"
    DEFVAL          { 0 }
    ::= { stmShowEntry 41 }

stmShowVlanMemberPorts  OBJECT-TYPE
    SYNTAX          Integer32 (0..65535)
    MAX-ACCESS      read-only
    STATUS          current
    DESCRIPTION
        "Vlan Member Ports"
    DEFVAL          { 0 }
    ::= { stmShowEntry 42 }
    
stmShowVlanMappingDefaultEntry  OBJECT-TYPE
    SYNTAX          Integer32 (0..65535)
    MAX-ACCESS      read-only
    STATUS          current
    DESCRIPTION
        "Vlan Mapping Default Entry"
    DEFVAL          { 0 }
    ::= { stmShowEntry 43 }

stmShowL2mcMemberPorts  OBJECT-TYPE
    SYNTAX          Integer32 (0..65535)
    MAX-ACCESS      read-only
    STATUS          current
    DESCRIPTION
        "L2mc Member Ports"
    DEFVAL          { 0 }
    ::= { stmShowEntry 44 }

stmShowL2mcv6Entries  OBJECT-TYPE
    SYNTAX          Integer32 (0..65535)
    MAX-ACCESS      read-only
    STATUS          current
    DESCRIPTION
        "L2mcv6 Entries"
    DEFVAL          { 0 }
    ::= { stmShowEntry 45 }
    
stmShowL2mcv6MemberPorts  OBJECT-TYPE
    SYNTAX          Integer32 (0..65535)
    MAX-ACCESS      read-only
    STATUS          current
    DESCRIPTION
        "L2mcv6 Member Ports"
    DEFVAL          { 0 }
    ::= { stmShowEntry 46 }
    
stmShowPBREntries  OBJECT-TYPE
    SYNTAX          Integer32 (0..65535)
    MAX-ACCESS      read-only
    STATUS          current
    DESCRIPTION
        "PBR Entries"
    DEFVAL          { 0 }
    ::= { stmShowEntry 47 }

stmShowPBRv6Entries  OBJECT-TYPE
    SYNTAX          Integer32 (0..65535)
    MAX-ACCESS      read-only
    STATUS          current
    DESCRIPTION
        "PBRv6 Entries"
    DEFVAL          { 0 }
    ::= { stmShowEntry 48 }
    
stmShowVoiceVlan  OBJECT-TYPE
    SYNTAX          Integer32 (0..65535)
    MAX-ACCESS      read-only
    STATUS          current
    DESCRIPTION
        "Voice Vlan"
    DEFVAL          { 0 }
    ::= { stmShowEntry 49 }

stmShowG8032MemberPortsPerRing  OBJECT-TYPE
    SYNTAX          Integer32 (0..65535)
    MAX-ACCESS      read-only
    STATUS          current
    DESCRIPTION
        "G8032 Member Ports Per Ring"
    DEFVAL          { 0 }
    ::= { stmShowEntry 50 }

stmShowMPLSLables   OBJECT-TYPE
    SYNTAX          Integer32 (0..65535)
    MAX-ACCESS      read-only
    STATUS          current
    DESCRIPTION
        "MPLS Lables"
    DEFVAL          { 0 }
    ::= { stmShowEntry 51 }
    
stmShowBFDSessions  OBJECT-TYPE
    SYNTAX          Integer32 (0..65535)
    MAX-ACCESS      read-only
    STATUS          current
    DESCRIPTION
        "BFD Sessions"
    DEFVAL          { 0 }
    ::= { stmShowEntry 52 }
    
    
-- Sub Module: DNSCLIENT

         
dnsClientMibObject OBJECT IDENTIFIER    ::= {  dnsClient 1  }

--
--  add/remove a static host
--

dnsClientHostTable         OBJECT-TYPE
    SYNTAX          SEQUENCE OF DnsClientHostEntry
    MAX-ACCESS      not-accessible
    STATUS          current
    DESCRIPTION        "The table containing information of DNS host."
    ::= { dnsClientMibObject 1 }
                           
dnsClientHostEntry  OBJECT-TYPE
    SYNTAX          DnsClientHostEntry
    MAX-ACCESS      not-accessible
    STATUS          current
    DESCRIPTION        
        "An entry containing information of DNS clients host."
    INDEX     { dnsClientHostIpHostIndex }
    ::= { dnsClientHostTable 1 }

DnsClientHostEntry    ::=
    SEQUENCE 
    {
        dnsClientHostIpHostIndex				
            INTEGER,
        dnsClientHostIpHostName         
            OCTET STRING ,
        dnsClientHostIpAddress           
            IpAddress,
        dnsClientHostRowStatus         
            RowStatus 
    }

dnsClientHostIpHostIndex         OBJECT-TYPE
    SYNTAX          INTEGER (1..1024)
    MAX-ACCESS      read-only
    STATUS          current
    DESCRIPTION
        "DNS host IP's index."
    ::= { dnsClientHostEntry 1 }
    
dnsClientHostIpHostName         OBJECT-TYPE
    SYNTAX          OCTET STRING (SIZE (0..255))
    MAX-ACCESS      read-write
    STATUS          current
    DESCRIPTION        
        "DNS host IP host name."
    ::= { dnsClientHostEntry 2 }

dnsClientHostIpAddress         OBJECT-TYPE
    SYNTAX          IpAddress
    MAX-ACCESS      read-write
    STATUS          current
    DESCRIPTION        
        "DNS host IP addresses."
    ::= { dnsClientHostEntry 3 }

dnsClientHostRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { dnsClientHostEntry 4 }        
                    


--
--  add/remove a static domain
--

dnsClientDomainTable         OBJECT-TYPE
    SYNTAX          SEQUENCE OF DnsClientDomainEntry
    MAX-ACCESS      not-accessible
    STATUS          current
    DESCRIPTION        "The table containing information of DNS domain."
    ::= { dnsClientMibObject 2 }
                           
dnsClientDomainEntry         OBJECT-TYPE
    SYNTAX          DnsClientDomainEntry
    MAX-ACCESS      not-accessible
    STATUS          current
    DESCRIPTION        "An entry containing information of DNS domain."
    INDEX     { dnsClientDomainIndex }
    ::= { dnsClientDomainTable 1 }

DnsClientDomainEntry    ::=
    SEQUENCE 
    {
		dnsClientDomainIndex		
		    INTEGER,
        dnsClientDomainName     
            OCTET STRING,
        dnsClientDomainRowStatus 
            RowStatus 
    }


dnsClientDomainIndex         OBJECT-TYPE
    SYNTAX          INTEGER (1..6)
    MAX-ACCESS      read-only
    STATUS          current
    DESCRIPTION
        "DNS domain's index."
    ::= { dnsClientDomainEntry 1 }
		    
dnsClientDomainName         OBJECT-TYPE
    SYNTAX          OCTET STRING (SIZE(0..256))
    MAX-ACCESS      read-write
    STATUS          current
    DESCRIPTION        "DNS domain name."
       -- DEFVAL { ipv4 }
    ::= { dnsClientDomainEntry 2 }

dnsClientDomainRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { dnsClientDomainEntry 3 }        
                    

--
--  add/remove a static DNS server
--

dnsClientServerTable OBJECT-TYPE
	SYNTAX          SEQUENCE OF DnsClientServerEntry
	MAX-ACCESS      not-accessible
	STATUS          current
	DESCRIPTION 
        "The table containing information of DNS server."
    ::= { dnsClientMibObject 3 }
                           
dnsClientServerEntry OBJECT-TYPE
	SYNTAX          DnsClientServerEntry
	MAX-ACCESS      not-accessible
	STATUS          current
	DESCRIPTION 
        "An entry containing information of DNS clients server."
	INDEX   { dnsClientServerIpAddress }
    ::= { dnsClientServerTable 1 }


DnsClientServerEntry   ::=
    SEQUENCE {
--      dnsClientServerIpAddressType     
--         		InetAddressType,
        dnsClientServerIpAddress           
        			IpAddress,
        dnsClientServerRowStatus          
        			RowStatus
        }

--dnsClientServerIpAddressType         OBJECT-TYPE
--    SYNTAX          InetAddressType
--    MAX-ACCESS      read-write
--    STATUS          current
--    DESCRIPTION        "DNS host IP addresses type (IPv4 or IPv6)."
--        DEFVAL { ipv4 }
--    ::= { dnsClientServerEntry 1 }

dnsClientServerIpAddress OBJECT-TYPE
	SYNTAX          IpAddress
	MAX-ACCESS      read-only
	STATUS          current
	DESCRIPTION 
        "DNS host IP addresses."
	::= { dnsClientServerEntry 1 }

dnsClientServerRowStatus OBJECT-TYPE
	SYNTAX          RowStatus
	MAX-ACCESS      read-create
	STATUS          current
	DESCRIPTION
        "The status of this conceptual row.Now only realize CreateAndGo and Destroy and Active.
        1 means Active
        4 means CreateAndGo
        6 means Destroy"
	::= { dnsClientServerEntry 2 }      
                    
-- Sub Module: SSH


-- ==================================================================
--
-- =====================object definition begin======================
--
-- ==================================================================
        sshServer      OBJECT IDENTIFIER    ::= { ssh 1 }


--
--sshServerEnable
--
sshServerEnable         OBJECT-TYPE
    SYNTAX          INTEGER
    {
        enable(1),
        disable(2)
    }
    MAX-ACCESS      read-write
    STATUS          current
    DESCRIPTION 
        "SSH server status (enable(1) or disable(2)).
        Default value is enable(1)."
    DEFVAL{ 1 }
    ::= { sshServer 1 }


--
--sshServerVersion
--
sshServerVersion         OBJECT-TYPE
    SYNTAX          INTEGER
    {
        v1(1),
        v2(2),
        all(3)
    }
    MAX-ACCESS      read-write
    STATUS          current
    DESCRIPTION 
    "SSH server version. 
    v1(1), SSH version v1
    v2(2), SSH version v2 
    all(3), SSH version v1 and v2.
    Default value is v2(2)."
    DEFVAL{ 2 }
    ::= { sshServer 2 }


--
--sshServerAuthTimer
--
sshServerAuthTimer         OBJECT-TYPE
    SYNTAX          Integer32(1..120)
    MAX-ACCESS      read-write
    STATUS          current
    DESCRIPTION 
        "SSH server login grace time.Range 1~120.
        Default value is 120."
    DEFVAL{ 120 }
    ::= { sshServer 3 }

--
--sshServerAuthRetries
--
sshServerAuthRetries         OBJECT-TYPE
    SYNTAX          Integer32(1..6)
    MAX-ACCESS      read-write
    STATUS          current
    DESCRIPTION 
        "SSH server max authentication retry times.Range 1~6.
        Default value is 6."
		DEFVAL{ 6 }
    ::= { sshServer 4 }

--
--sshServerAuthType
--
sshServerAuthType         OBJECT-TYPE
    SYNTAX          INTEGER
    {
        password(1),
        rsa(2),
        publicKey(3),
        passwordRsa(4),
        passwordPublicKey(5),
        rsaPublicKey(6),
        all(7)
    }
    MAX-ACCESS      read-write
    STATUS          current
    DESCRIPTION 
        "SSH server authentication type.
        password(1): Enable password authentication
        rsa(2): Enable SSHv1 RSA authentication
        publicKey(3): Enable SSHv2 public key authentication
        passwordRsa(4): Enable password and sshv1 Rsa authentication
        passwordPublicKey(5): Enable password and sshv2 public-key authentication.
        rsaPublicKey(6): Enable sshv1 rsa and sshv2 public-key authentication.
        all(7): Enable all authentication type.
        Default value is 5."
		DEFVAL{ 5 }
    ::= { sshServer 5 }

--
--sshServerRekeyInterval
--
sshServerRekeyInterval         OBJECT-TYPE
    SYNTAX          Integer32(1..1440)
    MAX-ACCESS      read-write
    STATUS          current
    DESCRIPTION 
        "Rekey interval of ip ssh server.Range 1~1440.
        Default value is 60."
    DEFVAL{ 60 }
    ::= { sshServer 6 }
 
 
sshRsaKey      OBJECT IDENTIFIER    ::= { ssh 2 }

--
--sshImportRsaKeyTable
--
sshImportRsaKeyTable         OBJECT-TYPE
    SYNTAX          SEQUENCE OF SshImportRsaKeyEntry
    MAX-ACCESS      not-accessible
    STATUS          current
    DESCRIPTION
        "Snmp community configure."
    ::= { sshRsaKey 8 }
 
sshImportRsaKeyEntry         OBJECT-TYPE
    SYNTAX          SshImportRsaKeyEntry
    MAX-ACCESS      not-accessible
    STATUS          current
    DESCRIPTION
        "The entry of sshImportRsaKeyTable."
    INDEX     { sshImportRsaKeyIndex }
    ::= { sshImportRsaKeyTable 1 }                         
                          
 
    SshImportRsaKeyEntry    ::=
    SEQUENCE 
    {
        sshImportRsaKeyIndex
            INTEGER,
        sshImportRsaKeyName
            OCTET STRING,
        sshImportRsaMgmtIf
            INTEGER,
        sshImportRsaKeyGenType 
            INTEGER,
        sshImportRsaKeyBits
            Integer32,
        sshImportRsaKeyFileName
            OCTET STRING,
        sshImportRsaKeyType
            INTEGER,
        sshImportRsaKeyFormatType    
            INTEGER,
        sshImportRsaKeyPasswd
            OCTET STRING, 
        sshImportRsaKeyRowStatus 
            RowStatus 
    }
 
sshImportRsaKeyIndex         OBJECT-TYPE
    SYNTAX          INTEGER (0..31)
    MAX-ACCESS      not-accessible
    STATUS          current
    DESCRIPTION
        "SSH rsa key's index.Range 0~31."
    ::= { sshImportRsaKeyEntry 1 }
 
sshImportRsaKeyName         OBJECT-TYPE
    SYNTAX          OCTET STRING (SIZE (1..31))
    MAX-ACCESS      read-write
    STATUS          current
    DESCRIPTION
        "SSH rsa key's name.Range 1~31"
    ::= { sshImportRsaKeyEntry 2 }
 
sshImportRsaMgmtIf      OBJECT-TYPE
    SYNTAX             INTEGER
      {
          getValue(0),
          noUse(1),
          setMgmtIf(2)
      }
    MAX-ACCESS      read-write
    STATUS          current
    DESCRIPTION
        "configuraion mgmt-if.getValue(0),no use(1),setMgmtIf(2)."
    ::= { sshImportRsaKeyEntry 3 }   
          
sshImportRsaKeyGenType         OBJECT-TYPE
    SYNTAX          INTEGER
    {
        autoGen(1),
        localFile(2),
        ftpFile(3),
        tftpFile(4)
    }
    MAX-ACCESS      read-write
    STATUS          current
    DESCRIPTION
        "sshImportRsaKeyGenType,Now only support auto-gen and local file.
        if autoGen is selected the index is invalid, it will select the index itself.
        1 autoGen.
        2 localFile.
        3 ftpFile.
        4 tftpFile."
    ::= { sshImportRsaKeyEntry 4 }
            
sshImportRsaKeyBits         OBJECT-TYPE
    SYNTAX          Integer32(768..4096)
    MAX-ACCESS      read-write
    STATUS          current
    DESCRIPTION
        "sshImportRsaKeyBits.Range 768~4096."
    ::= { sshImportRsaKeyEntry 5 }             
 
sshImportRsaKeyFileName         OBJECT-TYPE
    SYNTAX          OCTET STRING (SIZE (0..63))
    MAX-ACCESS      read-write
    STATUS          current
    DESCRIPTION
        "sshImportRsaKeyFileName.Range 0~63."
    ::= { sshImportRsaKeyEntry 6 }   
                        
 
sshImportRsaKeyType         OBJECT-TYPE
    SYNTAX          INTEGER
    {
        public(1),
        private(2)
    }
    MAX-ACCESS      read-write
    STATUS          current
    DESCRIPTION
        "sshImportRsaKeyGenType
         public(1): Import public key
         private(2): Import private key"
    ::= { sshImportRsaKeyEntry 7 }    
                        
sshImportRsaKeyFormatType         OBJECT-TYPE
    SYNTAX          INTEGER
    {
        der(1),
        derHex(2),
        pem(3),
        ssh1(4),
        ssh2(5)
    }
    MAX-ACCESS      read-write
    STATUS          current
    DESCRIPTION
        "sshImportRsaKeyGenType
        der(1): DER format
        derHex(2): DER HEX format
        pem(3): PEM format
        ssh1(4): SSHv1 format
        ssh2(5): SSHv2 format"
    ::= { sshImportRsaKeyEntry 8 }                                
                        
sshImportRsaKeyPasswd         OBJECT-TYPE
    SYNTAX          OCTET STRING (SIZE (6..256))
    MAX-ACCESS      read-write
    STATUS          current
    DESCRIPTION
        "SSH rsa key's Password.Range 6~256."
    ::= { sshImportRsaKeyEntry 9}
                        
sshImportRsaKeyRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { sshImportRsaKeyEntry 10 }                
                        
                        
--
--sshExportRsaKeyTable
--
sshExportRsaKeyTable         OBJECT-TYPE
    SYNTAX          SEQUENCE OF SshExportRsaKeyEntry
    MAX-ACCESS      not-accessible
    STATUS          current
    DESCRIPTION
        "Snmp community configure."
    ::= { sshRsaKey 9 }
    
sshExportRsaKeyEntry         OBJECT-TYPE
    SYNTAX          SshExportRsaKeyEntry
    MAX-ACCESS      not-accessible
    STATUS          current
    DESCRIPTION
        "The entry of sshExportRsaKeyTable."
    INDEX     { sshExportRsaKeyIndex }
    ::= { sshExportRsaKeyTable 1 }                         
                          
SshExportRsaKeyEntry    ::=
    SEQUENCE 
    {
        sshExportRsaKeyIndex
            INTEGER, 
        sshExportRsaKeyName
            OCTET STRING,
        sshExportRsaMgmtIf
            INTEGER,    
        sshExportRsaKeyExType
            INTEGER,
        sshExportRsaKeyFileName
            OCTET STRING,
        sshExportRsaKeyType
            INTEGER,
        sshExportRsaKeyFormatType    
            INTEGER,
        sshExportRsaKeyEncryptType    
            INTEGER,
        sshExportRsaKeyPassword
            OCTET STRING,
        sshExportRsaKeyRowStatus 
            RowStatus 
    }
sshExportRsaKeyIndex         OBJECT-TYPE
    SYNTAX          INTEGER (0)
    MAX-ACCESS      not-accessible
    STATUS          current
    DESCRIPTION
        "SSH rsa key's index."
    ::= { sshExportRsaKeyEntry 1 }
    
sshExportRsaKeyName         OBJECT-TYPE
    SYNTAX          OCTET STRING (SIZE (1..60))
    MAX-ACCESS      read-write
    STATUS          current
    DESCRIPTION
        "SSH rsa key's name.Range 1~60."
    ::= { sshExportRsaKeyEntry 2 }
 
sshExportRsaMgmtIf   OBJECT-TYPE
    SYNTAX             INTEGER
      {
          getValue(0),
          noUse(1),
          setMgmtIf(2)
      }
    MAX-ACCESS      read-write
    STATUS          current
    DESCRIPTION
        "configuraion mgmt-if.getValue(0),no use(1),setMgmtIf(2)."
    ::= { sshExportRsaKeyEntry 3 }        
        
sshExportRsaKeyExType         OBJECT-TYPE
    SYNTAX          INTEGER
    {
        localFile(1),
        ftpFile(2),
        tftpFile(3)
    }
    MAX-ACCESS      read-write
    STATUS          current
    DESCRIPTION
        "sshExportRsaKeyGenType,Now only support local-file.
        1 localFile.
        2 ftpFile.
        3 tftpFile."
    ::= { sshExportRsaKeyEntry 4 }
            
 
sshExportRsaKeyFileName         OBJECT-TYPE
    SYNTAX          OCTET STRING  (SIZE (0..256))
    MAX-ACCESS      read-write
    STATUS          current
    DESCRIPTION
        "sshExportRsaKeyFileName.Range 0~256."
    ::= { sshExportRsaKeyEntry 5 }   
                        
 
sshExportRsaKeyType         OBJECT-TYPE
    SYNTAX          INTEGER
    {
        public(1),
        private(2)
    }
    MAX-ACCESS      read-write
    STATUS          current
    DESCRIPTION
        "sshExportRsaKeyGenType
        public(1):  Export public key
        private(2): Export private key"
    ::= { sshExportRsaKeyEntry 6 }    
                        
sshExportRsaKeyFormatType         OBJECT-TYPE
    SYNTAX          INTEGER
    {
        der(1),
        derHex(2),
        pem(3),
        ssh1(4),
        ssh2(5)
    }
    MAX-ACCESS      read-write
    STATUS          current
    DESCRIPTION
        "sshExportRsaKeyGenType
        der(1):    DER format
        derHex(2): DER HEX format
        pem(3):    PEM format
        ssh1(4):   SSHv1 format
        ssh2(5):   SSHv2 format"
    ::= { sshExportRsaKeyEntry 7 }    
                                
sshExportRsaKeyEncryptType         OBJECT-TYPE
    SYNTAX          INTEGER
    {
        des(1),
        des3(2),
        aes128(3),
        aes192(4),
        aes256(5)
    }
    MAX-ACCESS      read-write
    STATUS          current
    DESCRIPTION
        "sshExportRsaKeyEncryptType
        des(1):    Encrypt the private key with DES
        des3(2):   Encrypt the private key with Triple DES
        aes128(3): Encrypt the private key with AES 128 bits
        aes192(4): Encrypt the private key with AES 192 bits
        aes256(5): Encrypt the private key with AES 256 bits"
    ::= { sshExportRsaKeyEntry 8 }                                    
                                
sshExportRsaKeyPassword         OBJECT-TYPE
    SYNTAX          OCTET STRING (SIZE (6..256))
    MAX-ACCESS      read-write
    STATUS          current
    DESCRIPTION
        "SSH rsa key's Password.Range 6~256."
    ::= { sshExportRsaKeyEntry 9 }                                                                                        
   
sshExportRsaKeyRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { sshExportRsaKeyEntry 10 }          
                                

sshHostKey      OBJECT IDENTIFIER    ::= { ssh 3 }        
                
--
--sshHostKeyRsaTable
--
                        
sshHostKeyRsaTable  OBJECT-TYPE
    SYNTAX          SEQUENCE OF SshHostKeyRsaEntry
    MAX-ACCESS      not-accessible
    STATUS          current
    DESCRIPTION
        "Ssh server rsa host key."
    ::= { sshHostKey 7 }
                        
                        
sshHostKeyRsaEntry  OBJECT-TYPE
    SYNTAX          SshHostKeyRsaEntry
    MAX-ACCESS      not-accessible
    STATUS          current
    DESCRIPTION
        "The entry of sshHostKeyRsaTable."
    INDEX     { sshHostKeyRsaIndex }
    ::= { sshHostKeyRsaTable 1 }                        
                                
                                
SshHostKeyRsaEntry    ::=
    SEQUENCE {
        sshHostKeyRsaIndex
            INTEGER, 
        sshHostKeyRsaName
            OCTET STRING,
        sshHostKeyRsaRowStatus 
            RowStatus 
    }        
sshHostKeyRsaIndex         OBJECT-TYPE
    SYNTAX          INTEGER (0)
    MAX-ACCESS      not-accessible
    STATUS          current
    DESCRIPTION
        "SSH rsa key's index."
    ::= { sshHostKeyRsaEntry 1 }
            
sshHostKeyRsaName         OBJECT-TYPE
    SYNTAX          OCTET STRING (SIZE (1..31))
    MAX-ACCESS      read-write
    STATUS          current
    DESCRIPTION
        "SSH rsa key's name. The rsa key should be exist first by sshRsaKey node. Starting with alphabetic and can only include [0-9a-zA-Z.-_]. Its length range is [1, 32)"
    ::= { sshHostKeyRsaEntry 2 }                    
                                
sshHostKeyRsaRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { sshHostKeyRsaEntry 3 }                                                                            


-- Sub Module: DHCP


dhcpGlobal OBJECT IDENTIFIER    ::= {  dhcp 1  }
    
dhcpEnable          OBJECT-TYPE
    SYNTAX          INTEGER
    {
        enable(1),
        disable(2)
    }
    MAX-ACCESS      read-write
    STATUS          current
    DESCRIPTION        
        "DHCPStatus (enable or disable)."
    DEFVAL { disable }
    ::= { dhcpGlobal 1 }
        
        
dhcpSnoop OBJECT IDENTIFIER    ::= {  dhcp 2  }

        
dhcpSnoopEnable         OBJECT-TYPE
    SYNTAX          INTEGER
    {
        enable(1),
        disable(2)
    }
    MAX-ACCESS      read-write
    STATUS          current
    DESCRIPTION        
        "DHCP SnoopingStatus (enable or disable)."
    DEFVAL     { disable }
    ::= { dhcpSnoop 1 }
                                     
                                       
dhcpSnoopVerMac         OBJECT-TYPE
    SYNTAX          INTEGER
    {
        enable(1),
        disable(2)
    }
    MAX-ACCESS      read-write
    STATUS          current
    DESCRIPTION        
        "DHCP Snooping verify mac-address (enable or disable)."
    DEFVAL { enable }
    ::= { dhcpSnoop 2 }


dhcpSnoopOption82    OBJECT-TYPE
    SYNTAX          INTEGER
    {
        enable(1),
        disable(2)
    }
    MAX-ACCESS      read-write
    STATUS          current
    DESCRIPTION        
        "DHCP Snooping option-82 data insertion (enable or disable)."
    DEFVAL  { disable }
    ::= { dhcpSnoop 3 }


dhcpSnoopOption82AllowUntrusted         OBJECT-TYPE
    SYNTAX          INTEGER
        {
            enable(1),
            disable(2)
        }
    MAX-ACCESS      read-write
    STATUS          current
    DESCRIPTION        "DHCP Snooping allow untrusted ports to accept incoming DHCP packets with relay agent information."
    DEFVAL  { disable }
    ::= { dhcpSnoop 4 }
        
dhcpSnoopAutoSaveInterval         OBJECT-TYPE
    SYNTAX          INTEGER (15..1200)
    MAX-ACCESS      read-write
    STATUS          current
    DESCRIPTION        "Specify DHCP snooping database auto save parameter."
    DEFVAL { 600 }
    ::= { dhcpSnoop 5 }
        
dhcpSnoopVlanTable           OBJECT-TYPE
    SYNTAX          SEQUENCE OF DhcpSnoopVlanEntry
    MAX-ACCESS      not-accessible
    STATUS          current
    DESCRIPTION        "A table is used to configure and monitor DHCP Snooping
    STATUS          of VLANs."
    ::= { dhcpSnoop 6 }

dhcpSnoopVlanEntry          OBJECT-TYPE
    SYNTAX          DhcpSnoopVlanEntry
    MAX-ACCESS      not-accessible
    STATUS          current
    DESCRIPTION        
        "The entry information about dhcpSnoopVlanTable."
    INDEX         
    {
        dhcpSnoopVlanIndex
    }
    ::= { dhcpSnoopVlanTable 1 }
 
    DhcpSnoopVlanEntry    ::=
    SEQUENCE
    {
        dhcpSnoopVlanIndex     
            Integer32,
        dhcpSnoopVlanEnable    
            TruthValue
    }

dhcpSnoopVlanIndex                OBJECT-TYPE
    SYNTAX          Integer32(0..4096)
    MAX-ACCESS      not-accessible
    STATUS          current
    DESCRIPTION        
        "current VLAN index."
    ::= { dhcpSnoopVlanEntry 1 }

dhcpSnoopVlanEnable                OBJECT-TYPE
    SYNTAX          TruthValue
    MAX-ACCESS      read-write
    STATUS          current
    DESCRIPTION        
        "DHCP SnoopingStatus ofcurrent VLAN."
--  DEFVAL    INDEX     { false }
    ::= { dhcpSnoopVlanEntry 2 }


dhcpSnoopBindingTable         OBJECT-TYPE
    SYNTAX          SEQUENCE OF DhcpSnoopBindingEntry
    MAX-ACCESS      not-accessible
    STATUS          current
    DESCRIPTION        
        "The table containing information of DHCP clients listened by
        DHCP snooping and it's enabled or disabled by setting
        dhcpSnoopEnable node."
    ::= { dhcpSnoop 7 }
                           
dhcpSnoopBindingEntry         OBJECT-TYPE
    SYNTAX          DhcpSnoopBindingEntry
    MAX-ACCESS      not-accessible
    STATUS          current
    DESCRIPTION        
        "An entry containing information of DHCP clients."
    INDEX          { dhcpSnoopClientVlan, dhcpSnoopClientMacAddress }
    ::= { dhcpSnoopBindingTable 1 }

DhcpSnoopBindingEntry    ::=
    SEQUENCE 
    {
        dhcpSnoopClientVlan    
            Integer32,
        dhcpSnoopClientMacAddress  
            MacAddress,
        dhcpSnoopClientIpAddressType 
            InetAddressType,
        dhcpSnoopClientIpAddress   
            InetAddress,
        dhcpSnoopClientIfindex    
            Integer32,
        dhcpSnoopClientExpiry      
            Integer32,
        dhcpSnoopClientRowStatus 
            RowStatus 
    }

dhcpSnoopClientVlan         OBJECT-TYPE
    SYNTAX          Integer32
    MAX-ACCESS      not-accessible
    STATUS          current
    DESCRIPTION        
        "DHCP clients' vlan id collected by DHCP snooping."
    ::= { dhcpSnoopBindingEntry 1 }

dhcpSnoopClientMacAddress         OBJECT-TYPE
    SYNTAX          MacAddress
    MAX-ACCESS      not-accessible
    STATUS          current
    DESCRIPTION        
        "DHCP clients' MAC addresses collected by DHCP snooping."
    ::= { dhcpSnoopBindingEntry 2 }
    
dhcpSnoopClientIpAddressType         OBJECT-TYPE
    SYNTAX          InetAddressType
    MAX-ACCESS      read-write
    STATUS          current
    DESCRIPTION        
        "DHCP clients' IP addresses type (IPv4 or IPv6). For DHCPv4 snooping, only support ipv4(1)."
        -- DEFVAL { ipv4 }
    ::= { dhcpSnoopBindingEntry 3 }

dhcpSnoopClientIpAddress         OBJECT-TYPE
    SYNTAX          InetAddress
    MAX-ACCESS      read-write
    STATUS          current
    DESCRIPTION        
        "DHCP clients' IP addresses collected by DHCP snooping."
    ::= { dhcpSnoopBindingEntry 4 }
        
dhcpSnoopClientIfindex         OBJECT-TYPE
    SYNTAX          Integer32
    MAX-ACCESS      read-write
    STATUS          current
    DESCRIPTION        
        "Interface collected by DHCP snooping."
    ::= { dhcpSnoopBindingEntry 5 }

dhcpSnoopClientExpiry         OBJECT-TYPE
    SYNTAX          Integer32
    MAX-ACCESS      read-write
    STATUS          current
    DESCRIPTION        
        "dhcp snooping Expiry"
    ::= { dhcpSnoopBindingEntry 6 }


dhcpSnoopClientRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { dhcpSnoopBindingEntry 7 }
        
--
--dhcpSnoopTrustTable
--
dhcpSnoopTrustTable         OBJECT-TYPE
    SYNTAX          SEQUENCE OF DhcpSnoopTrustEntry
    MAX-ACCESS      not-accessible
    STATUS          current
    DESCRIPTION        
        "A table is used to configure and monitor port trustedStatus ."
    ::= { dhcpSnoop 8 }

dhcpSnoopTrustEntry         OBJECT-TYPE
    SYNTAX          DhcpSnoopTrustEntry
    MAX-ACCESS      not-accessible
    STATUS          current
    DESCRIPTION        
        "An entry containing information about trustedStatus of ports."
    INDEX     { ifIndex }
    ::= { dhcpSnoopTrustTable 1 }

DhcpSnoopTrustEntry    ::=
    SEQUENCE 
    {
        dhcpSnoopTrustStatus INTEGER
    }

dhcpSnoopTrustStatus         OBJECT-TYPE
    SYNTAX          INTEGER
    {
        trusted(1),
        untrusted(2)
    }
    MAX-ACCESS      read-write
    STATUS          current
    DESCRIPTION        
        "TrustedStatus ofcurrent port which supports both get and
        set operation."
    DEFVAL   { untrusted }
    ::= { dhcpSnoopTrustEntry 1 }


--
--dhcpSnoopStatisticsGroup
--
dhcpSnoopStatisticsGroup     OBJECT IDENTIFIER    ::= { dhcpSnoop 9 }

dhcpSnoopDHCPPktNum         OBJECT-TYPE
    SYNTAX          Unsigned32
    MAX-ACCESS      read-only
    STATUS          current
    DESCRIPTION
        "The total number of DHCP packets received by DHCP Snooping."
    ::= { dhcpSnoopStatisticsGroup 1 }

dhcpSnoopBootpPktNum         OBJECT-TYPE
    SYNTAX          Unsigned32
    MAX-ACCESS      read-only
    STATUS          current
    DESCRIPTION
        "The total number of BOOTP packets received by DHCP Snooping."
    ::= { dhcpSnoopStatisticsGroup 2 }
        
dhcpSnoopFwdPktNum         OBJECT-TYPE
    SYNTAX          Unsigned32
    MAX-ACCESS      read-only
    STATUS          current
    DESCRIPTION
        "The total number of packets forwarded by DHCP Snooping."
    ::= { dhcpSnoopStatisticsGroup 3 }

dhcpSnoopInvalidPktNum         OBJECT-TYPE
    SYNTAX          Unsigned32
    MAX-ACCESS      read-only
    STATUS          current
    DESCRIPTION
        "The total number of invalid packets received by DHCP Snooping."
    ::= { dhcpSnoopStatisticsGroup 4 }

dhcpSnoopMacVerifyFailedPktNum         OBJECT-TYPE
    SYNTAX          Unsigned32
    MAX-ACCESS      read-only
    STATUS          current
    DESCRIPTION
        "The total number of MAC address verify failed packets received by DHCP Snooping."
    ::= { dhcpSnoopStatisticsGroup 5 }
                
dhcpSnoopDroppedPktNum         OBJECT-TYPE
    SYNTAX          Unsigned32
    MAX-ACCESS      read-only
    STATUS          current
    DESCRIPTION
        "The total number of dropped packets received by DHCP Snooping."
    ::= { dhcpSnoopStatisticsGroup 6 }
dhcpSnoopStatisticsReset             OBJECT-TYPE
    SYNTAX          TruthValue
    MAX-ACCESS      read-write
    STATUS          current
    DESCRIPTION
        "This node only supports set operation.
         If the value is true,it will clear all of the packet statistics."
    ::= { dhcpSnoopStatisticsGroup 7 }                

--
--dhcpSnoopClearAllBinding
--
dhcpSnoopClearAllBinding         OBJECT-TYPE
    SYNTAX          TruthValue
    MAX-ACCESS      read-write
    STATUS          current
    DESCRIPTION
        "This node only supports set operation.
        If the value is true,it will clear all of the dhcp snoop binding."
    ::= { dhcpSnoop 10 }                

dhcpSnoopRemoteIdFormatHostName         OBJECT-TYPE
    SYNTAX          TruthValue
    MAX-ACCESS      read-write
    STATUS          current
    DESCRIPTION        
        "The format type for the remote id ."
    ::= { dhcpSnoop 11 }    

dhcpSnoopRemoteIdFormatString         OBJECT-TYPE
    SYNTAX          OCTET STRING (SIZE(1..63))
    MAX-ACCESS      read-write
    STATUS          current
    DESCRIPTION
        "This node is used to format remote id of option 82 for dhcpsnooping."
    ::= { dhcpSnoop 12 }    

dhcpSnoopCircuitIdFormatTable         OBJECT-TYPE
    SYNTAX          SEQUENCE OF DhcpSnoopCircuitIdFormatEntry
    MAX-ACCESS      not-accessible
    STATUS          current
    DESCRIPTION        
        "A table is used to configure circuit id format on interface."
    ::= { dhcpSnoop 13 }

dhcpSnoopCircuitIdFormatEntry         OBJECT-TYPE
    SYNTAX          DhcpSnoopCircuitIdFormatEntry
    MAX-ACCESS      not-accessible
    STATUS          current
    DESCRIPTION        
        "An entry of circuit id format on interface."
    INDEX     { ifIndex, dhcpSnoopCircuitIdFormatVlan }
    ::= { dhcpSnoopCircuitIdFormatTable 1 }

DhcpSnoopCircuitIdFormatEntry    ::=
    SEQUENCE 
    {
        dhcpSnoopCircuitIdFormatVlan    
            Integer32,
        dhcpSnoopCircuitIdFormatString  
            OCTET STRING,
        dhcpSnoopCircuitIdFormatRowStatus 
            RowStatus 
    }

dhcpSnoopCircuitIdFormatVlan         OBJECT-TYPE
    SYNTAX          Integer32
    MAX-ACCESS      not-accessible
    STATUS          current
    DESCRIPTION        
        "The vlan id for the Circuit Id format entry."
    ::= { dhcpSnoopCircuitIdFormatEntry 1 }

dhcpSnoopCircuitIdFormatString OBJECT-TYPE
    SYNTAX  OCTET STRING (SIZE(1..63))
    MAX-ACCESS read-write
    STATUS current
    DESCRIPTION 
    	"This node to configure circuit id of option 82 for dhcpsnooping."
    ::= { dhcpSnoopCircuitIdFormatEntry 2 }

dhcpSnoopCircuitIdFormatRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { dhcpSnoopCircuitIdFormatEntry 3 }

-- 
--
-- =====================Dhcp relay definition begin======================
--
-- 
dhcpRelay      OBJECT IDENTIFIER    ::= { dhcp 3 }
       
--
-- dhcpRGlobal
--
       
dhcpRGlobal      OBJECT IDENTIFIER    ::= { dhcpRelay 1 }
       
--
--dhcpREnable
--
dhcpREnable         OBJECT-TYPE
    SYNTAX          INTEGER
    {
        enable(1),
        disable(2)
    }
    MAX-ACCESS      read-write
    STATUS          current
    DESCRIPTION        
        "DHCP relayStatus (enable or disable)."
    DEFVAL   { disable }
    ::= { dhcpRGlobal 1 }

dhcpROption82TrustAll         OBJECT-TYPE
    SYNTAX          TruthValue
    MAX-ACCESS      read-write
    STATUS          current
    DESCRIPTION        
        "Trust all interfaces for dhcp relay information."
    DEFVAL    { disable }
    ::= { dhcpRGlobal 2 }                                

--
--dhcpRIntf
--
dhcpRIntf      OBJECT IDENTIFIER    ::= { dhcpRelay 3 }

--
--dhcpRIfOption82TrustTable
--
dhcpRIfOption82TrustTable         OBJECT-TYPE
    SYNTAX          SEQUENCE OF DhcpRIfOption82TrustEntry
    MAX-ACCESS      not-accessible
    STATUS          current
    DESCRIPTION        
        "A table for configuring the interface that trust dhcp relay information."
    ::= { dhcpRIntf 1 }
        
dhcpRIfOption82TrustEntry         OBJECT-TYPE
    SYNTAX          DhcpRIfOption82TrustEntry
    MAX-ACCESS      not-accessible
    STATUS          current
    DESCRIPTION        
        "An entry for configuring the interface that trust dhcp relay information."
    INDEX     { ifIndex }
    ::= { dhcpRIfOption82TrustTable 1 }
        
DhcpRIfOption82TrustEntry    ::=
    SEQUENCE {
        dhcpRIfOption82Trust     
            TruthValue
    }
        
dhcpRIfOption82Trust         OBJECT-TYPE
    SYNTAX          TruthValue
    MAX-ACCESS      read-write
    STATUS          current
    DESCRIPTION        
        "Trust dhcp relay information."
    ::= { dhcpRIfOption82TrustEntry 1 }
        

--
--dhcpRIfSelectTable
--
dhcpRIfSelectTable         OBJECT-TYPE
    SYNTAX          SEQUENCE OF DhcpRIfSelectEntry
    MAX-ACCESS      not-accessible
    STATUS          current
    DESCRIPTION        
        "A table for configuring relay select server for interfaces."
    ::= { dhcpRIntf 2 }
        
dhcpRIfSelectEntry  OBJECT-TYPE
    SYNTAX          DhcpRIfSelectEntry
    MAX-ACCESS      not-accessible
    STATUS          current
    DESCRIPTION        
        "An entry for configuring relay select server for interfaces."
    INDEX     { ifIndex }
    ::= { dhcpRIfSelectTable 1 }
        
DhcpRIfSelectEntry    ::=
    SEQUENCE {
        dhcpRIfSelectserver     
            INTEGER
    }
        
dhcpRIfSelectserver         OBJECT-TYPE
    SYNTAX          INTEGER (0..16)
    MAX-ACCESS      read-write
    STATUS          current
    DESCRIPTION        
        "Specify DHCP server group number."
    ::= { dhcpRIfSelectEntry 1 }
                                
--
-- dhcpRServer
--
       
dhcpRServer      OBJECT IDENTIFIER    ::= { dhcpRelay 2 }

dhcpROption82Switch         OBJECT-TYPE
    SYNTAX          INTEGER
    {
        enable(1),
        disable(2)
    }
    MAX-ACCESS      read-write
    STATUS          current
    DESCRIPTION        
        "If the value is enabled, DHCP relay supporting option 82 function would
         be enabled."                        
    DEFVAL    { disable }
    ::= { dhcpRServer 1 }

dhcpROption82Check         OBJECT-TYPE
    SYNTAX          INTEGER
    {
        enable(1),
        disable(2)
    }
    MAX-ACCESS      read-write
    STATUS          current
    DESCRIPTION        
        "DHCP relay option-82 data check.If the value is enabled, 
        DHCP relay will validate relay information in BOOTREPLY."
    DEFVAL     { enable }
    ::= { dhcpRServer 2 }

dhcpROption82HandleStrategy         OBJECT-TYPE
    SYNTAX          INTEGER
    {
        replace(1),
        keep(2),
        drop(3)
    }
    MAX-ACCESS      read-write
    STATUS          current
    DESCRIPTION        
        "The strategies of DHCP relay handling option 82.
        'drop' indicates DHCP relay discarding the request
        packet including option 82.
        'keep' indicates DHCP relay accepting the request
        packet without any change of the option 82.
        'replace' indicates DHCP relay accepting the
        request packet on condition that it generates a new
        option 82 to replace the original one."
    DEFVAL     { keep }
    ::= { dhcpRServer 3 }


--
--dhcpRIpToGroupTable
--
dhcpRIpToGroupTable          OBJECT-TYPE
    SYNTAX          SEQUENCE OF DHCPRIpToGroupEntry
    MAX-ACCESS      not-accessible
    STATUS          current
    DESCRIPTION        
        "A table for configuring ip addresses for DHCP server groups."
    ::= { dhcpRServer 4 }

dhcpRIpToGroupEntry          OBJECT-TYPE
    SYNTAX          DHCPRIpToGroupEntry
    MAX-ACCESS      not-accessible
    STATUS          current
    DESCRIPTION
        "An entry for configuring ip addresses for a DHCP  server group. "
    INDEX                 
    {
        dhcpRIpToGroupGroupId
    }
    ::= { dhcpRIpToGroupTable 1 }

        DHCPRIpToGroupEntry    ::=
    SEQUENCE
    {
        dhcpRIpToGroupGroupId        
            Integer32,
        dhcpRIpToGroupServerIp      
            OCTET STRING,
        dhcpRIpToGroupRowStatus
            RowStatus 
    }
    
dhcpRIpToGroupGroupId            OBJECT-TYPE
    SYNTAX          Integer32 (1..16)
    MAX-ACCESS      not-accessible
    STATUS          current
    DESCRIPTION        "Group identifier of DHCP server group."
    ::= { dhcpRIpToGroupEntry 1 }

dhcpRIpToGroupServerIp           OBJECT-TYPE
    SYNTAX          OCTET STRING (SIZE(0..256))
    MAX-ACCESS      read-write
    STATUS          current
       DESCRIPTION        "Ip address of DHCP server.For example: 1.1.1.1,2.2.2.2        "
    ::= { dhcpRIpToGroupEntry 2 }

dhcpRIpToGroupRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { dhcpRIpToGroupEntry 3 }
        

--
--dhcpRStatisticsGroup
--
        dhcpRStatisticsGroup     OBJECT IDENTIFIER    ::= { dhcpRServer 5 }

dhcpRRxClientPktNum         OBJECT-TYPE
    SYNTAX          Unsigned32
    MAX-ACCESS      read-only
    STATUS          current
    DESCRIPTION
        "The total number of the packets received from DHCP
                        clients by DHCP relay.
        "
    ::= { dhcpRStatisticsGroup 1 }

dhcpRRxServerPktNum         OBJECT-TYPE
    SYNTAX          Unsigned32
    MAX-ACCESS      read-only
    STATUS          current
    DESCRIPTION
        "The total number of the packets received from
                        DHCP Servers by DHCP relay.
        "
    ::= { dhcpRStatisticsGroup 2 }

dhcpRRxClientErrPktNum         OBJECT-TYPE
    SYNTAX          Unsigned32
    MAX-ACCESS      read-only
    STATUS          current
    DESCRIPTION
        "The total number of the error packets received from
                        DHCP clients by DHCP relay.
        "
    ::= { dhcpRStatisticsGroup 3 }
                
dhcpRRxServerErrPktNum         OBJECT-TYPE
    SYNTAX          Unsigned32
    MAX-ACCESS      read-only
    STATUS          current
    DESCRIPTION
        "The total number of the error packets received from
                        DHCP Servers by DHCP relay.
        "
    ::= { dhcpRStatisticsGroup 4 }

dhcpRBogusAddrDropsPktNum         OBJECT-TYPE
    SYNTAX          Unsigned32
    MAX-ACCESS      read-only
    STATUS          current
       DESCRIPTION
        "The total number of the DHCP Bogus GIADDR drops packets handled
                        by DHCP relay.
        "
    ::= { dhcpRStatisticsGroup 5 }

dhcpRBadCircuitIDPktNum         OBJECT-TYPE
    SYNTAX          Unsigned32
    MAX-ACCESS      read-only
    STATUS          current
       DESCRIPTION
        "The total number of the DHCP Bad circuit ID packets handled
                        by DHCP relay.
        "
    ::= { dhcpRStatisticsGroup 6 }

dhcpRCorruptedAgentOpPktNum         OBJECT-TYPE
    SYNTAX          Unsigned32
    MAX-ACCESS      read-only
    STATUS          current
    DESCRIPTION
        "The total number of the DHCP corrupted agent options packets handled
                        by DHCP relay.
        "
    ::= { dhcpRStatisticsGroup 7 }

dhcpRMissAgentOpPktNum         OBJECT-TYPE
    SYNTAX          Unsigned32
    MAX-ACCESS      read-only
    STATUS          current
       DESCRIPTION
        "The total number of the DHCP Missing agent options packets handled
                        by DHCP relay.
        "
    ::= { dhcpRStatisticsGroup 8 }

dhcpRMissCircuitIDPktNum         OBJECT-TYPE
    SYNTAX          Unsigned32
    MAX-ACCESS      read-only
    STATUS          current
    DESCRIPTION
        "The total number of the DHCP Missing circuit IDs packets handled
                        by DHCP relay.
        "
    ::= { dhcpRStatisticsGroup 9 }

dhcpRStatisticsReset             OBJECT-TYPE
    SYNTAX          TruthValue
    MAX-ACCESS      read-write
    STATUS          current
       DESCRIPTION
        "This node only supports set operation.
                        If the value is true,it will clear all of the packet
                        statistics.
        "
    ::= { dhcpRStatisticsGroup 10 }

-- dhcpv6

dhcpv6Global OBJECT IDENTIFIER    ::= {  dhcp 6  }

dhcpv6Enable          OBJECT-TYPE
    SYNTAX          INTEGER
    {
        enable(1),
        disable(2)
    }
    MAX-ACCESS      read-write
    STATUS          current
    DESCRIPTION
        "DHCPv6 Status (enable or disable)."
    DEFVAL { disable }
    ::= { dhcpv6Global 1 }


dhcpv6Snoop OBJECT IDENTIFIER    ::= {  dhcp 7  }

dhcpv6SnoopGlobal      OBJECT IDENTIFIER    ::= { dhcpv6Snoop 1 }

dhcpv6SnoopEnable         OBJECT-TYPE
    SYNTAX          INTEGER
    {
        enable(1),
        disable(2)
    }
    MAX-ACCESS      read-write
    STATUS          current
    DESCRIPTION
        "DHCPv6 Snooping Status (enable or disable)."
    DEFVAL     { disable }
    ::= { dhcpv6SnoopGlobal 1 }

dhcpv6SnoopAutoSaveInterval         OBJECT-TYPE
    SYNTAX          INTEGER (15..1200)
    MAX-ACCESS      read-write
    STATUS          current
    DESCRIPTION        "Specify DHCPv6 snooping database auto save parameter."
    DEFVAL { 600 }
    ::= { dhcpv6SnoopGlobal 2 }
    
dhcpv6SnoopClearAllBinding         OBJECT-TYPE
    SYNTAX          TruthValue
    MAX-ACCESS      read-write
    STATUS          current
    DESCRIPTION
        "This node only supports set operation.
        If the value is true,it will clear all of the dhcpv6 snoop binding."
    DEFVAL { false }
    ::= { dhcpv6SnoopGlobal 3 }

dhcpv6SnoopVlanTable           OBJECT-TYPE
    SYNTAX          SEQUENCE OF Dhcpv6SnoopVlanEntry
    MAX-ACCESS      not-accessible
    STATUS          current
    DESCRIPTION     "A table is used to configure and monitor DHCPv6 Snooping 
                    status of VLANs."
    ::= { dhcpv6Snoop 2 }

dhcpv6SnoopVlanEntry          OBJECT-TYPE
    SYNTAX          Dhcpv6SnoopVlanEntry
    MAX-ACCESS      not-accessible
    STATUS          current
    DESCRIPTION
        "The entry information about dhcpv6SnoopVlanTable."
    INDEX
    {
        dhcpv6SnoopVlanIndex
    }
    ::= { dhcpv6SnoopVlanTable 1 }

    Dhcpv6SnoopVlanEntry    ::=
    SEQUENCE
    {
        dhcpv6SnoopVlanIndex
            Integer32,
        dhcpv6SnoopVlanEnable
            TruthValue
    }

dhcpv6SnoopVlanIndex                OBJECT-TYPE
    SYNTAX          Integer32(0..4096)
    MAX-ACCESS      not-accessible
    STATUS          current
    DESCRIPTION
        "current VLAN index."
    ::= { dhcpv6SnoopVlanEntry 1 }

dhcpv6SnoopVlanEnable                OBJECT-TYPE
    SYNTAX          TruthValue
    MAX-ACCESS      read-write
    STATUS          current
    DESCRIPTION
        "DHCPv6 Snooping Status of current VLAN."
    DEFVAL        { false }
    ::= { dhcpv6SnoopVlanEntry 2 }

dhcpv6SnoopBindingTable         OBJECT-TYPE
    SYNTAX          SEQUENCE OF Dhcpv6SnoopBindingEntry
    MAX-ACCESS      not-accessible
    STATUS          current
    DESCRIPTION
        "The table containing information of DHCPv6 clients listened by
        DHCPv6 snooping and it's enabled or disabled by setting
        dhcpv6SnoopEnable node."
    ::= { dhcpv6Snoop 3 }

dhcpv6SnoopBindingEntry         OBJECT-TYPE
    SYNTAX          Dhcpv6SnoopBindingEntry
    MAX-ACCESS      not-accessible
    STATUS          current
    DESCRIPTION
        "An entry containing information of DHCPv6 clients."
    INDEX          { dhcpv6SnoopClientVlan, dhcpv6SnoopClientMacAddress }
    ::= { dhcpv6SnoopBindingTable 1 }

Dhcpv6SnoopBindingEntry    ::=
    SEQUENCE
    {
        dhcpv6SnoopClientVlan
            Integer32,
        dhcpv6SnoopClientMacAddress
            MacAddress,
        dhcpv6SnoopClientIpAddressType
            InetAddressType,
        dhcpv6SnoopClientIpAddress
            InetAddress,
        dhcpv6SnoopClientIfindex
            Integer32,
        dhcpv6SnoopClientExpiry
            Integer32,
        dhcpv6SnoopClientRowStatus
            RowStatus
    }
   
dhcpv6SnoopClientVlan         OBJECT-TYPE
    SYNTAX          Integer32
    MAX-ACCESS      not-accessible
    STATUS          current
    DESCRIPTION
        "DHCPv6 clients' vlan id collected by DHCPv6 snooping."
    ::= { dhcpv6SnoopBindingEntry 1 }

dhcpv6SnoopClientMacAddress         OBJECT-TYPE
    SYNTAX          MacAddress
    MAX-ACCESS      not-accessible
    STATUS          current
    DESCRIPTION
        "DHCPv6 clients' MAC addresses collected by DHCPv6 snooping."
    ::= { dhcpv6SnoopBindingEntry 2 }
    
dhcpv6SnoopClientIpAddressType         OBJECT-TYPE
    SYNTAX          InetAddressType
    MAX-ACCESS      read-write
    STATUS          current
    DESCRIPTION
        "DHCPv6 clients' IP addresses type (IPv4 or IPv6). For DHCPv6 snooping, only support ipv6(2)."
        -- DEFVAL { ipv6 }
    ::= { dhcpv6SnoopBindingEntry 3 }
    
dhcpv6SnoopClientIpAddress         OBJECT-TYPE
    SYNTAX          InetAddress
    MAX-ACCESS      read-write
    STATUS          current
    DESCRIPTION
        "DHCPv6 clients' IP addresses collected by DHCPv6 snooping."
    ::= { dhcpv6SnoopBindingEntry 4 }

dhcpv6SnoopClientIfindex         OBJECT-TYPE
    SYNTAX          Integer32
    MAX-ACCESS      read-write
    STATUS          current
    DESCRIPTION
        "Interface collected by DHCPv6 snooping."
    ::= { dhcpv6SnoopBindingEntry 5 }

dhcpv6SnoopClientExpiry         OBJECT-TYPE
    SYNTAX          Integer32
    MAX-ACCESS      read-write
    STATUS          current
    DESCRIPTION
        "dhcpv6 snooping Expiry"
    ::= { dhcpv6SnoopBindingEntry 6 }

dhcpv6SnoopClientRowStatus         OBJECT-TYPE
    SYNTAX          RowStatus
    MAX-ACCESS      read-create
    STATUS          current
    DESCRIPTION
        "The status of this conceptual row. Now only realize CreateAndGo
        and Destroy and Active."
    ::= { dhcpv6SnoopBindingEntry 7 }

--
--dhcpv6SnoopTrustTable
--
dhcpv6SnoopTrustTable         OBJECT-TYPE
    SYNTAX          SEQUENCE OF Dhcpv6SnoopTrustEntry
    MAX-ACCESS      not-accessible
    STATUS          current
    DESCRIPTION
        "A table is used to configure and monitor port trustedStatus ."
    ::= { dhcpv6Snoop 4 }

dhcpv6SnoopTrustEntry         OBJECT-TYPE
    SYNTAX          Dhcpv6SnoopTrustEntry
    MAX-ACCESS      not-accessible
    STATUS          current
    DESCRIPTION
        "An entry containing information about trusted status of ports."
    INDEX     { ifIndex }
    ::= { dhcpv6SnoopTrustTable 1 }

Dhcpv6SnoopTrustEntry    ::=
    SEQUENCE
    {
        dhcpv6SnoopTrust INTEGER
    }

dhcpv6SnoopTrust         OBJECT-TYPE
    SYNTAX          INTEGER
    {
        trusted(1),
        untrusted(2)
    }
    MAX-ACCESS      read-write
    STATUS          current
    DESCRIPTION
        "Trusted status of current port which enable dhcpv6 snooping."
    DEFVAL   { untrusted }
    ::= { dhcpv6SnoopTrustEntry 1 }

--
--dhcpv6SnoopStatisticsGroup
--
dhcpv6SnoopStatisticsGroup     OBJECT IDENTIFIER    ::= { dhcpv6Snoop 5 }

dhcpv6SnoopDHCPv6PktNum         OBJECT-TYPE
    SYNTAX          Unsigned32
    MAX-ACCESS      read-only
    STATUS          current
    DESCRIPTION
        "The total number of DHCPv6 packets received by DHCPv6 Snooping."
    ::= { dhcpv6SnoopStatisticsGroup 1 }

dhcpv6SnoopFwdPktNum         OBJECT-TYPE
    SYNTAX          Unsigned32
    MAX-ACCESS      read-only
    STATUS          current
    DESCRIPTION
        "The total number of packets forwarded by DHCPv6 Snooping."
    ::= { dhcpv6SnoopStatisticsGroup 2 }

dhcpv6SnoopInvalidPktNum         OBJECT-TYPE
    SYNTAX          Unsigned32
    MAX-ACCESS      read-only
    STATUS          current
    DESCRIPTION
        "The total number of invalid packets received by DHCPv6 Snooping."
    ::= { dhcpv6SnoopStatisticsGroup 3 }

dhcpv6SnoopDroppedPktNum         OBJECT-TYPE
    SYNTAX          Unsigned32
    MAX-ACCESS      read-only
    STATUS          current
    DESCRIPTION
        "The total number of dropped packets received by DHCPv6 Snooping."
    ::= { dhcpv6SnoopStatisticsGroup 4 }
    
dhcpv6SnoopStatisticsReset             OBJECT-TYPE
    SYNTAX          TruthValue
    MAX-ACCESS      read-write
    STATUS          current
    DESCRIPTION
        "This node only supports set operation.
         If the value is true,it will clear all of the packet statistics."
    ::= { dhcpv6SnoopStatisticsGroup 64 }
    
--
-- =====================Dhcpv6 relay definition begin======================
--
dhcpv6Relay      OBJECT IDENTIFIER    ::= { dhcp 8 }

--
-- dhcpv6RGlobal
--

dhcpv6RGlobal      OBJECT IDENTIFIER    ::= { dhcpv6Relay 1 }

--
--dhcpv6REnable
--
dhcpv6REnable         OBJECT-TYPE
    SYNTAX          INTEGER
    {
        enable(1),
        disable(2)
    }
    MAX-ACCESS      read-write
    STATUS          current
    DESCRIPTION
        "DHCPv6 relay status (enable or disable)."
    DEFVAL   { disable }
    ::= { dhcpv6RGlobal 1 }
     
--
-- dhcpv6RServer
--

dhcpv6RServer      OBJECT IDENTIFIER    ::= { dhcpv6Relay 2 }

--
--dhcpv6RIpToGroupTable
--
dhcpv6RIpToGroupTable          OBJECT-TYPE
    SYNTAX          SEQUENCE OF DHCPv6RIpToGroupEntry
    MAX-ACCESS      not-accessible
    STATUS          current
    DESCRIPTION
        "A table for configuring ip addresses for DHCPv6 server groups."
    ::= { dhcpv6RServer 1 }

dhcpv6RIpToGroupEntry          OBJECT-TYPE
    SYNTAX          DHCPv6RIpToGroupEntry
    MAX-ACCESS      not-accessible
    STATUS          current
    DESCRIPTION
        "An entry for configuring ip addresses for a DHCPv6 server group. "
    INDEX
    {
        dhcpv6RIpToGroupGroupId
    }
    ::= { dhcpv6RIpToGroupTable 1 }

    DHCPv6RIpToGroupEntry    ::=
    SEQUENCE
    {
        dhcpv6RIpToGroupGroupId
            Integer32,
        dhcpv6RIpToGroupServerIpIf
            OCTET STRING,
        dhcpv6RIpToGroupRowStatus
            RowStatus
    }

dhcpv6RIpToGroupGroupId            OBJECT-TYPE
    SYNTAX          Integer32 (1..16)
    MAX-ACCESS      not-accessible
    STATUS          current
    DESCRIPTION        "Group identifier of DHCPv6 server group."
    ::= { dhcpv6RIpToGroupEntry 1 }

dhcpv6RIpToGroupServerIpIf           OBJECT-TYPE
    SYNTAX          OCTET STRING (SIZE(0..512))
    MAX-ACCESS      read-write
    STATUS          current
    DESCRIPTION        "Ipv6 address of DHCPv6 server.For example: 2001:1::1"
    ::= { dhcpv6RIpToGroupEntry 2 }
    
dhcpv6RIpToGroupRowStatus         OBJECT-TYPE
    SYNTAX          RowStatus
    MAX-ACCESS      read-create
    STATUS          current
    DESCRIPTION
        "The status of this conceptual row.Now only realize CreateAndGo and Destroy and Active."
    ::= { dhcpv6RIpToGroupEntry 3 }
        
--
--dhcpv6RIfSelectTable
--
dhcpv6RIfSelectTable         OBJECT-TYPE
    SYNTAX          SEQUENCE OF Dhcpv6RIfSelectEntry
    MAX-ACCESS      not-accessible
    STATUS          current
    DESCRIPTION
        "A table for configuring relay select server for interfaces."
    ::= { dhcpv6RServer 2 }

dhcpv6RIfSelectEntry  OBJECT-TYPE
    SYNTAX          Dhcpv6RIfSelectEntry
    MAX-ACCESS      not-accessible
    STATUS          current
    DESCRIPTION
        "An entry for configuring relay select server for interfaces."
    INDEX     { ifIndex }
    ::= { dhcpv6RIfSelectTable 1 }

Dhcpv6RIfSelectEntry    ::=
    SEQUENCE {
        dhcpv6RIfSelectserver
            INTEGER
    }

dhcpv6RIfSelectserver         OBJECT-TYPE
    SYNTAX          INTEGER (0..16)
    MAX-ACCESS      read-write
    STATUS          current
    DESCRIPTION
        "Specify DHCPv6 server group number."
    ::= { dhcpv6RIfSelectEntry 1 }

--
dhcpv6ROption      OBJECT IDENTIFIER    ::= { dhcpv6Relay 3 }
--

    
dhcpv6RRemoteid         OBJECT-TYPE
    SYNTAX          INTEGER
    {
        enable(1),
        disable(2)
    }
    MAX-ACCESS      read-write
    STATUS          current
    DESCRIPTION
        "DHCPv6 remote-id option."
    DEFVAL   { disable }
    ::= { dhcpv6ROption 1 }

dhcpv6RRemoteidFormatDuid         OBJECT-TYPE
    SYNTAX          TruthValue
    MAX-ACCESS      read-write
    STATUS          current
    DESCRIPTION
        "Use DUID in DHCPv6 remote-id format."
    DEFVAL   { true }
    ::= { dhcpv6ROption 2 }
        
dhcpv6RRemoteidFormatIfname         OBJECT-TYPE
    SYNTAX          TruthValue
    MAX-ACCESS      read-write
    STATUS          current
    DESCRIPTION
        "Use name of interface in DHCPv6 remote-id format."
    DEFVAL   { true }
    ::= { dhcpv6ROption 3 }
      
dhcpv6RRemoteidFormatVlan         OBJECT-TYPE
    SYNTAX          TruthValue
    MAX-ACCESS      read-write
    STATUS          current
    DESCRIPTION
        "Use vlan in DHCPv6 remote-id format."
    DEFVAL   { false }
    ::= { dhcpv6ROption 4 }

dhcpv6RPDrouteEnable         OBJECT-TYPE
    SYNTAX          INTEGER
    {
        enable(1),
        disable(2)
    }
    MAX-ACCESS      read-write
    STATUS          current
    DESCRIPTION
        "DHCPv6 prefix-delegation route learning (enable or disable)."
    DEFVAL   { disable }
    ::= { dhcpv6ROption 5 }
 
dhcpv6RPDrouteDistance         OBJECT-TYPE
    SYNTAX          INTEGER (1..255)
    MAX-ACCESS      read-write
    STATUS          current
    DESCRIPTION
        "Set the default distance for prefix-delegation route learned by DHCPv6 relay."
    DEFVAL   { 254 }
    ::= { dhcpv6ROption 6 }
       
dhcpv6RPDrouteAllClear         OBJECT-TYPE
    SYNTAX          TruthValue
    MAX-ACCESS      read-write
    STATUS          current
    DESCRIPTION
        "This node only supports set operation.
        If the value is true,it will clear all of the prefix-delegation route."
    ::= { dhcpv6ROption 7 }
    
dhcpv6RPDrouteTable         OBJECT-TYPE
    SYNTAX          SEQUENCE OF Dhcpv6RPDrouteEntry
    MAX-ACCESS      not-accessible
    STATUS          current
    DESCRIPTION
        "An table for prefix-delegation route."
    ::= { dhcpv6ROption 8 }
    
dhcpv6RPDrouteEntry  OBJECT-TYPE
    SYNTAX          Dhcpv6RPDrouteEntry
    MAX-ACCESS      not-accessible
    STATUS          current
    DESCRIPTION
        "An entry for prefix-delegation route."
    INDEX          { dhcpv6RPDrouteId }
    ::= { dhcpv6RPDrouteTable 1 }

Dhcpv6RPDrouteEntry    ::=
    SEQUENCE
    {
        dhcpv6RPDrouteId
            Unsigned32,
        dhcpv6RPDrouteIf
            Integer32,
        dhcpv6RPDrouteClientIp
            OCTET STRING,
        dhcpv6RPDroutePrefix
            OCTET STRING,
        dhcpv6RPDrouteExpiry
            Unsigned32,      
        dhcpv6RPDrouteRowStatus
            RowStatus
    }

dhcpv6RPDrouteId         OBJECT-TYPE
    SYNTAX          Unsigned32
    MAX-ACCESS      not-accessible
    STATUS          current
    DESCRIPTION
        "The ID of DHCPv6 prefix-delegation route item."
    ::= { dhcpv6RPDrouteEntry 1 }

dhcpv6RPDrouteIf         OBJECT-TYPE
    SYNTAX          Integer32
    MAX-ACCESS      read-only
    STATUS          current
    DESCRIPTION
        "The name of interface to DHCPv6 client."
    ::= { dhcpv6RPDrouteEntry 2 }

dhcpv6RPDrouteClientIp         OBJECT-TYPE
    SYNTAX          OCTET STRING (SIZE(0..40))
    MAX-ACCESS      read-only
    STATUS          current
    DESCRIPTION
        "DHCPv6 PD clients' Ipv6 address."
    ::= { dhcpv6RPDrouteEntry 3 }
    
dhcpv6RPDroutePrefix         OBJECT-TYPE
    SYNTAX          OCTET STRING (SIZE(0..42))
    MAX-ACCESS      read-only
    STATUS          current
    DESCRIPTION
        "DHCPv6 prefix-delegation prefix."
    ::= { dhcpv6RPDrouteEntry 4 }

dhcpv6RPDrouteExpiry         OBJECT-TYPE
    SYNTAX          Unsigned32
    MAX-ACCESS      read-only
    STATUS          current
    DESCRIPTION
        "Lease of DHCPv6 prefix-delegation prefix."
    ::= { dhcpv6RPDrouteEntry 5 }
    
dhcpv6RPDrouteRowStatus         OBJECT-TYPE
    SYNTAX          RowStatus
    MAX-ACCESS      read-write
    STATUS          current
    DESCRIPTION
        "The status of this conceptual row.Now only realize CreateAndGo and Destroy and Active."
    ::= { dhcpv6RPDrouteEntry 6 }
    
--
dhcpv6RStatisticsGroup     OBJECT IDENTIFIER    ::= { dhcpv6Relay 4 }
--

dhcpv6RRxClientPktNum         OBJECT-TYPE
    SYNTAX          Unsigned32
    MAX-ACCESS      read-only
    STATUS          current
    DESCRIPTION
        "The total number of the packets received from DHCPv6
                        clients by DHCPv6 relay.
        "
    ::= { dhcpv6RStatisticsGroup 1 }

dhcpv6RRxServerPktNum         OBJECT-TYPE
    SYNTAX          Unsigned32
    MAX-ACCESS      read-only
    STATUS          current
    DESCRIPTION
        "The total number of the packets received from
                        DHCPv6 Servers by DHCPv6 relay.
        "
    ::= { dhcpv6RStatisticsGroup 2 }

dhcpv6RRxClientErrPktNum         OBJECT-TYPE
    SYNTAX          Unsigned32
    MAX-ACCESS      read-only
    STATUS          current
    DESCRIPTION
        "The total number of the error packets received from
                        DHCPv6 clients by DHCPv6 relay.
        "
    ::= { dhcpv6RStatisticsGroup 3 }

dhcpv6RRxServerErrPktNum         OBJECT-TYPE
    SYNTAX          Unsigned32
    MAX-ACCESS      read-only
    STATUS          current
    DESCRIPTION
        "The total number of the error packets received from
                        DHCPv6 Servers by DHCPv6 relay.
        "
    ::= { dhcpv6RStatisticsGroup 4 }
    
dhcpv6RStatisticsReset             OBJECT-TYPE
    SYNTAX          TruthValue
    MAX-ACCESS      read-write
    STATUS          current
    DESCRIPTION
        "This node only supports set operation.
                        If the value is true,it will clear all of the packet
                        statistics.
        "
    ::= { dhcpv6RStatisticsGroup 64 }
    
-- Sub Module: LSWDEVMMIB

-- ==================================================================

lswdevMMibObject OBJECT-IDENTITY
        STATUS current
        DESCRIPTION
            "Description."
        ::= { lswdevMMib 1 }


devMFanMibObject OBJECT IDENTIFIER    ::= {  lswdevMMibObject 1  }

devMFanStatusTable         OBJECT-TYPE
    SYNTAX          SEQUENCE OF DevMFanStatusEntry
    MAX-ACCESS      not-accessible
    STATUS          current
    DESCRIPTION "Fan status description table"
    ::= { devMFanMibObject  1 }
    
    
devMFanStatusEntry         OBJECT-TYPE
    SYNTAX          DevMFanStatusEntry
    MAX-ACCESS      not-accessible
    STATUS          current
    DESCRIPTION        
        "Fan status description table entry"
    INDEX     {devMFanPosition, devMFanModuleId, devMFanIndex }
    ::= { devMFanStatusTable 1 }
    
    
DevMFanStatusEntry    ::=
    SEQUENCE 
    {
    devMFanPosition
        INTEGER,
    devMFanModuleId
        INTEGER,
    devMFanIndex
        INTEGER,
    devMFanStatus 
        INTEGER,
    devMFanSpeed
        OCTET STRING,
    devMFanLowSpeed
        INTEGER,
    devMFanHighSpeed
        INTEGER,
    devMFanSpeedAdjust 
        INTEGER,
    devMFanSetSpeed
        INTEGER
    }
    
devMFanPosition  OBJECT-TYPE
    SYNTAX          INTEGER
    {
        default (1),
        left    (2),
        right   (3)
    }
    MAX-ACCESS      read-only
    STATUS          current
    DESCRIPTION 
        "Fan position type: 1-default, 2-left, 3-right. "
    ::= { devMFanStatusEntry 1 }

devMFanModuleId  OBJECT-TYPE
    SYNTAX          INTEGER
    MAX-ACCESS      read-only
    STATUS          current
    DESCRIPTION 
        "Fan Module id."
    ::= { devMFanStatusEntry 2 }    
        
devMFanIndex  OBJECT-TYPE
    SYNTAX          INTEGER (1..18)
    MAX-ACCESS      read-only
    STATUS          current
    DESCRIPTION 
        "Fan number"
    ::= { devMFanStatusEntry 3 }
    
devMFanStatus       OBJECT-TYPE
    SYNTAX          INTEGER
    {
        active     (1),
        deactive   (2),
        notInstall  (3),
        unsupport    (4)
    }
    MAX-ACCESS      read-only
    STATUS          current
    DESCRIPTION        
        "FanStatus : active (1), deactive (2) not installed (3) and unsupported (4)."
    ::= { devMFanStatusEntry 4 }
    
devMFanSpeed  OBJECT-TYPE
    SYNTAX          OCTET STRING
    MAX-ACCESS      read-only
    STATUS          current
    DESCRIPTION 
        "Fan speed(RPM)"
    ::= { devMFanStatusEntry 5 }
    
devMFanLowSpeed  OBJECT-TYPE
    SYNTAX          INTEGER (0..65535)
    MAX-ACCESS      read-only
    STATUS          obsolete
    DESCRIPTION 
        "Fan speed low threshold(RPM)."
    ::= { devMFanStatusEntry 6 }
    
devMFanHighSpeed  OBJECT-TYPE
    SYNTAX          INTEGER (0..65535)
    MAX-ACCESS      read-only
    STATUS          obsolete
    DESCRIPTION 
        "Fan speed high threshold(RPM)."
    ::= { devMFanStatusEntry 7 }

devMFanSpeedAdjust  OBJECT-TYPE
    SYNTAX          INTEGER
    {
        unsupport (0),
        support   (1)
    }
    MAX-ACCESS      read-only
    STATUS          current
    DESCRIPTION 
        "Whether fan support speed adjust, 0 mean unsupport, 1 mean support."
    ::= { devMFanStatusEntry 8 } 
    
devMFanSetSpeed  OBJECT-TYPE
    SYNTAX          INTEGER
    MAX-ACCESS      read-only
    STATUS          current
    DESCRIPTION 
        "Config speed value."
    ::= { devMFanStatusEntry 9 }      
    
--devMFanTemperatureTable         OBJECT-TYPE
--    SYNTAX          SEQUENCE OF DevMFanTemperatureEntry
--    MAX-ACCESS      not-accessible
--    STATUS          current
--            DESCRIPTION "Fan temperature description table"
--    ::= { devMFanMibObject  2 }
--    
--    
--devMFanTemperatureEntry         OBJECT-TYPE
--    SYNTAX          DevMFanTemperatureEntry
--    MAX-ACCESS      not-accessible
--    STATUS          current
--    DESCRIPTION        "Fan temperature description entry"
--    INDEX     { devMFanTemperatureLocation,  devMFanTemperatureIndex}
--    ::= { devMFanTemperatureTable 1 }
--    
--    
--DevMFanTemperatureEntry    ::=
--    SEQUENCE 
--    {
--        devMFanTemperatureLocation           INTEGER,
--        devMFanTemperatureIndex              Integer32,
--        devMFanTemperatureValue              Integer32,
--        devMFanTemperatureLow                Integer32,
--        devMFanTemperatureHigh               INTEGER
--    }
--    
--    
--devMFanTemperatureLocation          OBJECT-TYPE
--    SYNTAX          INTEGER
--    {
--        default(1),
--        left(2),
--        right(3)
--    }
--    MAX-ACCESS      not-accessible
--    STATUS          current
--    DESCRIPTION        
--        "Fan sensor position type: 1-default, 2-left, 3-right"
--    ::= { devMFanTemperatureEntry 1 }
--    
--devMFanTemperatureIndex         OBJECT-TYPE
--    SYNTAX          Integer32   (1..16)
--    MAX-ACCESS      read-only
--    STATUS          current
--    DESCRIPTION        "Fan sensor number"
--    ::= { devMFanTemperatureEntry 2 }
--    
--devMFanTemperatureValue         OBJECT-TYPE
--    SYNTAX          Integer32
--    MAX-ACCESS      read-only
--    STATUS          current
--    DESCRIPTION        "Fan sensor temperature"
--    ::= { devMFanTemperatureEntry 3 }
--    
--devMFanTemperatureLow         OBJECT-TYPE
--    SYNTAX          Integer32
--    MAX-ACCESS      read-only
--    STATUS          current
--    DESCRIPTION        "Fan sensor temperature low"
--    ::= { devMFanTemperatureEntry 4 }
--    
--devMFanTemperatureHigh          OBJECT-TYPE
--    SYNTAX          INTEGER (50..90)
--    MAX-ACCESS      read-only
--    STATUS          current
--    DESCRIPTION        "Fan sensor temperature high"
--    ::= { devMFanTemperatureEntry 5 }
            

devMPowerStatusTable         OBJECT-TYPE
    SYNTAX          SEQUENCE OF DevMPowerStatusEntry
    MAX-ACCESS      not-accessible
    STATUS          current
    DESCRIPTION 
        "Power status description table."
    ::= { lswdevMMibObject  2 }
    
    
devMPowerStatusEntry OBJECT-TYPE
    SYNTAX          DevMPowerStatusEntry
    MAX-ACCESS      not-accessible
    STATUS          current
    DESCRIPTION 
        "Power status description table entry."
    INDEX   { devMPowerIndex }
    ::= { devMPowerStatusTable 1 }
    
DevMPowerStatusEntry    ::=
    SEQUENCE 
    {
        devMPowerIndex          
           INTEGER,
        devMPowerStatus
           INTEGER,
        devMPowerWorkStatus
           INTEGER,
        devMPowerType
           INTEGER,
        devMPowerFanStatus
           INTEGER,
        devMPowerControlStatus
           INTEGER
    }
    
    
devMPowerIndex          OBJECT-TYPE
    SYNTAX          INTEGER (0..65535)
    MAX-ACCESS        not-accessible
    STATUS          current
    DESCRIPTION        
        "Power number."
    ::= { devMPowerStatusEntry 1 }
  
  devMPowerStatus    OBJECT-TYPE
    SYNTAX          INTEGER
    {
        present      (1),
        absent       (2),
        unsupport    (3)
        
    }
    MAX-ACCESS      read-only
    STATUS          current
    DESCRIPTION " Power whole device status: present (1), absent (2), unsupport (3)."
    ::= { devMPowerStatusEntry 2 }
    
  devMPowerWorkStatus   OBJECT-TYPE
      SYNTAX          INTEGER
    {
        active     (1),
        deactive   (2),
        notInstall (3),
        unsupport    (4)
        
    }
    MAX-ACCESS      read-only
    STATUS          current
    DESCRIPTION "Power status: active (1), deactive (2) not installed (3) and unsupported (4). "
    ::= { devMPowerStatusEntry 3 }
   
   devMPowerType     OBJECT-TYPE
    SYNTAX          INTEGER
    {
        ac (1),
        dc (2),
        unknow       (3),
        notInstall   (4),
        unsupport    (5) 
    }
    MAX-ACCESS      read-only
    STATUS          current
    DESCRIPTION " Power status: AC (1), DC (2), UNKNOW (3), notInstall (4) and unsupported (5)."
    ::= { devMPowerStatusEntry 4 }
    
   devMPowerFanStatus  OBJECT-TYPE
   SYNTAX          INTEGER
    {
        active     (1),
        deactive   (2),
        notInstall (3),
        unsupport    (4)
        
    }
    MAX-ACCESS      read-only
    STATUS          current
    DESCRIPTION " Power status: work (1), failed (2) not installed (3) and unsupported (4). "
    ::= { devMPowerStatusEntry 5 }
   
   devMPowerControlStatus OBJECT-TYPE
   SYNTAX          INTEGER
    {
        on           (1),
        down         (2),
        uninstall    (3),	
        unsupported    (4) 
    }
    MAX-ACCESS      read-only
    STATUS          current
    DESCRIPTION " Power status: on (1), down (2), uninstall(3), unsupported(4)."
    ::= { devMPowerStatusEntry 6 }
    
    
devMSlotEnvironmentTable         OBJECT-TYPE
    SYNTAX          SEQUENCE OF DevMSlotEnvironmentEntry
    MAX-ACCESS      not-accessible
    STATUS          current
            DESCRIPTION " Environment description table  "
    ::= { lswdevMMibObject  3 }
    
    
devMSlotEnvironmentEntry         OBJECT-TYPE
    SYNTAX          DevMSlotEnvironmentEntry
    MAX-ACCESS      not-accessible
    STATUS          current
    DESCRIPTION        " Environment DESCRIPTION table entry."
    INDEX     { devMSlotEnvironmentType, devMSlotEnvironmentSlot, devMSlotEnvironmentIndex}
    ::= { devMSlotEnvironmentTable 1 }
    
    
    DevMSlotEnvironmentEntry    ::=
    SEQUENCE 
    {
        devMSlotEnvironmentType               INTEGER,
        devMSlotEnvironmentSlot             Integer32,
        devMSlotEnvironmentIndex              Integer32,
        devMSlotEnvironmentValue              Integer32,
        devMSlotEnvironmentCriticalLimit      INTEGER,
        devMSlotEnvironmentUpperLimit         INTEGER,
        devMSlotEnvironmentLowerLimit         INTEGER
    }
    
    
devMSlotEnvironmentType          OBJECT-TYPE
    SYNTAX          INTEGER
    {
        temperature(1),
        humidity(2),
        fog(3)
    }
    MAX-ACCESS      not-accessible
    STATUS          current
    DESCRIPTION        
        "Environment type. 1-temperature, 2-humidity, 3-fog.
        only support temperature(1) now, Not support humidity(2) and flog(3)."
    ::= { devMSlotEnvironmentEntry 1 }
    
devMSlotEnvironmentSlot         OBJECT-TYPE
    SYNTAX          Integer32
    MAX-ACCESS      not-accessible
    STATUS          current
    DESCRIPTION        "Environment slot number."
    ::= { devMSlotEnvironmentEntry 2 }
    
devMSlotEnvironmentIndex         OBJECT-TYPE
    SYNTAX          Integer32
    MAX-ACCESS      not-accessible
    STATUS          current
    DESCRIPTION        "Environment index. 
    For temperature,max temperature sensor num is 6."
    ::= { devMSlotEnvironmentEntry 3 }
    
devMSlotEnvironmentValue         OBJECT-TYPE
    SYNTAX          Integer32
    MAX-ACCESS      read-only
    STATUS          current
    DESCRIPTION        " Environment value."
    ::= { devMSlotEnvironmentEntry 4 }
    
devMSlotEnvironmentCriticalLimit          OBJECT-TYPE
    SYNTAX          INTEGER (55..90)
    MAX-ACCESS      read-write
    STATUS          current
    DESCRIPTION        "Environment critical temperature threshold, unit is Celsius."
    ::= { devMSlotEnvironmentEntry 5 }
            
devMSlotEnvironmentUpperLimit          OBJECT-TYPE
    SYNTAX          INTEGER (50..85)
    MAX-ACCESS      read-write
    STATUS          current
    DESCRIPTION        "Environment high temperature threshold, unit is Celsius."
    ::= { devMSlotEnvironmentEntry 6 }
    
    
devMSlotEnvironmentLowerLimit         OBJECT-TYPE
    SYNTAX          INTEGER (-15..50)
    MAX-ACCESS      read-write
    STATUS          current
    DESCRIPTION        " Environment Low temperature threshold, unit is Celsius."
    ::= { devMSlotEnvironmentEntry 7 }


--linkUpDownTrapEnable          OBJECT-TYPE
--    SYNTAX          INTEGER
--        {
--        enableBoth(1) ,
--        disableBoth(2) ,
--        enableLinkUpTrapOnly(3) ,
--        enableLinkDownTrapOnly(4)
--        }
--    MAX-ACCESS      read-write
--    STATUS          current
--    DESCRIPTION
--        "Enable/Disable linkUp/linkDown traps of the device, determining whether
--         to enable linkUp/linkDown traps with that of the interface.
--         When the value is enableBoth(1), the linkUp/linkDown traps are both
--         enabled.
--         When the value is disableBoth(2), the linkUp/linkDown traps are both
--         disabled.
--         When the value is enableLinkUpTrapOnly(3), the linkUp traps is enabled
--         and the linkDown traps is disabled.
--         When the value is enableLinkDownTrapOnly(4), the linkUp traps is
--         disabled and the linkDown traps is enabled."
--    ::= { lswdevMMibObject  9 }
--
--dot1qTpFdbLearnStatus         OBJECT-TYPE
--    SYNTAX          INTEGER
--        {
--                enabled(1),
--                disabled(2)
--        }
--    MAX-ACCESS      read-write
--    STATUS          current
--    DESCRIPTION        " Enable/Disable the address learning."
--    ::= { lswdevMMibObject  10 }
--
--
--
--cfmWriteFlash         OBJECT-TYPE
--    SYNTAX          INTEGER
--        {
--                write(1)
--        }
--    MAX-ACCESS      read-write
--    STATUS          current
--    DESCRIPTION        " Write thecurrent effective configuration into the Flash memory.
--                      This object does not support read operation."
--    ::= { lswdevMMibObject  11 }
--
--
--cfmEraseFlash         OBJECT-TYPE
--    SYNTAX          INTEGER
--        {
--                erase(1)
--        }
--    MAX-ACCESS      read-write
--    STATUS          current
--    DESCRIPTION        " Delete the configuration from the Flash memory.
--                      This object does not support read operation."
--    ::= { lswdevMMibObject  12 }
--
--




-- ==================================================================
--
-- Frame information table
--
-- ==================================================================
--lswFrameTable            OBJECT-TYPE
--    SYNTAX          SEQUENCE OF LswFrameEntry
--    MAX-ACCESS      not-accessible
--    STATUS          current
--    DESCRIPTION
--        "Frame information table."
--    ::= {lswdevMMibObject 4}
--
--lswFrameEntry            OBJECT-TYPE
--    SYNTAX          LswFrameEntry
--    MAX-ACCESS      not-accessible
--    STATUS          current
--    DESCRIPTION
--        "Frame description table entry."
--    INDEX     { lswFrameIndex }
--    ::= {lswFrameTable 1}
--
--LswFrameEntry    ::=    
--    SEQUENCE
--    {
--        lswFrameIndex        Integer32,
--        lswFrameType         Integer32,
--        lswFrameDesc         OCTET STRING ,
--        lswSlotNumber        Integer32,
--        lswFrameAdminStatus INTEGER,
--        lswFrameOperStatus INTEGER
--    }
--
--lswFrameIndex            OBJECT-TYPE
--    SYNTAX          Integer32 (0..65535)
--    MAX-ACCESS      not-accessible
--    STATUS          current
--    DESCRIPTION
--        "The unique index of frame."
--    ::= {lswFrameEntry 1}
--
--lswFrameType            OBJECT-TYPE
--    SYNTAX          Integer32 (0..65535)
--    MAX-ACCESS      read-only
--    STATUS          current
--    DESCRIPTION
--        "Frame type."
--    ::= {lswFrameEntry 2}
--
--lswFrameDesc            OBJECT-TYPE
--    SYNTAX          OCTET STRING (SIZE(0..64))
--    MAX-ACCESS      read-write
--    STATUS          current
--    DESCRIPTION
--        "Frame description."
--    ::= {lswFrameEntry 3}
--
--lswSlotNumber            OBJECT-TYPE
--    SYNTAX          Integer32
--    MAX-ACCESS      read-only
--    STATUS          current
--    DESCRIPTION
--        "Number of slots of thecurrent frame."
--    ::= {lswFrameEntry 4}
--
--lswFrameAdminStatus         OBJECT-TYPE
--    SYNTAX          INTEGER
--    {
--      normal (1),
--      fault  (2),
--      other  (3)
--    }
--    MAX-ACCESS      read-only
--    STATUS          current
--    DESCRIPTION
--        "The status of frame."
--    ::= {lswFrameEntry 5}
--
--lswFrameOperStatus         OBJECT-TYPE
--    SYNTAX          INTEGER
--    {
--          disable    (1),
--          enable     (2),
--          haReload   (3),
--          haSwitchover   (4),
--          syncStartupConfig   (5)
--    }
--    MAX-ACCESS      read-write
--    STATUS          current
--    DESCRIPTION
--        "The operationStatus of frame."
--    ::= {lswFrameEntry 6}
-- ==================================================================
--
-- slot information table
--
-- ==================================================================

lswSlotTable            OBJECT-TYPE
    SYNTAX          SEQUENCE OF LswSlotEntry
    MAX-ACCESS      not-accessible
    STATUS          current
    DESCRIPTION
        "Slot description table."
    ::= {lswdevMMibObject 5}

lswSlotEntry            OBJECT-TYPE
    SYNTAX          LswSlotEntry
    MAX-ACCESS      not-accessible
    STATUS          current
    DESCRIPTION
        "Slot description table entry."
    INDEX        { lswSlotFrameIndex, lswSlotIndex }
    ::= {lswSlotTable 1}

LswSlotEntry    ::=    
    SEQUENCE
    {
        lswSlotFrameIndex           Integer32,
        lswSlotIndex                Integer32,
        lswSlotConfigType           OCTET STRING,
        lswSlotCurrentType          OCTET STRING,
        lswSlotStatus               OCTET STRING,
        lswSlotSupStatus            OCTET STRING,
        lswSlotPortNumber           Integer32,
        lswSlotHwVer                OCTET STRING,
        lswSlotRom                  OCTET STRING,
        lswSlotSerialNo             OCTET STRING
   }

lswSlotFrameIndex            OBJECT-TYPE
    SYNTAX          Integer32 (1..16)
    MAX-ACCESS      read-only
    STATUS          current
    DESCRIPTION
        "Frame index. Now we only support 1."
    ::= {lswSlotEntry 1}
        
lswSlotIndex            OBJECT-TYPE
    SYNTAX          Integer32 (1..128)
    MAX-ACCESS      read-only
    STATUS          current
    DESCRIPTION
        "Slot index."
    ::= {lswSlotEntry 2}

lswSlotConfigType            OBJECT-TYPE
    SYNTAX          OCTET STRING  (SIZE(0..64))
    MAX-ACCESS      read-only
    STATUS          current
    DESCRIPTION
        "The configed Slot type. Include SUP-1, LC-24S, LC-24T, LC-2X8S, LC-2X8ST."
    ::= {lswSlotEntry 3}

lswSlotCurrentType            OBJECT-TYPE
    SYNTAX          OCTET STRING  (SIZE(0..64))
    MAX-ACCESS      read-only
    STATUS          current
    DESCRIPTION
        "The current Slot type. Include SUP-1, LC-24S, LC-24T, LC-2X8S, LC-2X8ST."
    ::= {lswSlotEntry 4}

lswSlotStatus         OBJECT-TYPE
    SYNTAX          OCTET STRING  (SIZE(0..64))
    MAX-ACCESS      read-only
    STATUS          current
    DESCRIPTION
        "The Slot status. Include absent, creating, initing, syncing, fail, ready, uninit, conflict."
    ::= {lswSlotEntry 5}

lswSlotSupStatus         OBJECT-TYPE
    SYNTAX          OCTET STRING  (SIZE(0..64))
    MAX-ACCESS      read-only
    STATUS          current
    DESCRIPTION
        "The supervisor card status. This node is just for supervisor card. Include Active and Standby."
    ::= {lswSlotEntry 6}

lswSlotPortNumber            OBJECT-TYPE
    SYNTAX          Integer32
    MAX-ACCESS      read-only
    STATUS          current
    DESCRIPTION
        "Number of the ports on the card in this slot. On supervisor the number is 0."
    ::= {lswSlotEntry 7}
    
lswSlotHwVer            OBJECT-TYPE
    SYNTAX          OCTET STRING  (SIZE(0..64))
    MAX-ACCESS      read-only
    STATUS          current
    DESCRIPTION
        "The hardware version of the card in this slot. If the line card is absent, none info will be printed."
    ::= {lswSlotEntry 8}
    
lswSlotRom            OBJECT-TYPE
    SYNTAX          OCTET STRING  (SIZE(0..16))
    MAX-ACCESS      read-only
    STATUS          current
    DESCRIPTION
        "The bootrom version of the card in this slot. If the line card is absent, none info will be printed."
    ::= {lswSlotEntry 9}
    
lswSlotSerialNo            OBJECT-TYPE
    SYNTAX          OCTET STRING  (SIZE(0..64))
    MAX-ACCESS      read-only
    STATUS          current
    DESCRIPTION
        "The serial number of the card in this Slot. If the line card is absent, none info will be printed."
    ::= {lswSlotEntry 10}
    
-- ==================================================================
--
-- sub slot information table
--
-- ==================================================================

--lswSubslotTable        OBJECT-TYPE
--    SYNTAX          SEQUENCE OF LswSubslotEntry
--    MAX-ACCESS      not-accessible
--    STATUS          current
--    DESCRIPTION
--        "Subslot    DESCRIPTION table."
--    ::= {lswdevMMibObject 6}
--
--lswSubslotEntry            OBJECT-TYPE
--    SYNTAX          LswSubslotEntry
--    MAX-ACCESS      not-accessible
--    STATUS          current
--    DESCRIPTION
--        "Subslot    DESCRIPTION table entry."
--    INDEX          
--    {
--        lswFrameIndex,
--        lswSlotIndex,
--        lswSubslotIndex
--    }
--    ::= {lswSubslotTable 1}
--
--LswSubslotEntry    ::=    
--    SEQUENCE
--    {
--        lswSubslotFrameIndex         
--            Integer32,
--        lswSubslotSlotIndex          
--            Integer32,
--        lswSubslotIndex       
--            Integer32,
--        lswSubslotType        
--            INTEGER,
--        lswSubslotPortNum     
--            Integer32,
--        lswSubslotAdminStatus 
--            INTEGER,
--        lswSubslotOperStatus 
--            INTEGER
--   }
--lswSubslotFrameIndex              OBJECT-TYPE
--    SYNTAX          Integer32
--    MAX-ACCESS      read-only
--    STATUS          current
--    DESCRIPTION
--        "Fram index."
--    ::= {lswSubslotEntry 1}
--        
--lswSubslotSlotIndex              OBJECT-TYPE
--    SYNTAX          Integer32
--    MAX-ACCESS      read-only
--    STATUS          current
--    DESCRIPTION
--        "slot index."
--    ::= {lswSubslotEntry 2}
--
--lswSubslotIndex              OBJECT-TYPE
--    SYNTAX          Integer32 (0..65535)
--    MAX-ACCESS      read-only
--    STATUS          current
--    DESCRIPTION
--        "Subslot index."
--    ::= {lswSubslotEntry 3}
--
-- value list of lswSubslotType are identical with the value list of lswSlotType.
--lswSubslotType              OBJECT-TYPE
--    SYNTAX          INTEGER
--    {
--        subcard4GE(1),
--        subcard1XG(2)
--    }
--    MAX-ACCESS      read-only
--    STATUS          current
--    DESCRIPTION
--        "Type of the pinch board in the subslot."
--    ::= {lswSubslotEntry 4}
--
--lswSubslotPortNum           OBJECT-TYPE
--    SYNTAX          Integer32
--    MAX-ACCESS      read-only
--    STATUS          current
--    DESCRIPTION
--        "Number of physical ports in the pinch board."
--    ::= {lswSubslotEntry 5}
--
--
--lswSubslotAdminStatus         OBJECT-TYPE
--    SYNTAX          INTEGER
--    {
--        normal      (1),
--        fault       (2),
--        forbidden   (3)
--    }
--    MAX-ACCESS      read-only
--    STATUS          current
--    DESCRIPTION
--        "Status of the pinch board in the subslot."
--    ::= {lswSubslotEntry 6}
--        
--lswSubslotOperStatus         OBJECT-TYPE
--    SYNTAX          INTEGER
--        {
--            firstattach(0),
--            present(1),
--        absent(2),
--            available(3),
--        unavailable(4),
--            clearConfig (5)
--        }
--    MAX-ACCESS      read-write
--    STATUS          current
--    DESCRIPTION
--        "Slot operationStatus ."
--    ::= {lswSubslotEntry 7}
        
lswDiagnosticBootupLevel         OBJECT-TYPE
    SYNTAX          INTEGER
    {
      noDiagnostic (1),
      minimal    (2),
      complete   (3)
    }
    MAX-ACCESS      read-write
    STATUS          current
    DESCRIPTION
        "Diagnostic Bootup Level.
         noDiagnostic (1),
         minimal    (2),
         complete   (3).
         
         The configured value will be valid after next reload.
         The return value is the current bootup diag level."
    ::= { lswdevMMibObject 7 } 
          
--transceiverSfpMonitorResult         OBJECT-TYPE
--    SYNTAX          OCTET STRING (SIZE (0..255))
--    MAX-ACCESS      read-only
--    STATUS          current
--    DESCRIPTION
--        "This string only for transceiver Sfp Monitor warning and alarm message traps
--         can not read and write."
--    ::= { lswdevMMibObject 9 }    
    
transinformation OBJECT-IDENTITY
    STATUS current
    DESCRIPTION
        "Transceiver information description."
    ::= { lswdevMMibObject 10 }
    
transbasicinformationTable    OBJECT-TYPE
    SYNTAX     SEQUENCE OF TransbasicinformationEntry
    MAX-ACCESS     not-accessible
    STATUS     current
    DESCRIPTION
        "Show the basic information for transceiver."
    ::= {transinformation 1}

transbasicinformationEntry    OBJECT-TYPE
    SYNTAX         TransbasicinformationEntry
    MAX-ACCESS     not-accessible
    STATUS         current
    DESCRIPTION
        "Show the basic information for transceiver."
    INDEX {ifIndex}
    ::= {transbasicinformationTable 1}

TransbasicinformationEntry ::= 
   SEQUENCE{
        transceiveType                 
            OCTET STRING,
        transceiveVender               
            OCTET STRING,
        transceivePartNumber           
            OCTET STRING,
        transceiveSerialNumber         
            OCTET STRING,
        transceiveWaveLength           
            Integer32,
        link9SinglemodeLengthKm        
            Integer32,
        link9SinglemodeLengthM         
            Integer32,
        link50MultimodeLength          
            Integer32,
        link62MultimodeLength          
            Integer32,
        linkCopperLength               
            Integer32,
        transceiveStatus               
            OCTET STRING,
        transceiveMointorStatus               
            OCTET STRING
   }
transceiveType      OBJECT-TYPE
    SYNTAX         OCTET STRING (SIZE(0..256))
    MAX-ACCESS     read-only
    STATUS         current
    DESCRIPTION
        "Transceiver type. For example: 1000BASE-LX, 1000BASE-SX, 10GBASE-SR and so on."
    ::= {transbasicinformationEntry 1}

transceiveVender      OBJECT-TYPE
    SYNTAX         OCTET STRING (SIZE(0..256))
    MAX-ACCESS     read-only
    STATUS         current
    DESCRIPTION
        "Transceiver vender name."
    ::= {transbasicinformationEntry 2}

transceivePartNumber   OBJECT-TYPE
    SYNTAX         OCTET STRING (SIZE(0..256))
    MAX-ACCESS     read-only
    STATUS         current
    DESCRIPTION
        "Transceiver PN information"
    ::= {transbasicinformationEntry 3}


transceiveSerialNumber    OBJECT-TYPE
    SYNTAX              OCTET STRING (SIZE(0..256))
    MAX-ACCESS          read-only
    STATUS              current
    DESCRIPTION
        "Transceiver serial number information."
    ::= {transbasicinformationEntry 4}
        
transceiveWaveLength    OBJECT-TYPE
    SYNTAX              Integer32 (0..65535)
    MAX-ACCESS          read-only
    STATUS              current
    DESCRIPTION
        "Transceiver Wavelength ,unit is nm(nanometer)."
    ::= {transbasicinformationEntry 5} 
           
link9SinglemodeLengthKm    OBJECT-TYPE
    SYNTAX              Integer32 (0..65535)
    MAX-ACCESS          read-only
    STATUS              current
    DESCRIPTION
        "Link Length for 9/125um single mode fiber,unit is km(kilometer)."
    ::= {transbasicinformationEntry 6}  
          
link9SinglemodeLengthM   OBJECT-TYPE
    SYNTAX              Integer32 (0..65535)
    MAX-ACCESS          read-only
    STATUS              current
    DESCRIPTION
        "Link Length for 9/125um single mode fiber,unit is m(meter)."
    ::= {transbasicinformationEntry 7}    
           
link50MultimodeLength   OBJECT-TYPE
    SYNTAX              Integer32 (0..65535)
    MAX-ACCESS          read-only
    STATUS              current
    DESCRIPTION
        "Link Length for 50/125um multi-mode fiber,unit is m(meter)."
    ::= {transbasicinformationEntry 8} 
           
link62MultimodeLength  OBJECT-TYPE
    SYNTAX              Integer32 (0..65535)
    MAX-ACCESS          read-only
    STATUS              current
    DESCRIPTION
        "Link Length for 62.5/125um multi-mode fiber,unit is m(meter)."
    ::= {transbasicinformationEntry 9}    
           
linkCopperLength   OBJECT-TYPE
    SYNTAX              Integer32 (0..65535)
    MAX-ACCESS          read-only
    STATUS              current
    DESCRIPTION
        "Link Length for copper,unit is m(meter)."
    ::= {transbasicinformationEntry 10} 
    
transceiveStatus      OBJECT-TYPE
    SYNTAX         OCTET STRING (SIZE(0..256))
    MAX-ACCESS     read-only
    STATUS         current
    DESCRIPTION
        "Transceiver current status."
    ::= {transbasicinformationEntry 11}    

transceiveMointorStatus      OBJECT-TYPE
    SYNTAX         OCTET STRING (SIZE(0..256))
    MAX-ACCESS     read-only
    STATUS         current
    DESCRIPTION
        "Transceiver current mointor status."
    ::= {transbasicinformationEntry 12}

        
-- End    
--  transTemperinformationTable
transTemperinformationTable    OBJECT-TYPE
    SYNTAX         SEQUENCE OF TransTemperinformationEntry
    MAX-ACCESS     not-accessible
    STATUS         current
    DESCRIPTION
        "Show the  temperature information for transceiver."
    ::= {transinformation 2}

transTemperinformationEntry    OBJECT-TYPE
    SYNTAX         TransTemperinformationEntry
    MAX-ACCESS     not-accessible
    STATUS         current
    DESCRIPTION
        "Show the temperature information for transceiver."
    INDEX {ifIndex}
    ::= {transTemperinformationTable 1}

TransTemperinformationEntry ::= 
   SEQUENCE{
        temperHighAlarmThreshold            
            OCTET STRING,   
        temperLowAlarmThreshold             
            OCTET STRING, 
        temperHighWarnThreshold             
            OCTET STRING,
        temperLowWarnThreshold              
            OCTET STRING,          
        temperCurrent              
            OCTET STRING
   }
temperHighAlarmThreshold      OBJECT-TYPE
    SYNTAX         OCTET STRING (SIZE(0..256))
    MAX-ACCESS     read-only
    STATUS         current
    DESCRIPTION
        "Transceiver  temperature high-alarm threshold value,unit is Celsius."
    ::= {transTemperinformationEntry 1}
        
temperLowAlarmThreshold      OBJECT-TYPE
    SYNTAX         OCTET STRING (SIZE(0..256))
    MAX-ACCESS     read-only
    STATUS         current
    DESCRIPTION
        "Transceiver  temperature Low-alarm threshold value, unit is Celsius."
    ::= {transTemperinformationEntry 2}      
   
temperHighWarnThreshold      OBJECT-TYPE
    SYNTAX         OCTET STRING (SIZE(0..256))
    MAX-ACCESS     read-only
    STATUS         current
    DESCRIPTION
        "Transceiver  temperature high-warn threshold value,unit is Celsius."
    ::= {transTemperinformationEntry 3}
         
temperLowWarnThreshold      OBJECT-TYPE
    SYNTAX         OCTET STRING (SIZE(0..256))
    MAX-ACCESS     read-only
    STATUS         current
    DESCRIPTION
        "Transceiver  temperature low-warn threshold value,unit is Celsius."
    ::= {transTemperinformationEntry 4}
   
temperCurrent      OBJECT-TYPE
    SYNTAX         OCTET STRING (SIZE(0..256))
    MAX-ACCESS     read-only
    STATUS         current
    DESCRIPTION
        "Transceiver  currently temperature value,unit is Celsius ."
    ::= {transTemperinformationEntry 5}
 --End  
 --3  transVoltageinformationTable
transVoltageinformationTable    OBJECT-TYPE
    SYNTAX         SEQUENCE OF TransVoltageinformationEntry
    MAX-ACCESS     not-accessible
    STATUS         current
    DESCRIPTION
        "Show the  voltag information for transceiver."
    ::= {transinformation 3}
        
transVoltageinformationEntry    OBJECT-TYPE
    SYNTAX         TransVoltageinformationEntry
    MAX-ACCESS     not-accessible
    STATUS         current
    DESCRIPTION
        "Show the voltag information for transceiver."
    INDEX {ifIndex}
    ::= {transVoltageinformationTable 1}   
          
TransVoltageinformationEntry ::= 
   SEQUENCE{
        voltageHighAlarmThreshold            
            OCTET STRING,   
        voltageLowAlarmThreshold             
            OCTET STRING, 
        voltageHighWarnThreshold             
            OCTET STRING,
        voltageLowWarnThreshold              
            OCTET STRING,          
        voltageCurrent              
            OCTET STRING
   }
voltageHighAlarmThreshold      OBJECT-TYPE
    SYNTAX         OCTET STRING (SIZE(0..256))
    MAX-ACCESS     read-only
    STATUS         current
    DESCRIPTION
        "Transceiver  voltage high-alarm threshold value,unit is Voltage ."
    ::= {transVoltageinformationEntry 1}
        
voltageLowAlarmThreshold      OBJECT-TYPE
    SYNTAX         OCTET STRING (SIZE(0..256))
    MAX-ACCESS     read-only
    STATUS         current
    DESCRIPTION
        "Transceiver  voltage Low-alarm threshold value,unit is Voltage."
    ::= {transVoltageinformationEntry 2}      
   
voltageHighWarnThreshold      OBJECT-TYPE
    SYNTAX         OCTET STRING (SIZE(0..256))
    MAX-ACCESS     read-only
    STATUS         current
    DESCRIPTION
        "Transceiver  voltage high-warn threshold value,unit is Voltage."
    ::= {transVoltageinformationEntry 3}
         
voltageLowWarnThreshold      OBJECT-TYPE
    SYNTAX         OCTET STRING (SIZE(0..256))
    MAX-ACCESS     read-only
    STATUS         current
    DESCRIPTION
        "Transceiver  voltage low-warn threshold value,unit is Voltage."
    ::= {transVoltageinformationEntry 4}
   
voltageCurrent      OBJECT-TYPE
    SYNTAX         OCTET STRING (SIZE(0..256))
    MAX-ACCESS     read-only
    STATUS         current
    DESCRIPTION
        "Transceiver  currently voltage value, unit is Voltage."
    ::= {transVoltageinformationEntry 5}
     
--End
--  transBiasinformationTable
transBiasinformationTable    OBJECT-TYPE
    SYNTAX         SEQUENCE OF TransBiasinformationEntry
    MAX-ACCESS     not-accessible
    STATUS         current
    DESCRIPTION
        "Show the  Current  information for transceiver."
    ::= {transinformation 4}
        
transBiasinformationEntry    OBJECT-TYPE
    SYNTAX         TransBiasinformationEntry
    MAX-ACCESS     not-accessible
    STATUS         current
    DESCRIPTION
        "Show the current value information for transceiver."
    INDEX {ifIndex}
    ::= {transBiasinformationTable 1}   
          
TransBiasinformationEntry ::= 
   SEQUENCE{
        biasHighAlarmThreshold            
            OCTET STRING,   
        biasLowAlarmThreshold             
            OCTET STRING, 
        biasHighWarnThreshold             
            OCTET STRING,
        biasLowWarnThreshold              
            OCTET STRING,          
        biasCurrent              
            OCTET STRING
   }
biasHighAlarmThreshold      OBJECT-TYPE
    SYNTAX         OCTET STRING (SIZE(0..256))
    MAX-ACCESS     read-only
    STATUS         current
    DESCRIPTION
        "Transceiver  bias high-alarm threshold value ,unit is mA(milliamperes)."
    ::= {transBiasinformationEntry 1}
        
biasLowAlarmThreshold      OBJECT-TYPE
    SYNTAX         OCTET STRING (SIZE(0..256))
    MAX-ACCESS     read-only
    STATUS         current
    DESCRIPTION
        "Transceiver  bias Low-alarm threshold value ,unit is mA(milliamperes)."
    ::= {transBiasinformationEntry 2}      
   
biasHighWarnThreshold      OBJECT-TYPE
    SYNTAX         OCTET STRING (SIZE(0..256))
    MAX-ACCESS     read-only
    STATUS         current
    DESCRIPTION
        "Transceiver  current high-warn threshold value ,unit is mA(milliamperes) ."
    ::= {transBiasinformationEntry 3}
         
biasLowWarnThreshold      OBJECT-TYPE
    SYNTAX         OCTET STRING (SIZE(0..256))
    MAX-ACCESS     read-only
    STATUS         current
    DESCRIPTION
        "Transceiver  bias low-warn threshold value ,unit is mA(milliamperes)."
    ::= {transBiasinformationEntry 4}
   
biasCurrent      OBJECT-TYPE
    SYNTAX         OCTET STRING (SIZE(0..256))
    MAX-ACCESS     read-only
    STATUS         current
    DESCRIPTION
        "Transceiver  currently bias value, unit is mA(milliamperes)."
    ::= {transBiasinformationEntry 5}
 --End
 -- 5  transTransmitPowerTables
    
transTransmitPowerTable    OBJECT-TYPE
    SYNTAX         SEQUENCE OF TransTransmitPowerEntry
    MAX-ACCESS     not-accessible
    STATUS         current
    DESCRIPTION
        "Show the  Transmit Power information for transceiver."
    ::= {transinformation 5}
        
transTransmitPowerEntry   OBJECT-TYPE
    SYNTAX         TransTransmitPowerEntry
    MAX-ACCESS     not-accessible
    STATUS         current
    DESCRIPTION
        "Show the Transmit Power value information for transceiver."
    INDEX {ifIndex}
    ::= {transTransmitPowerTable 1}   
          
TransTransmitPowerEntry ::= 
   SEQUENCE{
        transpowerHighAlarmThreshold            
            OCTET STRING,   
        transpowerLowAlarmThreshold             
            OCTET STRING, 
        transpowerHighWarnThreshold             
            OCTET STRING,
        transpowerLowWarnThreshold              
            OCTET STRING,          
        transpowerCurrent              
            OCTET STRING
   }
transpowerHighAlarmThreshold      OBJECT-TYPE
    SYNTAX         OCTET STRING (SIZE(0..256))
    MAX-ACCESS     read-only
    STATUS         current
    DESCRIPTION
        "Transceiver transmit power high-alarm threshold value,unit is dBm."
    ::= {transTransmitPowerEntry 1}
        
transpowerLowAlarmThreshold      OBJECT-TYPE
    SYNTAX         OCTET STRING (SIZE(0..256))
    MAX-ACCESS     read-only
    STATUS         current
    DESCRIPTION
        "Transceiver transmit power Low-alarm threshold value,unit is dBm."
    ::= {transTransmitPowerEntry 2}      
   
transpowerHighWarnThreshold      OBJECT-TYPE
    SYNTAX         OCTET STRING (SIZE(0..256))
    MAX-ACCESS     read-only
    STATUS         current
    DESCRIPTION
        "Transceiver transmit power high-warn threshold value,unit is dBm."
    ::= {transTransmitPowerEntry 3}
         
transpowerLowWarnThreshold      OBJECT-TYPE
    SYNTAX         OCTET STRING (SIZE(0..256))
    MAX-ACCESS     read-only
    STATUS         current
    DESCRIPTION
        "Transceiver transmit power low-warn threshold value,unit is dBm."
    ::= {transTransmitPowerEntry 4}
   
transpowerCurrent      OBJECT-TYPE
    SYNTAX         OCTET STRING (SIZE(0..256))
    MAX-ACCESS     read-only
    STATUS         current
    DESCRIPTION
        "Transceiver currently transmit power value, unit is dBm."
    ::= {transTransmitPowerEntry 5}       

 --  6  transReceivePowerTable   
        
transReceivePowerTable    OBJECT-TYPE
    SYNTAX        SEQUENCE OF TransReceivePowerEntry
    MAX-ACCESS     not-accessible
    STATUS         current
    DESCRIPTION
        "Show the receive Power information for transceiver."
    ::= {transinformation 6}
        
transReceivePowerEntry   OBJECT-TYPE
    SYNTAX         TransReceivePowerEntry
    MAX-ACCESS     not-accessible
    STATUS         current
    DESCRIPTION
        "Show the Transmit Power information for transceiver."
    INDEX {ifIndex}
    ::= {transReceivePowerTable 1}   
          
TransReceivePowerEntry ::= 
   SEQUENCE{
        receivepowerHighAlarmThreshold           
             OCTET STRING,   
        receivepowerLowAlarmThreshold             
             OCTET STRING, 
        receivepowerHighWarnThreshold             
             OCTET STRING,
        receivepowerLowWarnThreshold             
             OCTET STRING,          
        receivepowerCurrent              
             OCTET STRING
   }
   
receivepowerHighAlarmThreshold      OBJECT-TYPE
    SYNTAX         OCTET STRING (SIZE(0..256))
    MAX-ACCESS     read-only
    STATUS         current
    DESCRIPTION
        "Transceiver receive power high-alarm threshold value,unit is dBm."
    ::= {transReceivePowerEntry 1}
        
receivepowerLowAlarmThreshold      OBJECT-TYPE
    SYNTAX         OCTET STRING (SIZE(0..256))
    MAX-ACCESS     read-only
    STATUS         current
    DESCRIPTION
        "Transceiver receive power Low-alarm threshold value,unit is dBm."
    ::= {transReceivePowerEntry 2}      
   
receivepowerHighWarnThreshold      OBJECT-TYPE
    SYNTAX         OCTET STRING (SIZE(0..256))
    MAX-ACCESS     read-only
    STATUS         current
    DESCRIPTION
        "Transceiver receive power high-warn threshold value,unit is dBm."
    ::= {transReceivePowerEntry 3}
         
receivepowerLowWarnThreshold      OBJECT-TYPE
    SYNTAX         OCTET STRING (SIZE(0..256))
    MAX-ACCESS     read-only
    STATUS         current
    DESCRIPTION
        "Transceiver receive power low-warn threshold value,unit is dBm."
    ::= {transReceivePowerEntry 4}
   
receivepowerCurrent      OBJECT-TYPE
    SYNTAX         OCTET STRING (SIZE(0..256))
    MAX-ACCESS     read-only
    STATUS         current
    DESCRIPTION
        "Transceiver currently receive power value, unit is dBm."
    ::= {transReceivePowerEntry 5}

poeInformation OBJECT-IDENTITY
    STATUS current
    DESCRIPTION
        "Transceiver information description."
    ::= { lswdevMMibObject 13 }

poeSysConfigTable OBJECT-TYPE
    SYNTAX        SEQUENCE OF PoeSysConfigEntry
    MAX-ACCESS    not-accessible
    STATUS        current
    DESCRIPTION
        "table of PoE system configuration."
    ::= { poeInformation 1 }

poeSysConfigEntry OBJECT-TYPE
    SYNTAX        PoeSysConfigEntry
    MAX-ACCESS    not-accessible
    STATUS        current
    DESCRIPTION
        "A list of PoE system configuration."
    INDEX    { interfaceIndex }
    ::= {  poeSysConfigTable 1 }

PoeSysConfigEntry    ::=
    SEQUENCE
    {
        poeSysConfigMaxPower
            INTEGER,
        poeSysConfigUtiliThresholdPower
            INTEGER,
        poeSysConfigReservePower
            INTEGER,
        poeSysConfigLegacy
            INTEGER,
        poeSysConfigPM
            INTEGER
    }

poeSysConfigMaxPower OBJECT-TYPE
    SYNTAX        INTEGER(15400..739200)
    MAX-ACCESS    read-write
    STATUS        current
    DESCRIPTION
        "Set PoE system max consumption (milli-watt)."
        DEFVAL { 739200 }
    ::= { poeSysConfigEntry 1 }

poeSysConfigUtiliThresholdPower OBJECT-TYPE
    SYNTAX        INTEGER(0..100)
    MAX-ACCESS    read-write
    STATUS        current
    DESCRIPTION
        "Set PSE alarm threshold of current consumption (percentage)."
        DEFVAL { 90 }
    ::= { poeSysConfigEntry 2 }

poeSysConfigReservePower OBJECT-TYPE
    SYNTAX        INTEGER(0..100)
    MAX-ACCESS    read-write
    STATUS        current
    DESCRIPTION
        "Set PSE reserved consumption (percentage)."
        DEFVAL { 20 }
    ::= { poeSysConfigEntry 3 }

poeSysConfigLegacy OBJECT-TYPE
    SYNTAX        INTEGER {disable(1),enable(2)}
    MAX-ACCESS    read-write
    STATUS        current
    DESCRIPTION
        "Set PoE system legacy capability.The meanings of the values are:
        disable(1)  -  Enable legacy PD detection capability;
        enable(2) -  Disable legacy PD detection capability;"
        DEFVAL { disable }
    ::= { poeSysConfigEntry 4 }

poeSysConfigPM OBJECT-TYPE
    SYNTAX        INTEGER {manual(1),auto(2)}
    MAX-ACCESS    read-write
    STATUS        current
    DESCRIPTION
        "Set PoE system power management.The meanings of the values are:
        manual(1) -  Manual mode;
        auto(2)  -  Auto mode;"
        DEFVAL { manual }
    ::= { poeSysConfigEntry 5 }

poeSysStatusTable OBJECT-TYPE
    SYNTAX        SEQUENCE OF PoeSysStatusEntry
    MAX-ACCESS    not-accessible
    STATUS        current
    DESCRIPTION
        "table of PoE system status."
    ::= { poeInformation 2 }

poeSysStatusEntry OBJECT-TYPE
    SYNTAX        PoeSysStatusEntry
    MAX-ACCESS    not-accessible
    STATUS        current
    DESCRIPTION
        "A list of PoE system status information."
    INDEX    { interfaceIndex }
    ::= { poeSysStatusTable 1 }

PoeSysStatusEntry    ::=
    SEQUENCE
    {
        poeSysStatusCurPower
            INTEGER,
        poeSysStatusAverPower
            INTEGER,
        poeSysStatusPeakPower
            INTEGER,
        poeSysStatusMaxPower
            INTEGER,
        poeSysStatusRemainPower
            INTEGER,
        poeSysStatusUtiliThresholdPower
            INTEGER,
        poeSysStatusReservePower
            INTEGER,
        poeSysStatusCurVoltage
            INTEGER,
        poeSysStatusAverVoltage
            INTEGER,
        poeSysStatusPeakVoltage
            INTEGER,
        poeSysStatusLegacy
            OCTET STRING,
        poeSysStatusPM
            OCTET STRING
    }

poeSysStatusCurPower OBJECT-TYPE
    SYNTAX        INTEGER(0..739200)
    MAX-ACCESS    read-only
    STATUS        current
    DESCRIPTION
        "Get PSE total current consumption (milli-watt)."
        DEFVAL { 0 }
    ::= { poeSysStatusEntry 1 }

poeSysStatusAverPower OBJECT-TYPE
    SYNTAX        INTEGER(0..739200)
    MAX-ACCESS    read-only
    STATUS        current
    DESCRIPTION
        "Get PSE history average consumption of certain period of time recently (milli-watt)."
        DEFVAL { 0 }
    ::= { poeSysStatusEntry 2 }

poeSysStatusPeakPower OBJECT-TYPE
    SYNTAX        INTEGER(0..739200)
    MAX-ACCESS    read-only
    STATUS        current
    DESCRIPTION
        "Get PSE history peak consumption of certain period of time recently (milli-watt)."
        DEFVAL { 0 }
    ::= { poeSysStatusEntry 3 }

poeSysStatusMaxPower OBJECT-TYPE
    SYNTAX        INTEGER(15400..739200)
    MAX-ACCESS    read-only
    STATUS        current
    DESCRIPTION
        "Get PoE system max consumption (milli-watt)."
        DEFVAL { 0 }
    ::= { poeSysStatusEntry 4 }

poeSysStatusRemainPower OBJECT-TYPE
    SYNTAX        INTEGER(0..739200)
    MAX-ACCESS    read-only
    STATUS        current
    DESCRIPTION
        "Get PSE remaining power including PSE reserved power (milli-watt)."
        DEFVAL { 0 }
    ::= { poeSysStatusEntry 5 }

poeSysStatusUtiliThresholdPower OBJECT-TYPE
    SYNTAX        INTEGER(0..100)
    MAX-ACCESS    read-only
    STATUS        current
    DESCRIPTION
        "Get PSE alarm threshold of current consumption (percentage)."
        DEFVAL { 0 }
    ::= { poeSysStatusEntry 6 }

poeSysStatusReservePower OBJECT-TYPE
    SYNTAX        INTEGER(0..100)
    MAX-ACCESS    read-only
    STATUS        current
    DESCRIPTION
        "Get PSE reserved consumption (percentage)."
        DEFVAL { 0 }
    ::= { poeSysStatusEntry 7 }

poeSysStatusCurVoltage OBJECT-TYPE
    SYNTAX        INTEGER(0..60000)
    MAX-ACCESS    read-only
    STATUS        current
    DESCRIPTION
        "Get PSE current voltage of supply power (milli-voltage)."
        DEFVAL { 0 }
    ::= { poeSysStatusEntry 8 }

poeSysStatusAverVoltage OBJECT-TYPE
    SYNTAX        INTEGER(0..60000)
    MAX-ACCESS    read-only
    STATUS        current
    DESCRIPTION
        "Get PSE average voltage of supply power of certain period of time recently (milli-voltage)."
        DEFVAL { 0 }
    ::= { poeSysStatusEntry 9 }

poeSysStatusPeakVoltage OBJECT-TYPE
    SYNTAX        INTEGER(0..60000)
    MAX-ACCESS    read-only
    STATUS        current
    DESCRIPTION
        "Get PSE peak voltage of supply power of certain period of time recently (milli-voltage)."
        DEFVAL { 0 }
    ::= { poeSysStatusEntry 10 }

poeSysStatusLegacy OBJECT-TYPE
    SYNTAX        OCTET STRING (SIZE(0..256))
    MAX-ACCESS    read-only
    STATUS        current
    DESCRIPTION
        "Get PoE system legacy capability."
        DEFVAL { "disable" }
    ::= { poeSysStatusEntry 11 }

poeSysStatusPM OBJECT-TYPE
    SYNTAX        OCTET STRING (SIZE(0..256))
    MAX-ACCESS    read-only
    STATUS        current
    DESCRIPTION
        "Get PoE system power management."
        DEFVAL { "manual" }
    ::= { poeSysStatusEntry 12 }

poePortStatusTable OBJECT-TYPE
    SYNTAX        SEQUENCE OF PoePortStatusEntry
    MAX-ACCESS    not-accessible
    STATUS        current
    DESCRIPTION
        "table of PoE port status."
    ::= { poeInformation 3 }

poePortStatusEntry OBJECT-TYPE
    SYNTAX        PoePortStatusEntry
    MAX-ACCESS    not-accessible
    STATUS        current
    DESCRIPTION
        "A list of PoE port status information."
    INDEX    { interfaceIndex }
    ::= { poePortStatusTable 1 }

PoePortStatusEntry    ::=
    SEQUENCE
    {
        poePortAdmin
            OCTET STRING,
        poePortPriority
            OCTET STRING,
        poePortOper
            OCTET STRING,
        poePortClass
            OCTET STRING,
        poePortCurPower
            INTEGER,
        poePortAverPower
            INTEGER,
        poePortPeakPower
            INTEGER,
        poePortMaxPower
            INTEGER
    }

poePortAdmin OBJECT-TYPE
    SYNTAX        OCTET STRING (SIZE(0..256))
    MAX-ACCESS    read-only
    STATUS        current
    DESCRIPTION
        "Get PoE port admin."
        DEFVAL { "enable" }
    ::= { poePortStatusEntry 1 }

poePortPriority OBJECT-TYPE
    SYNTAX        OCTET STRING (SIZE(0..256))
    MAX-ACCESS    read-only
    STATUS        current
    DESCRIPTION
        "Get PoE port priority level."
        DEFVAL { "low" }
    ::= { poePortStatusEntry 2 }

poePortOper OBJECT-TYPE
    SYNTAX        OCTET STRING (SIZE(0..256))    
    MAX-ACCESS    read-only
    STATUS        current
    DESCRIPTION
        "Get PoE port operating result status."
    ::= { poePortStatusEntry 3 }

poePortClass OBJECT-TYPE
    SYNTAX        OCTET STRING (SIZE(0..256))
    MAX-ACCESS    read-only
    STATUS        current
    DESCRIPTION
        "Get PoE port PD IEEE class level."
    ::= { poePortStatusEntry 4 }

poePortCurPower OBJECT-TYPE
    SYNTAX        INTEGER(0..30000)
    MAX-ACCESS    read-only
    STATUS        current
    DESCRIPTION
        "Get PoE port current consumption (milli-watt)."
    ::= { poePortStatusEntry 5 }

poePortAverPower OBJECT-TYPE
    SYNTAX        INTEGER(0..30000)
    MAX-ACCESS    read-only
    STATUS        current
    DESCRIPTION
        "Get PoE port history average consumption of certain period of time recently (milli-watt)."
    ::= { poePortStatusEntry 6 }

poePortPeakPower OBJECT-TYPE
    SYNTAX        INTEGER(0..30000)
    MAX-ACCESS    read-only
    STATUS        current
    DESCRIPTION
        "Get PoE port history peak consumption of certain period of time recently (milli-watt)."
    ::= { poePortStatusEntry 7 }

poePortMaxPower OBJECT-TYPE
    SYNTAX        INTEGER(0..30000)
    MAX-ACCESS    read-only
    STATUS        current
    DESCRIPTION
        "Get PoE port max consumption limit (milli-watt)."
    ::= { poePortStatusEntry 8 }

-- Sub Module: LSWTRAPMIB
        
        
        
    lswTRAPMibObject OBJECT IDENTIFIER ::= {   lswTrapMib 1  }    

         
            
            
powerabsent NOTIFICATION-TYPE
    OBJECTS      { devMPowerIndex }
    STATUS          current
    DESCRIPTION
        "Power supply absent."
    ::= { lswTRAPMibObject 1 }
    
powerfailure NOTIFICATION-TYPE
    OBJECTS      { devMPowerIndex }
    STATUS          current
    DESCRIPTION
        "Power supply failure."
    ::= { lswTRAPMibObject 2 }
       
powerNormal NOTIFICATION-TYPE
    OBJECTS       { devMPowerIndex }
    STATUS          current
    DESCRIPTION
        "Power supply normal."
    ::= { lswTRAPMibObject 3 }       

powerfanfailure NOTIFICATION-TYPE
    OBJECTS      { devMPowerIndex }
    STATUS          current
    DESCRIPTION
        "The fan of power supply failure."
    ::= { lswTRAPMibObject 4 }

fanfailure NOTIFICATION-TYPE
    OBJECTS       { devMFanPosition, devMFanModuleId, devMFanIndex }
    STATUS          current
    DESCRIPTION
        "Fan failure."
    ::= { lswTRAPMibObject 5 }
      
      
fanNormal NOTIFICATION-TYPE
    OBJECTS       { devMFanPosition, devMFanModuleId, devMFanIndex }
    STATUS          current
    DESCRIPTION
        "Fan normal."
    ::= { lswTRAPMibObject 6 }
    
 
--linecardRemoved NOTIFICATION-TYPE
--    OBJECTS   {lswSlotFrameIndex, lswSlotIndex }
--    STATUS          current
--    DESCRIPTION
--        "Linecard removed."
--    ::= { lswTRAPMibObject 7 }
--      
--linecardInserted NOTIFICATION-TYPE
--    OBJECTS       { lswSlotFrameIndex,lswSlotIndex }
--    STATUS          current
--    DESCRIPTION
--        "Linecard inserted."
--    ::= { lswTRAPMibObject 8 }
--          
--subcardRemove NOTIFICATION-TYPE
--    OBJECTS { lswSubslotFrameIndex, lswSubslotSlotIndex, lswSubslotIndex }
--    STATUS          current
--    DESCRIPTION
--        "Sub card removed."
--    ::= { lswTRAPMibObject 9 }
--
--subcardInsert NOTIFICATION-TYPE
--    OBJECTS { lswSubslotFrameIndex, lswSubslotSlotIndex, lswSubslotIndex }
--    STATUS          current
--    DESCRIPTION
--        "Sub card inserted."
--    ::= { lswTRAPMibObject 10 }
  
supervisorRemove NOTIFICATION-TYPE
    OBJECTS      { lswSlotFrameIndex,lswSlotIndex }
    STATUS          current
    DESCRIPTION
        "Supervisor card removed."
    ::= { lswTRAPMibObject 11 }

supervisorInsert NOTIFICATION-TYPE
    OBJECTS   { lswSlotFrameIndex,lswSlotIndex }
    STATUS          current
    DESCRIPTION
        "Supervisor card inserted."
    ::= { lswTRAPMibObject 12 }     
      
boardTemperatureAlarm NOTIFICATION-TYPE
    OBJECTS    { lswSlotFrameIndex,lswSlotIndex,devMSlotEnvironmentValue }
    STATUS          current
    DESCRIPTION
        "Board temperature high."
    ::= { lswTRAPMibObject 13 } 
      
boardTemperatureReturnNormal NOTIFICATION-TYPE
    OBJECTS        { lswSlotFrameIndex,lswSlotIndex,devMSlotEnvironmentValue }
    STATUS          current
    DESCRIPTION
        "Board temperature from higher to normal."
    ::= { lswTRAPMibObject 14 }      

loadFailure NOTIFICATION-TYPE
    OBJECTS    { lswSlotFrameIndex,lswSlotIndex }
    STATUS          current
    DESCRIPTION
        "Board load failure."
    ::= { lswTRAPMibObject 15 } 

loadFinished NOTIFICATION-TYPE
      OBJECTS  { lswSlotFrameIndex,lswSlotIndex }
    STATUS          current
    DESCRIPTION
        "Board load finished."
    ::= { lswTRAPMibObject 16 }  
      
--fatalInterrupt NOTIFICATION-TYPE
--      OBJECTS  { lswFatalInterruptAddr,lswFatalInterruptMask }
--    STATUS          current
--    DESCRIPTION
--        "Get fatal interrupt message."
--    ::= { lswTRAPMibObject 17 }
    
transceiverInsert NOTIFICATION-TYPE
    OBJECTS  { transceiveStatus }
    STATUS          current
    DESCRIPTION
        "Transceiver inserted."
    ::= { lswTRAPMibObject 18 }
      
transceiverRemove NOTIFICATION-TYPE
    OBJECTS  { transceiveStatus }
    STATUS          current
    DESCRIPTION
        "Transceiver removed."
    ::= { lswTRAPMibObject 19 }
    
transceiverSfpMonitor NOTIFICATION-TYPE
    OBJECTS    { transceiveMointorStatus }
    STATUS          current
    DESCRIPTION
        "Transceiver Sfp Monitor has detected warning or alarm."
    ::= { lswTRAPMibObject 20}   

chsmBootupDiagTrap NOTIFICATION-TYPE
    OBJECTS    { devMFanPosition }
    STATUS          current
    DESCRIPTION
        "Chsm bootup diag trap."
    ::= { lswTRAPMibObject 21}   

chsmPoePortStatTrap NOTIFICATION-TYPE
    OBJECTS    { poeInformation }
    STATUS          current
    DESCRIPTION
        "Chsm PoE port status change trap."
    ::= { lswTRAPMibObject 22}

chsmPoeSysConsumpThresholdTrap NOTIFICATION-TYPE
    OBJECTS    { poeInformation }
    STATUS          current
    DESCRIPTION
        "Chsm PoE system consumption warn threshold trap."
    ::= { lswTRAPMibObject 23}

chsmPoePseVoltageTrap NOTIFICATION-TYPE
    OBJECTS    { poeInformation }
    STATUS          current
    DESCRIPTION
        "Chsm bootup diag trap."
    ::= { lswTRAPMibObject 24}   

fanAbsent NOTIFICATION-TYPE
    OBJECTS       { devMFanIndex }
    STATUS          current
    DESCRIPTION
        "Fan absent."
    ::= { lswTRAPMibObject 25 }


fanPresent NOTIFICATION-TYPE
    OBJECTS      { devMFanIndex }
    STATUS          current
    DESCRIPTION
        "Fan present."
    ::= { lswTRAPMibObject 26 }
    
powerAlert NOTIFICATION-TYPE
    OBJECTS       { devMPowerIndex }
    STATUS          current
    DESCRIPTION
        "Power alert."
    ::= { lswTRAPMibObject 27 }       

powerNoAlert NOTIFICATION-TYPE
    OBJECTS       { devMPowerIndex }
    STATUS          current
    DESCRIPTION
        "Power no alert."
    ::= { lswTRAPMibObject 28 }       

-- Sub Module: IPSOURCEGUARD

            
       
-- ip source guard binding type
        IpSourceGuardType    ::= TEXTUAL-CONVENTION
    STATUS          current
    DESCRIPTION
        "p source guard's binding type, ip, ip-mac, ip-vlan, ip-mac-vlan."
    SYNTAX          INTEGER
    {
        disable(0),
        ip(1),
        ipMac(2),
        ip-vlan(3),
        ipMacVlan(4)
    }
            
--
-- Node of ipSourceGuard max number of binding entry perport
--
ipSourceGuardPerportMaximalnumber         OBJECT-TYPE
    SYNTAX          Integer32 (0..30)
    MAX-ACCESS      read-write
    STATUS          current
    DESCRIPTION
        "config ip source guard max number of entry perport."
    ::= { ipSourceGuard 1 }
            
    
--
-- Nodes of ipSourceGuard entry table
--
ipSourceGuardBindingTable         OBJECT-TYPE
    SYNTAX          SEQUENCE OF IpSourceGuardBindingEntry
    MAX-ACCESS      not-accessible
    STATUS          current
    DESCRIPTION
        "table of ip source guard binding entry.
        "
    ::= { ipSourceGuard 2 }
            
ipSourceGuardBindingEntry         OBJECT-TYPE
    SYNTAX          IpSourceGuardBindingEntry
    MAX-ACCESS      not-accessible
    STATUS          current
    DESCRIPTION
        "ip source guard binding entry."
    INDEX     { ipSourceGuardIpAddress}
    ::= { ipSourceGuardBindingTable 1 }
            
        IpSourceGuardBindingEntry    ::=
    SEQUENCE
    {
        ipSourceGuardIpAddress
            IpAddress,
        ipSourceGuardMacAddress
            MacAddress,
        ipSourceGuardVlan
            Integer32,
        iSGIfIndex
            Integer32,
        ipSourceGuardRowStatus
            RowStatus
    }

ipSourceGuardIpAddress         OBJECT-TYPE
    SYNTAX          IpAddress
    MAX-ACCESS      read-only
    STATUS          current
    DESCRIPTION
        "the ip address of a packet."
    ::= { ipSourceGuardBindingEntry 1 }

ipSourceGuardMacAddress         OBJECT-TYPE
    SYNTAX          MacAddress
    MAX-ACCESS      read-create
    STATUS          current
    DESCRIPTION
        "The MAC address of a packet."
    ::= { ipSourceGuardBindingEntry 2 }

ipSourceGuardVlan         OBJECT-TYPE
    SYNTAX          Integer32 (1..4094)
    MAX-ACCESS      read-create
    STATUS          current
    DESCRIPTION
        "The VLAN ID of a packet."
    ::= { ipSourceGuardBindingEntry 3 }

iSGIfIndex         OBJECT-TYPE
    SYNTAX          Integer32
    MAX-ACCESS      read-create
    STATUS          current
    DESCRIPTION
        "The interface from which the packet comes."
    ::= { ipSourceGuardBindingEntry 4 }

ipSourceGuardRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { ipSourceGuardBindingEntry 5 }   

--
-- Nodes of ipSourceGuard enable on the interface
--
ipSourceGuardEnableTable         OBJECT-TYPE
    SYNTAX          SEQUENCE OF IpSourceGuardEnableEntry
    MAX-ACCESS      not-accessible
    STATUS          current
    DESCRIPTION
        "A table for ip source guard enable .
        "
    ::= { ipSourceGuard 3 }         
            
ipSourceGuardEnableEntry         OBJECT-TYPE
    SYNTAX          IpSourceGuardEnableEntry
    MAX-ACCESS      not-accessible
    STATUS          current
    DESCRIPTION
        "A entry for ip source guard enable."
    INDEX     { iSGEnableIfIndex }
    ::= { ipSourceGuardEnableTable 1 }        
            
IpSourceGuardEnableEntry    ::=
    SEQUENCE
    {
        iSGEnableIfIndex
            Integer32,
        ipSourceGuardEnableType
            IpSourceGuardType
     }

iSGEnableIfIndex         OBJECT-TYPE
    SYNTAX          Integer32 (0..65535)
    MAX-ACCESS      not-accessible
    STATUS          current
    DESCRIPTION
        "the interface index of isg enabled."
    ::= { ipSourceGuardEnableEntry 1 }  
             
ipSourceGuardEnableType         OBJECT-TYPE
    SYNTAX          IpSourceGuardType
    MAX-ACCESS      read-write
    STATUS          current
    DESCRIPTION
        "the enable type of ip source guard, support ip, ip-mac, ip-vlan, ip-mac-vlan."
    ::= { ipSourceGuardEnableEntry 2}       
  

        
-- Sub Module: INTERFACE

interfaceTable         OBJECT-TYPE
    SYNTAX          SEQUENCE OF InterfaceEntry
    MAX-ACCESS      not-accessible
    STATUS          current
    DESCRIPTION
        "table of interface entry."
    ::= { interface 1 }
            
interfaceEntry         OBJECT-TYPE
    SYNTAX          InterfaceEntry
    MAX-ACCESS      not-accessible
    STATUS          current
    DESCRIPTION
        "interface entry        "
    INDEX     { interfaceIndex}
    ::= { interfaceTable 1 }
            
InterfaceEntry    ::=
    SEQUENCE
    {
        interfaceIndex
            Integer32,
        interfaceName
            OCTET STRING,
        interfaceType
            INTEGER,
        interfaceIPv4Addr
            OCTET STRING,
        interfaceDesc
            OCTET STRING,
        interfaceMediaType
            INTEGER,
        interfaceSpeed
            INTEGER,
        interfaceDuplex
            INTEGER,
        interfaceResetCnt
            INTEGER,
        interfaceArpRetryInterval
            INTEGER,
        interfaceArpTimeout
            INTEGER,
        interfaceArpClear
            INTEGER,
        interfacejumboFrameEnable
            INTEGER,
        interfaceClearIPv4Addr
            INTEGER,
        interfaceBandwidth
            INTEGER,
        interfacePortIsolateGroupID
            INTEGER,
        interfaceArpProxy
            INTEGER,
        interfaceLocalArpProxy
            INTEGER,
        interfacePoeAdmin
            INTEGER,
        interfacePoeBudget
            INTEGER,
        interfacePoePriority
            INTEGER,
        interfaceLoadInterval
            INTEGER,
        interfaceMtu
            INTEGER,
	interfaceIpUrpf
            INTEGER,
	interfaceIpv6Urpf
            INTEGER,
	interfaceIpv6DadAttempt
            INTEGER,
	interfaceNDClear
            INTEGER
     }

interfaceIndex         OBJECT-TYPE
    SYNTAX          Integer32 (1..65535)
    MAX-ACCESS      not-accessible
    STATUS          current
    DESCRIPTION
        "Interface index. physical interface:0x1~0x3FF,
  agg interface: 0x400~0x7FF, vlan interface:0x1000~0x1FFF,
  lookback interface:0x3000~0x3FFF"
    ::= { interfaceEntry 1 }

interfaceName         OBJECT-TYPE
    SYNTAX          OCTET STRING (SIZE (1..16))
    MAX-ACCESS      read-only
    STATUS          current
    DESCRIPTION        "Interface name."
    ::= { interfaceEntry 2 }

interfaceType         OBJECT-TYPE
    SYNTAX          INTEGER
            {
                switch(1),
                route(2)
            }
    MAX-ACCESS      read-write
    STATUS          current
    DESCRIPTION
        "The interface type.1:switch 2:route."
    ::= { interfaceEntry 3 }

        interfaceIPv4Addr         OBJECT-TYPE
    SYNTAX          OCTET STRING (SIZE(9..18))
    MAX-ACCESS      read-write
    STATUS          current
    DESCRIPTION        "IP addresses with mask , such as 123.123.123.123/24 ."
    ::= { interfaceEntry 4 }


interfaceDesc         OBJECT-TYPE
    SYNTAX          OCTET STRING (SIZE(0..20))
    MAX-ACCESS      read-write
    STATUS          current
            DESCRIPTION "Interface specific description."
    ::= { interfaceEntry 5 }

interfaceMediaType         OBJECT-TYPE
    SYNTAX          INTEGER
            {
                autoSelect(0),
                rj45(1),
                sfp(2)
            }
    MAX-ACCESS      read-write
    STATUS          current
    DESCRIPTION
        "Specifies the port media type.0:auto-select 1:rj45 2:sfp."
    ::= { interfaceEntry 6 }

interfaceSpeed         OBJECT-TYPE
    SYNTAX          INTEGER
            {
                auto(0),
                speed10M(1),
                speed100M(2),
                speed1000M(3),
    speed10G(4)
            }
    MAX-ACCESS      read-write
    STATUS          current
    DESCRIPTION
        "Specifies the port speed.0:auto 1:10 2:100 3:1000. speed10G can not be set, but can be get "
    ::= { interfaceEntry 7 }

interfaceDuplex         OBJECT-TYPE
    SYNTAX          INTEGER
            {
                auto(0),
                half(1),
                full(2)
            }
    MAX-ACCESS      read-write
    STATUS          current
    DESCRIPTION        "Specifies the port duplexStatus .0:auto 1:half 2:full."
    ::= { interfaceEntry 8 }

interfaceResetCnt         OBJECT-TYPE
    SYNTAX          INTEGER
            {
                noUse(0),
        resetCount(1)
            }
    MAX-ACCESS      read-write
    STATUS          current
    DESCRIPTION
        "Reset interface counters; 0: noUse, 1: resetCount."
    ::= { interfaceEntry 9 }

interfaceArpRetryInterval         OBJECT-TYPE
    SYNTAX          INTEGER(0..3)
    MAX-ACCESS      read-write
    STATUS          current
    DESCRIPTION        " Set arp request retry delay value to interface. Interval range 0~3."
    ::= { interfaceEntry 10 }

interfaceArpTimeout         OBJECT-TYPE
    SYNTAX          INTEGER(1..2147483)
    MAX-ACCESS      read-write
    STATUS          current
    DESCRIPTION
        " Set arp age timeout value to interface. Timeout range 1~2147483. "
    ::= { interfaceEntry 11 }

interfaceArpClear         OBJECT-TYPE
    SYNTAX          INTEGER
            {
                noUse(0),
        clearArp(1)
            }
    MAX-ACCESS      read-write
    STATUS          current
    DESCRIPTION        "Clear arp cache.0:no use, 1:clear arp. "
    ::= { interfaceEntry 12 }

interfacejumboFrameEnable OBJECT-TYPE
    SYNTAX  INTEGER
    {
        enable(1),
        disable(2)
    }
    MAX-ACCESS read-write
    STATUS current
    DESCRIPTION
   "Jumbo frame. 1:enabel, 2:disable"
    ::= { interfaceEntry 13 }

interfaceClearIPv4Addr OBJECT-TYPE
    SYNTAX  INTEGER
    {
        noUse(0),
        clearIPv4Addr(1)
    }
    MAX-ACCESS read-write
    STATUS current
    DESCRIPTION
    "Clear the IPv4 address of the interface including secondary IPv4 address.0:no use, 1:clear IPv4 address. "
    ::= { interfaceEntry 14 }

interfaceBandwidth OBJECT-TYPE
    SYNTAX  INTEGER(0..10000000)
    MAX-ACCESS read-write
    STATUS current
    DESCRIPTION
    "Set bandwidth informational parameter(bandwidth in kilobits). Use 0 to set default value.
    The default value of 10M port is 10000.
    The default value of 100M port is 100000.
    The default value of 1000M port is 1000000."
    ::= { interfaceEntry 15 }

interfacePortIsolateGroupID OBJECT-TYPE
    SYNTAX  INTEGER(1..31255)
    MAX-ACCESS read-write
    STATUS current
    DESCRIPTION
    "Set the isolate group of a interface. isolate group id range is 1 ~ 31. and 255(0xFF) mean delete group. "
    ::= { interfaceEntry 16 }

interfaceArpProxy         OBJECT-TYPE
    SYNTAX          INTEGER{enable(1),disable(2)}
    MAX-ACCESS      read-write
    STATUS          current
    DESCRIPTION
        " Enable or disable arp proxy feature."
    DEFVAL { disable }
    ::= { interfaceEntry 17 }

interfaceLocalArpProxy         OBJECT-TYPE
    SYNTAX          INTEGER{enable(1),disable(2)}
    MAX-ACCESS      read-write
    STATUS          current
    DESCRIPTION
        " Enable or disable local arp proxy feature."
    DEFVAL { disable }
    ::= { interfaceEntry 18 }

interfacePoeAdmin OBJECT-TYPE
    SYNTAX        INTEGER {enable(1),disable(2),force-power(3)}
    MAX-ACCESS    read-write
    STATUS        current
    DESCRIPTION
        "Set PoE port admin.The meanings of the values are:
        enable(1)  -  Enable port PoE;
        disable(2) -  Disable port PoE;
        force-power(3) - Force to power on port PoE;"
        DEFVAL { enable }
    ::= { interfaceEntry 19 }

interfacePoeBudget OBJECT-TYPE
    SYNTAX        INTEGER(0..30000)
    MAX-ACCESS    read-write
    STATUS        current
    DESCRIPTION
        "Set PoE port max consumption limitation (milli-watt)."
        DEFVAL { 30000 }
    ::= { interfaceEntry 20 }

interfacePoePriority OBJECT-TYPE
    SYNTAX        INTEGER{low(1),high(2),critical(3)}
    MAX-ACCESS    read-write
    STATUS        current
    DESCRIPTION
        "Set PoE port priority level. The meanings of the value are:
        low(1) - Low priority;
        high(2) - High priority;
        critical(3) - critical priority;"
        DEFVAL { low }
    ::= { interfaceEntry 21 }

interfaceLoadInterval OBJECT-TYPE
    SYNTAX  INTEGER(30..600)
    MAX-ACCESS read-write
    STATUS current
    DESCRIPTION
        "Specify interval for interface speed calculation.
         Load-interval must be in increments of 30 seconds.
         The load-interval ranges from 30 to 600 and default
         value is 300."
         DEFVAL { 300 }
    ::= { interfaceEntry 22 }

interfaceMtu OBJECT-TYPE
    SYNTAX        INTEGER(68..9000)
    MAX-ACCESS    read-write
    STATUS        current
    DESCRIPTION
        "Set MTU of the interface."
        DEFVAL { 1500 }
    ::= { interfaceEntry 23 }
    
 interfaceIpUrpf OBJECT-TYPE
    SYNTAX        INTEGER{enable(1),disable(2)}
    MAX-ACCESS    read-write
    STATUS        current
    DESCRIPTION
        "Set IP Unicast reverse-path of the interface."
        DEFVAL {disable }
    ::= { interfaceEntry 24 }
    
interfaceIpv6Urpf OBJECT-TYPE
    SYNTAX        INTEGER{enable(1),disable(2)}
    MAX-ACCESS    read-write
    STATUS        current
    DESCRIPTION
        "Set IPv6 Unicast reverse-path of the interface."
        DEFVAL {disable }
    ::= { interfaceEntry 25 }  
    
 interfaceIpv6DadAttempt OBJECT-TYPE
    SYNTAX        INTEGER(0..600)
    MAX-ACCESS    read-write
    STATUS        current
    DESCRIPTION
        "Set IPv6 Duplicate address detection attempts number."
        DEFVAL {1}
    ::= { interfaceEntry 26 }
    
interfaceNDClear OBJECT-TYPE
    SYNTAX        INTEGER{noUse(0),clearND(1)}
    MAX-ACCESS    read-write
    STATUS        current
    DESCRIPTION
        "Clear arp cache.0:no use, 1:clear ND."
    ::= { interfaceEntry 27 }
	
--
--  config interface secondary ip address
--
interfaceSecondaryIpAddrTable         OBJECT-TYPE
    SYNTAX          SEQUENCE OF InterfaceSecondaryIpAddrEntry
    MAX-ACCESS      not-accessible
    STATUS          current
    DESCRIPTION
        "table of interface secondary ip address."
    ::= { interface 2 }

interfaceSecondaryIpAddrEntry         OBJECT-TYPE
    SYNTAX          InterfaceSecondaryIpAddrEntry
    MAX-ACCESS      not-accessible
    STATUS          current
    DESCRIPTION
        "interface entry."
    INDEX     {interfaceIndex,ifSecondaryIpAddr}
    ::= { interfaceSecondaryIpAddrTable 1 }

        InterfaceSecondaryIpAddrEntry    ::=
    SEQUENCE
    {
        ifSecondaryIpAddr
            IpAddress,
        ifSecondaryIpAddrMask
            Integer32,
        interfaceSecondaryIpAddrStatus
            RowStatus
    }


ifSecondaryIpAddr         OBJECT-TYPE
    SYNTAX          IpAddress
    MAX-ACCESS      not-accessible
    STATUS          current
    DESCRIPTION
        "Set secondary ip address on interface."
    ::= { interfaceSecondaryIpAddrEntry 1 }



ifSecondaryIpAddrMask         OBJECT-TYPE
    SYNTAX          Integer32 (1..32)
    MAX-ACCESS      read-write
    STATUS          current
    DESCRIPTION        
        " Set secondary ip address mask on interface."
    ::= { interfaceSecondaryIpAddrEntry 2 }              
            
            
            
interfaceSecondaryIpAddrStatus         OBJECT-TYPE
    SYNTAX          RowStatus
    MAX-ACCESS      read-create
    STATUS          current
    DESCRIPTION        
        "The status of this conceptual row.Now only realize CreateAndGo 
        and Destroy and Active.
        1 means Active
        4 means CreateAndGo
        6 means Destroy"
    ::= { interfaceSecondaryIpAddrEntry 3 }              
        
        








loopbackInterfaceTable         OBJECT-TYPE
    SYNTAX          SEQUENCE OF LoopbackInterfaceEntry
    MAX-ACCESS      not-accessible
    STATUS          current
    DESCRIPTION
        "table of loopback interface."
    ::= { interface 3 }
            
loopbackInterfaceEntry         OBJECT-TYPE
    SYNTAX          LoopbackInterfaceEntry
    MAX-ACCESS      not-accessible
    STATUS          current
    DESCRIPTION
        "loopback interface entry."
    INDEX     {loopbackInterfaceNum}
    ::= { loopbackInterfaceTable 1 }
            
LoopbackInterfaceEntry    ::=
    SEQUENCE
    {
        loopbackInterfaceNum
            Integer32,
        loopbackInterfaceIndex
            Integer32,
        loopbackInterfaceStatus
            RowStatus 
    }

loopbackInterfaceNum         OBJECT-TYPE
    SYNTAX          Integer32 (0..255)
    MAX-ACCESS      read-only
    STATUS          current
    DESCRIPTION        "The number of loopback interface."
    ::= { loopbackInterfaceEntry 1 }

loopbackInterfaceIndex         OBJECT-TYPE
    SYNTAX       Integer32
    MAX-ACCESS      read-only
    STATUS          current
    DESCRIPTION        "The index of loopback interface."
    ::= { loopbackInterfaceEntry 2 }

loopbackInterfaceStatus         OBJECT-TYPE
    SYNTAX          RowStatus
    MAX-ACCESS      read-create
    STATUS          current
    DESCRIPTION       
        "The status of this conceptual row.Now only realize CreateAndGo 
        and Destroy and Active.
        1 means Active
        4 means CreateAndGo
        6 means Destroy"
    ::= { loopbackInterfaceEntry 3 }

--
--  config interface ipv6 address
--
interfaceIpv6AddrTable         OBJECT-TYPE
    SYNTAX          SEQUENCE OF InterfaceIpv6AddrEntry
    MAX-ACCESS      not-accessible
    STATUS          current
    DESCRIPTION
        "table of interface ipv6 address."
    ::= { interface 4 }

interfaceIpv6AddrEntry         OBJECT-TYPE
    SYNTAX          InterfaceIpv6AddrEntry
    MAX-ACCESS      not-accessible
    STATUS          current
    DESCRIPTION
        "interface ipv6 address entry."
    INDEX     {interfaceIndex,ifIpv6Addr}
    ::= { interfaceIpv6AddrTable 1 }

    InterfaceIpv6AddrEntry    ::=
    SEQUENCE
    {
        ifIpv6Addr
            OCTET STRING,
        ifIpv6AddrLength
            Integer32,
        ifIpv6AddrEui64
            INTEGER,
        ifIpv6AddrLinkLocal
            INTEGER,  
        ifIpv6AddrStatus
            RowStatus
    }

ifIpv6Addr          OBJECT-TYPE
    SYNTAX          OCTET STRING
    MAX-ACCESS      not-accessible
    STATUS          current
    DESCRIPTION
        "Set ipv6 address on interface."
    ::= { interfaceIpv6AddrEntry 1 }

ifIpv6AddrLength         OBJECT-TYPE
    SYNTAX          Integer32 (1..128)
    MAX-ACCESS      read-create
    STATUS          current
    DESCRIPTION
        " Set ipv6 address prefix length."
    ::= { interfaceIpv6AddrEntry 2 }
    
ifIpv6AddrEui64         OBJECT-TYPE
    SYNTAX          INTEGER{enable(1),disable(2)}
    MAX-ACCESS      read-create
    STATUS          current
    DESCRIPTION
        " Set ipv6 address use eui-64 interface identifier."
        DEFVAL {disable}   
    ::= { interfaceIpv6AddrEntry 3 } 
    
ifIpv6AddrLinkLocal     OBJECT-TYPE
    SYNTAX          INTEGER{enable(1),disable(2)}
    MAX-ACCESS      read-create
    STATUS          current
    DESCRIPTION
        " Set ipv6 link-local address."
        DEFVAL {disable}
    ::= { interfaceIpv6AddrEntry 4 }
    
ifIpv6AddrStatus         OBJECT-TYPE
    SYNTAX          RowStatus
    MAX-ACCESS      read-create
    STATUS          current
    DESCRIPTION
        "The status of this conceptual row.Now only realize CreateAndGo
        and Destroy and Active."
    ::= { interfaceIpv6AddrEntry 5 }

interfaceTrapObject OBJECT IDENTIFIER ::= { interface 10  }

ifpReceiveManyErrorPacket NOTIFICATION-TYPE
    OBJECTS      { interfaceIndex }
    STATUS          current
    DESCRIPTION
        "Receive many CRC error packets on the interface."
    ::= { interfaceTrapObject 1 }



        -- Sub Module: MANAGEMENTIP
managementIp                OBJECT IDENTIFIER    ::= { management 1 }

managementIpTable         OBJECT-TYPE
    SYNTAX          SEQUENCE OF ManagementIpEntry
    MAX-ACCESS      not-accessible
    STATUS          current
    DESCRIPTION
        "table of management ip entry."
    ::= { managementIp 1 }
            
managementIpEntry         OBJECT-TYPE
    SYNTAX          ManagementIpEntry
    MAX-ACCESS      not-accessible
    STATUS          current
    DESCRIPTION
        "interface entry        "
    INDEX     { managementIpSlot}
    ::= { managementIpTable 1 }
            
ManagementIpEntry    ::=
    SEQUENCE
    {
        managementIpSlot
            Integer32,
        managementIPv4Addr
            OCTET STRING,
        managementRowStatus
            RowStatus
     }

managementIpSlot         OBJECT-TYPE
    SYNTAX          Integer32 (0..65535)
    MAX-ACCESS      not-accessible
    STATUS          current
    DESCRIPTION        
        "Management ip slot."
    ::= { managementIpEntry 1 }
            
            
managementIPv4Addr         OBJECT-TYPE
    SYNTAX          OCTET STRING (SIZE(0..256))
    MAX-ACCESS      read-write
    STATUS          current
    DESCRIPTION        
        "IP addresses with masklen. The format is like 'xxx.xxx.xxx.xxx/xx'."
    ::= { managementIpEntry 2 }

managementRowStatus         OBJECT-TYPE
    SYNTAX          RowStatus
    MAX-ACCESS      read-create
    STATUS          current
    DESCRIPTION        
        "The status of management IP row.Now only realize Create, Destroy and Active."
    ::= { managementIpEntry 3 }            
    
    
managementGateway               OBJECT IDENTIFIER    ::= { management 3 }
managementIpGatewayTable         OBJECT-TYPE
    SYNTAX          SEQUENCE OF ManagementIpGatewayEntry
    MAX-ACCESS      not-accessible
    STATUS          current
    DESCRIPTION
        "table of management ip gateway entry."
    ::= { managementGateway 1 }
            
managementIpGatewayEntry         OBJECT-TYPE
    SYNTAX          ManagementIpGatewayEntry
    MAX-ACCESS      not-accessible
    STATUS          current
    DESCRIPTION
        "management ip Gateway entry."
    INDEX     { managementIpGatewaySlot, managementIpGateway }
    ::= { managementIpGatewayTable 1 }
            
ManagementIpGatewayEntry    ::=
    SEQUENCE
    {
        managementIpGatewaySlot
            Integer32,
         managementIpGateway
            IpAddress,
        managementIpGatewayStatus 
            RowStatus 
     }

managementIpGatewaySlot         OBJECT-TYPE
    SYNTAX          Integer32 (0..65535)
    MAX-ACCESS      not-accessible
    STATUS          current
    DESCRIPTION        
        "Management ip gateway slot."
    ::= { managementIpGatewayEntry 1 }
    
managementIpGateway         OBJECT-TYPE
    SYNTAX          IpAddress
    MAX-ACCESS      not-accessible
    STATUS          current
    DESCRIPTION        
        "Management ip gateway."
    ::= { managementIpGatewayEntry 2 }
                
managementIpGatewayStatus         OBJECT-TYPE
    SYNTAX          RowStatus
    MAX-ACCESS      read-create
    STATUS          current
    DESCRIPTION        
        "The status of this conceptual row.Now only realize CreateAndGo 
        and Destroy and Active.
        1 means Active
        4 means CreateAndGo
        6 means Destroy"
    ::= { managementIpGatewayEntry 3 }
        


-- Sub Module: MVR


mvrGlobalStatus         OBJECT-TYPE
    SYNTAX          INTEGER
    {
      enable    (1),
      disable    (2)
    }
    MAX-ACCESS      read-write
    STATUS          current
    DESCRIPTION
        " Enable/Disable MVR on the switch."
    ::= { mvr 1 }
        
mvrGlobalGroupTable         OBJECT-TYPE
    SYNTAX          SEQUENCE OF MvrGlobalGroupEntry
    MAX-ACCESS      not-accessible
    STATUS          current
    DESCRIPTION
        "table of MVR multicast group."
    ::= { mvr 2 }
            
mvrGlobalGroupEntry         OBJECT-TYPE
    SYNTAX          MvrGlobalGroupEntry
    MAX-ACCESS      not-accessible
    STATUS          current
    DESCRIPTION
        "MVR multicast group entry."
    INDEX     { mvrGlobalGroup}
    ::= { mvrGlobalGroupTable 1 }
            
MvrGlobalGroupEntry    ::=
    SEQUENCE
    {
        mvrGlobalGroup
            IpAddress,
        mvrGlobalGroupRowStatus 
            RowStatus 
    }
        
mvrGlobalGroup         OBJECT-TYPE
    SYNTAX          IpAddress
    MAX-ACCESS      not-accessible
    STATUS          current
    DESCRIPTION
        "MVR multicast group."
    ::= { mvrGlobalGroupEntry 1 }     

mvrGlobalGroupRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { mvrGlobalGroupEntry 2 }   

mvrSourceVlan         OBJECT-TYPE
    SYNTAX          INTEGER(0..4094)
    MAX-ACCESS      read-write
    STATUS          current
    DESCRIPTION
        " Configure a source VLAN for MVR; 0 unset source vlan."
    ::= { mvr 3 }

mvrSourceIP         OBJECT-TYPE
    SYNTAX          IpAddress
    MAX-ACCESS      read-write
    STATUS          current
    DESCRIPTION
        " Mvr Source IP address. Use 0.0.0.0 to restore the default value."
    ::= { mvr 4 }

mvrSourcePortTable         OBJECT-TYPE
    SYNTAX          SEQUENCE OF MvrSourcePortEntry
    MAX-ACCESS      not-accessible
    STATUS          current
    DESCRIPTION
        "table of MVR source port."
    ::= { mvr 5 }
            
mvrSourcePortEntry         OBJECT-TYPE
    SYNTAX          MvrSourcePortEntry
    MAX-ACCESS      not-accessible
    STATUS          current
    DESCRIPTION
        "MVR source port entry."
    INDEX     { mvrSourcePortIfindex}
    ::= { mvrSourcePortTable 1 }
            
        MvrSourcePortEntry    ::=
    SEQUENCE
            {
                mvrSourcePortIfindex
                    Integer32,
                mvrSourcePortRowStatus 
                    RowStatus 
            }
        
mvrSourcePortIfindex         OBJECT-TYPE
    SYNTAX          Integer32 (0..65535)
    MAX-ACCESS      not-accessible
    STATUS          current
    DESCRIPTION
        "MVR source port ifindex."
    ::= { mvrSourcePortEntry 1 }     

mvrSourcePortRowStatus         OBJECT-TYPE
    SYNTAX          RowStatus
    MAX-ACCESS      read-create
    STATUS          current
    DESCRIPTION
        "The status of this conceptual row.Now only realize CreateAndGo and Destroy and Active.
        1 means Active
        4 means CreateAndGo
        6 means Destroy"
    ::= { mvrSourcePortEntry 2 }  

mvrRcvPortTable         OBJECT-TYPE
    SYNTAX          SEQUENCE OF MvrRcvPortEntry
    MAX-ACCESS      not-accessible
    STATUS          current
    DESCRIPTION
        "table of MVR receive port."
    ::= { mvr 6 }
            
mvrRcvPortEntry         OBJECT-TYPE
    SYNTAX          MvrRcvPortEntry
    MAX-ACCESS      not-accessible
    STATUS          current
    DESCRIPTION
        "MVR receive port entry."
    INDEX     { mvrRcvPortIfindex,mvrRcvVlanId}
    ::= { mvrRcvPortTable 1 }
            
MvrRcvPortEntry    ::=
    SEQUENCE
    {
        mvrRcvPortIfindex
            Integer32,
        mvrRcvVlanId
            Integer32,
        mvrRcvPortRowStatus 
            RowStatus 
    }
        
mvrRcvPortIfindex         OBJECT-TYPE
    SYNTAX          Integer32 (0..65535)
    MAX-ACCESS      not-accessible
    STATUS          current
    DESCRIPTION
        "MVR receive port ifindex."
    ::= { mvrRcvPortEntry 1 }     

mvrRcvVlanId         OBJECT-TYPE
    SYNTAX          Integer32 (0..4094)
    MAX-ACCESS      not-accessible
    STATUS          current
    DESCRIPTION
        "MVR receive vlan id."
    ::= { mvrRcvPortEntry 2 }  
            
mvrRcvPortRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { mvrRcvPortEntry 3 }  
    
mvrIPMcastRouting         OBJECT-TYPE
    SYNTAX          INTEGER
    {
      enable    (1),
      disable    (2)
    }
    MAX-ACCESS      read-write
    STATUS          current
    DESCRIPTION
        " Enable/Disable IP Multicast-routing on the switch."
    ::= { mvr 7 }    

-- Sub Module: ERPS


-- ==================================================================
--
-- =====================object definition begin======================
--
-- ==================================================================
        

erpsDomainTable         OBJECT-TYPE
    SYNTAX          SEQUENCE OF ErpsDomainEntry
    MAX-ACCESS      not-accessible
    STATUS          current
    DESCRIPTION
        "table of domain entry."
    ::= { erps 2 }
            
erpsDomainEntry         OBJECT-TYPE
    SYNTAX          ErpsDomainEntry
    MAX-ACCESS      not-accessible
    STATUS          current
    DESCRIPTION
        "domain entry."
    INDEX     { domainIndex}
    ::= { erpsDomainTable 1 }
            
ErpsDomainEntry    ::=
    SEQUENCE
    {
        domainIndex
            Integer32,
        domainName
            OCTET STRING,
        domainHellotime
            Integer32,
        domainFailtime
            Integer32,
        domainPrimaryControlVlan
            Integer32,
        domainSubControlVlan
            Integer32,
        domainEnable
            INTEGER,
        domainInstance
            Integer32,            
        domainRowStatus
            RowStatus
    }

domainIndex         OBJECT-TYPE
    SYNTAX          Integer32 (1..255)
    MAX-ACCESS      not-accessible
    STATUS          current
    DESCRIPTION
        "Domain index.Range 1~255."
    ::= { erpsDomainEntry 1 }
            
domainName         OBJECT-TYPE
    SYNTAX          OCTET STRING (SIZE (0..15))
    MAX-ACCESS      read-create
    STATUS          current
    DESCRIPTION        
        "Domain name.Range 1~16.0 means default domain name"
    ::= { erpsDomainEntry 2 }
    
domainHellotime         OBJECT-TYPE
    SYNTAX          Integer32
    MAX-ACCESS      read-write
    STATUS          current
    DESCRIPTION
        "Domain hello timer interval,the range is 1~~15.The default value is 1."
    ::= { erpsDomainEntry 3 }

domainFailtime         OBJECT-TYPE
    SYNTAX          Integer32
    MAX-ACCESS      read-write
    STATUS          current
    DESCRIPTION
         "Domain fail timer interval,the range is 3~~45.The default value is 3."
    ::= { erpsDomainEntry 4 }

domainPrimaryControlVlan         OBJECT-TYPE
    SYNTAX          Integer32
    MAX-ACCESS      read-write
    STATUS          current
    DESCRIPTION
        "Domain primary control vlan ,the range is 2~~4094."
    ::= { erpsDomainEntry 5 }

domainSubControlVlan         OBJECT-TYPE
    SYNTAX          Integer32
    MAX-ACCESS      read-write
    STATUS          current
    DESCRIPTION
        "Domain sub control vlan ,the range is 2~~4094."
    ::= { erpsDomainEntry 6 }

domainEnable         OBJECT-TYPE
    SYNTAX          INTEGER
    {
        enable(1),
        disable(2)
    }
    MAX-ACCESS      read-write
    STATUS          current
    DESCRIPTION
        "Enable or disable the domain. Enable(1),Disable(2).
        Only support set operation."
    ::= { erpsDomainEntry 7 }

domainInstance         OBJECT-TYPE
    SYNTAX          Integer32
    MAX-ACCESS      read-write
    STATUS          current
    DESCRIPTION
        "Set or unset the instance which the domain bound.
         the range is 0~~4094.  0 is the default value"
    ::= { erpsDomainEntry 8 }

domainRowStatus         OBJECT-TYPE
    SYNTAX          RowStatus
    MAX-ACCESS      read-create
    STATUS          current
    DESCRIPTION
        "The status of this conceptual row.Now only realize Destroy and Active."
    ::= { erpsDomainEntry 9 }

--erpsDomainStatsTable         OBJECT-TYPE
--    SYNTAX          SEQUENCE OF ErpsDomainStatsEntry
--    MAX-ACCESS      not-accessible
--    STATUS          current
--    DESCRIPTION
--        "table of domain statistics entry."
--    ::= { erps 3 }
--
--erpsDomainStatsEntry         OBJECT-TYPE
--    SYNTAX          ErpsDomainStatsEntry
--    MAX-ACCESS      not-accessible
--    STATUS          current
--    DESCRIPTION
--        "Domain statistics entry."
--    INDEX     { domainStatsIndex}
--    ::= { erpsDomainStatsTable 1 }
--
--ErpsDomainStatsEntry    ::=
--    SEQUENCE
--    {
--        domainStatsIndex
--            Integer32,
--        domainStatsTotalSendPackets
--            Unsigned32,
--        domainStatsHelloSendPackets
--            Unsigned32,
--        domainStatsRingUpFlushFdbSendPackets
--            Unsigned32,
--        domainStatsRingDownFlushFdbSendPackets
--            Unsigned32,
--        domainStatsLinkDownSendPackets
--            Unsigned32,
--        domainStatsAskStateSendPackets
--            Unsigned32,
--        domainStatsTotalRecPackets
--            Unsigned32,
--        domainStatsHelloRecPackets
--            Unsigned32,
--        domainStatsRingUpFlushFdbRecPackets
--            Unsigned32,
--        domainStatsRingDownFlushFdbRecPackets
--            Unsigned32,
--        domainStatsLinkDownRecPackets
--            Unsigned32,
--        domainStatsAskStateRecPackets
--            Unsigned32,
--        domainStatsClearPackets
--            Integer32
--     }
--
--domainStatsIndex         OBJECT-TYPE
--    SYNTAX          Integer32 (0..65535)
--    MAX-ACCESS      not-accessible
--    STATUS          current
--    DESCRIPTION
--        "Domain statistics."
--    ::= { erpsDomainStatsEntry 1 }
--
--domainStatsTotalSendPackets         OBJECT-TYPE
--    SYNTAX          Unsigned32
--    MAX-ACCESS      read-only
--    STATUS          current
--    DESCRIPTION
--        "Domain statistics."
--    ::= { erpsDomainStatsEntry 2 }
--
--domainStatsHelloSendPackets         OBJECT-TYPE
--    SYNTAX          Unsigned32
--    MAX-ACCESS      read-only
--    STATUS          current
--    DESCRIPTION
--        "Domain statistics."
--    ::= { erpsDomainStatsEntry 3 }
--
--domainStatsRingUpFlushFdbSendPackets         OBJECT-TYPE
--    SYNTAX          Unsigned32
--    MAX-ACCESS      read-only
--    STATUS          current
--    DESCRIPTION
--        "Domain statistics."
--    ::= { erpsDomainStatsEntry 4 }
--
--domainStatsRingDownFlushFdbSendPackets         OBJECT-TYPE
--    SYNTAX          Unsigned32
--    MAX-ACCESS      read-only
--    STATUS          current
--    DESCRIPTION
--        "Domain statistics."
--    ::= { erpsDomainStatsEntry 5 }
--
--domainStatsLinkDownSendPackets         OBJECT-TYPE
--    SYNTAX          Unsigned32
--    MAX-ACCESS      read-only
--    STATUS          current
--    DESCRIPTION
--        "Domain statistics."
--    ::= { erpsDomainStatsEntry 6 }
--
--domainStatsAskStateSendPackets         OBJECT-TYPE
--    SYNTAX          Unsigned32
--    MAX-ACCESS      read-only
--    STATUS          current
--    DESCRIPTION
--        "Domain statistics."
--    ::= { erpsDomainStatsEntry 7 }
--
--domainStatsTotalRecPackets         OBJECT-TYPE
--    SYNTAX          Unsigned32
--    MAX-ACCESS      read-only
--    STATUS          current
--    DESCRIPTION
--        "Domain statistics."
--    ::= { erpsDomainStatsEntry 8 }
--
--domainStatsHelloRecPackets         OBJECT-TYPE
--    SYNTAX          Unsigned32
--    MAX-ACCESS      read-only
--    STATUS          current
--    DESCRIPTION
--        "Domain statistics."
--    ::= { erpsDomainStatsEntry 9 }
--
--domainStatsRingUpFlushFdbRecPackets         OBJECT-TYPE
--    SYNTAX          Unsigned32
--    MAX-ACCESS      read-only
--    STATUS          current
--    DESCRIPTION
--        "Domain statistics."
--    ::= { erpsDomainStatsEntry 10 }
--
--domainStatsRingDownFlushFdbRecPackets         OBJECT-TYPE
--    SYNTAX          Unsigned32
--    MAX-ACCESS      read-only
--    STATUS          current
--    DESCRIPTION
--        "Domain statistics."
--    ::= { erpsDomainStatsEntry 11 }
--
--domainStatsLinkDownRecPackets         OBJECT-TYPE
--    SYNTAX          Unsigned32
--    MAX-ACCESS      read-only
--    STATUS          current
--    DESCRIPTION        "Domain statistics."
--    ::= { erpsDomainStatsEntry 12 }
--
--domainStatsAskStateRecPackets         OBJECT-TYPE
--    SYNTAX          Unsigned32
--    MAX-ACCESS      read-only
--    STATUS          current
--    DESCRIPTION
--        "Domain statistics."
--    ::= { erpsDomainStatsEntry 13 }
--
--domainStatsClearPackets         OBJECT-TYPE
--    SYNTAX          Integer32
--    MAX-ACCESS      read-write
--    STATUS          current
--    DESCRIPTION
--        "Clear domain statistics and the set number is 1."
--    ::= { erpsDomainStatsEntry 14 }

erpsRingTable         OBJECT-TYPE
    SYNTAX          SEQUENCE OF ErpsRingEntry
    MAX-ACCESS      not-accessible
    STATUS          current
    DESCRIPTION
        "table of ring entry."
    ::= { erps 4 }

erpsRingEntry         OBJECT-TYPE
    SYNTAX          ErpsRingEntry
    MAX-ACCESS      not-accessible
    STATUS          current
    DESCRIPTION
        "domain entry        "
    INDEX     { ringIndex}
    ::= { erpsRingTable 1 }

ErpsRingEntry    ::=
    SEQUENCE
    {
        ringIndex
            Integer32,
        ringLevel
            INTEGER,
        ringmode
            INTEGER,
        ringEdgemode
            INTEGER,
        ringPrimaryIf
            OCTET STRING,
        ringSecondaryIf
            OCTET STRING,
        ringEdgeIf
            OCTET STRING,
        ringCommonIf
            OCTET STRING,
        ringSrpt
            INTEGER,
        ringEnable
            INTEGER,
        ringRowStatus
            RowStatus,
        ringStatus         
            INTEGER  
    }

ringIndex         OBJECT-TYPE
    SYNTAX          Integer32 (1..255)
    MAX-ACCESS      not-accessible
    STATUS          current
    DESCRIPTION
        "Ring index.Range 1~255."
    ::= { erpsRingEntry 1 }

ringLevel         OBJECT-TYPE
    SYNTAX          INTEGER
    {
        primary(0),
        sub(1)
    }
    MAX-ACCESS      read-create
    STATUS          current
    DESCRIPTION
        "Create ring with level.primary:0 sub:1."
    ::= { erpsRingEntry 2 }

ringmode         OBJECT-TYPE
    SYNTAX          INTEGER
            {
                unknow(0),
                master(1),
                transit(2),
                vpls(3)
            }
    MAX-ACCESS      read-create
    STATUS          current
    DESCRIPTION
        "Set ring mode.unknow:0 master:1 transit:2 vpls:3."
    ::= { erpsRingEntry 3 }

ringEdgemode         OBJECT-TYPE
    SYNTAX          INTEGER
            {
                unknow(0),
                edge(1),
                assistantedge(2)
            }
    MAX-ACCESS      read-create
    STATUS          current
    DESCRIPTION
        "Set ring mode.unknow:0 edge:1 assistantedge:2."
    ::= { erpsRingEntry 4 }

ringPrimaryIf         OBJECT-TYPE
    SYNTAX          OCTET STRING (SIZE(0..256))
    MAX-ACCESS      read-create
    STATUS          current
    DESCRIPTION
        "Set ring primary port."
    ::= { erpsRingEntry 5 }

ringSecondaryIf         OBJECT-TYPE
    SYNTAX          OCTET STRING (SIZE(0..256))
    MAX-ACCESS      read-create
    STATUS          current
    DESCRIPTION
        "Set ring primary port."
    ::= { erpsRingEntry 6 }

ringEdgeIf         OBJECT-TYPE
    SYNTAX          OCTET STRING (SIZE(0..256))
    MAX-ACCESS      read-create
    STATUS          current
    DESCRIPTION
        "Set ring edge port."
    ::= { erpsRingEntry 7 }

ringCommonIf         OBJECT-TYPE
    SYNTAX          OCTET STRING (SIZE(0..256))
    MAX-ACCESS      read-create
    STATUS          current
    DESCRIPTION
        "Set ring common port."
    ::= { erpsRingEntry 8 }

ringSrpt         OBJECT-TYPE
    SYNTAX          INTEGER
    {
        enable(1),
        disable(2)
    }
    MAX-ACCESS      read-create
    STATUS          current
    DESCRIPTION
         "Set ring srpt. enable:1 disable:2"
    ::= { erpsRingEntry 9 }

ringEnable         OBJECT-TYPE
    SYNTAX          INTEGER
    {
        enable(1),
        disable(2)
    }
    MAX-ACCESS      read-create
    STATUS          current
    DESCRIPTION
        "Enable ring. enable:1 disable:2"
    ::= { erpsRingEntry 10 }

ringRowStatus         OBJECT-TYPE
    SYNTAX          RowStatus
    MAX-ACCESS      read-create
    STATUS          current
    DESCRIPTION
        "The status of this conceptual row.Now only realize Destroy and Active."
    ::= { erpsRingEntry 11 }

ringStatus         OBJECT-TYPE
    SYNTAX          INTEGER
    {
        idel(0),
        complete(1),
        failed(2),
        linkup(3),
        linkdown(4),
        preforwording(5),
        init(6)
    }
    MAX-ACCESS      read-only
    STATUS          current
    DESCRIPTION        
        "The status of this ring. idel(0), complete(1),
        failed(2), linkup(3), linkdown(4),
        preforwording(5), init(6)."
    ::= { erpsRingEntry 12 }

erpsRingStatsTable         OBJECT-TYPE
    SYNTAX          SEQUENCE OF ErpsRingStatsEntry
    MAX-ACCESS      not-accessible
    STATUS          current
    DESCRIPTION
        "table of ring statistics entry."
    ::= { erps 5 }

erpsRingStatsEntry         OBJECT-TYPE
    SYNTAX          ErpsRingStatsEntry
    MAX-ACCESS      not-accessible
    STATUS          current
    DESCRIPTION
        "ring statistics entry."
    INDEX     { ringStatsIndex}
    ::= { erpsRingStatsTable 1 }

ErpsRingStatsEntry    ::=
    SEQUENCE
    {
        ringStatsIndex
            Integer32,
        ringStatsTotalSendPackets
            Unsigned32,
        ringStatsHelloSendPackets
            Unsigned32,
        ringStatsRingUpFlushFdbSendPackets
            Unsigned32,
        ringStatsRingDownFlushFdbSendPackets
            Unsigned32,
        ringStatsLinkDownSendPackets
            Unsigned32,
        ringStatsEdgeHelloSendPackets
            Unsigned32,
        ringStatsMajorFaultSendPackets
            Unsigned32,
        ringStatsTotalRecPackets
            Unsigned32,
        ringStatsHelloRecPackets
            Unsigned32,
        ringStatsRingUpFlushFdbRecPackets
            Unsigned32,
        ringStatsRingDownFlushFdbRecPackets
            Unsigned32,
        ringStatsLinkDownRecPackets
            Unsigned32,
        ringStatsEdgeHelloRecPackets
            Unsigned32,
        ringStatsMajorFaultRecPackets
            Unsigned32,
        ringStatsClearPackets
            Integer32
    }

ringStatsIndex         OBJECT-TYPE
    SYNTAX          Integer32 (0..65535)
    MAX-ACCESS      not-accessible
    STATUS          current
    DESCRIPTION
        "Ring statistics."
    ::= { erpsRingStatsEntry 1 }

ringStatsTotalSendPackets         OBJECT-TYPE
    SYNTAX          Unsigned32
    MAX-ACCESS      read-only
    STATUS          current
    DESCRIPTION
        "Ring statistics."
    ::= { erpsRingStatsEntry 2 }

ringStatsHelloSendPackets         OBJECT-TYPE
    SYNTAX          Unsigned32
    MAX-ACCESS      read-only
    STATUS          current
    DESCRIPTION
        "Ring statistics."
    ::= { erpsRingStatsEntry 3 }

ringStatsRingUpFlushFdbSendPackets         OBJECT-TYPE
    SYNTAX          Unsigned32
    MAX-ACCESS      read-only
    STATUS          current
    DESCRIPTION
        "Ring statistics."
    ::= { erpsRingStatsEntry 4 }

ringStatsRingDownFlushFdbSendPackets         OBJECT-TYPE
    SYNTAX          Unsigned32
    MAX-ACCESS      read-only
    STATUS          current
    DESCRIPTION
        "Ring statistics."
    ::= { erpsRingStatsEntry 5 }

ringStatsLinkDownSendPackets         OBJECT-TYPE
    SYNTAX          Unsigned32
    MAX-ACCESS      read-only
    STATUS          current
    DESCRIPTION
        "Ring statistics."
    ::= { erpsRingStatsEntry 6 }

ringStatsEdgeHelloSendPackets         OBJECT-TYPE
    SYNTAX          Unsigned32
    MAX-ACCESS      read-only
    STATUS          current
    DESCRIPTION        "Ring statistics."
    ::= { erpsRingStatsEntry 7 }

ringStatsMajorFaultSendPackets         OBJECT-TYPE
    SYNTAX          Unsigned32
    MAX-ACCESS      read-only
    STATUS          current
    DESCRIPTION
        "Ring statistics."
    ::= { erpsRingStatsEntry 8 }

ringStatsTotalRecPackets         OBJECT-TYPE
    SYNTAX          Unsigned32
    MAX-ACCESS      read-only
    STATUS          current
    DESCRIPTION
        "Ring statistics."
    ::= { erpsRingStatsEntry 9 }

ringStatsHelloRecPackets         OBJECT-TYPE
    SYNTAX          Unsigned32
    MAX-ACCESS      read-only
    STATUS          current
    DESCRIPTION
        "Ring statistics."
    ::= { erpsRingStatsEntry 10 }

ringStatsRingUpFlushFdbRecPackets         OBJECT-TYPE
    SYNTAX          Unsigned32
    MAX-ACCESS      read-only
    STATUS          current
    DESCRIPTION        "Ring statistics."
    ::= { erpsRingStatsEntry 11 }

ringStatsRingDownFlushFdbRecPackets         OBJECT-TYPE
    SYNTAX          Unsigned32
    MAX-ACCESS      read-only
    STATUS          current
    DESCRIPTION
        "Ring statistics."
    ::= { erpsRingStatsEntry 12 }

ringStatsLinkDownRecPackets         OBJECT-TYPE
    SYNTAX          Unsigned32
    MAX-ACCESS      read-only
    STATUS          current
    DESCRIPTION
        "Ring statistics."
    ::= { erpsRingStatsEntry 13 }

ringStatsEdgeHelloRecPackets         OBJECT-TYPE
    SYNTAX          Unsigned32
    MAX-ACCESS      read-only
    STATUS          current
    DESCRIPTION
        "Ring statistics."
    ::= { erpsRingStatsEntry 14 }

ringStatsMajorFaultRecPackets         OBJECT-TYPE
    SYNTAX          Unsigned32
    MAX-ACCESS      read-only
    STATUS          current
    DESCRIPTION
        "Ring statistics."
    ::= { erpsRingStatsEntry 15 }

ringStatsClearPackets         OBJECT-TYPE
    SYNTAX          Integer32
    MAX-ACCESS      read-write
    STATUS          current
    DESCRIPTION
        "Clear ring statistics and the set number is 1."
    ::= { erpsRingStatsEntry 16 }

erpsTrapObject OBJECT IDENTIFIER ::= {   erps 10  }

erpsLinkSwitch NOTIFICATION-TYPE
    OBJECTS      { ringStatus }
    STATUS          current
    DESCRIPTION
        "Erps link change notification."
    ::= { erpsTrapObject 1 }

-- Sub Module: PREFIXLIST



-- prefix list type - permit or deny
PrefixListType    ::= TEXTUAL-CONVENTION
    STATUS          current
    DESCRIPTION
        "prefix list type, permit or deny."
    SYNTAX          INTEGER
            {
                deny(1),
                permit(2)
            }

-- prefix list clear value
PrefixListClearValue ::= TEXTUAL-CONVENTION
    STATUS          current
    DESCRIPTION
        "prefix list value: 1."
    SYNTAX          INTEGER
        {
            clear(1)
        }

-- prefix list sequence-use type
--        PrefixListSeqUseType    ::= TEXTUAL-CONVENTION
--    STATUS          current
--    DESCRIPTION
--        "prefix list    SEQUENCE-number use type        "
--    SYNTAX          INTEGER
--            {
--                useSeq(1),
--                noUseSeq(2)
--            }

--
-- Node of prefixListSeqNumUse
--
--prefixListSeqNumUse         OBJECT-TYPE
--    SYNTAX          PrefixListSeqUseType
--    MAX-ACCESS      read-write
--    STATUS          current
--    DESCRIPTION
--        "config prefix list    SEQUENCE number use        "
--    ::= { prefixList 100 }
--
--
--
-- Nodes of prefixList entry table
--
prefixListTable         OBJECT-TYPE
    SYNTAX          SEQUENCE OF PrefixListEntry
    MAX-ACCESS      not-accessible
    STATUS          current
    DESCRIPTION
        "table of  prefix list entry."
    ::= { prefixList 1 }

prefixListEntry         OBJECT-TYPE
    SYNTAX          PrefixListEntry
    MAX-ACCESS      not-accessible
    STATUS          current
    DESCRIPTION
        "ip prefix list entry."
    INDEX  { prefixListIpAddressType, prefixListIndex}
    ::= { prefixListTable 1 }

PrefixListEntry    ::=
    SEQUENCE
    {
        prefixListIpAddressType
            InetAddressType,
        prefixListIndex
            Unsigned32,
        prefixListName
            OCTET STRING,
        prefixListDescription
            OCTET STRING,
        prefixListRowStatus
            RowStatus
     }
prefixListIpAddressType         OBJECT-TYPE
    SYNTAX          InetAddressType
    MAX-ACCESS      not-accessible
    STATUS          current
    DESCRIPTION
        "The ip type:ip or ipv6."
    ::= { prefixListEntry 1 }

prefixListIndex         OBJECT-TYPE
    SYNTAX          Unsigned32 (0..4294967295)
    MAX-ACCESS      read-only
    STATUS          current
    DESCRIPTION
        "prefix list index."
    ::= { prefixListEntry 2 }

prefixListName         OBJECT-TYPE
    SYNTAX          OCTET STRING (SIZE(0..20))
    MAX-ACCESS      read-create
    STATUS          current
    DESCRIPTION
        "prefix list name, siez (1-20)."
    ::= { prefixListEntry 3 }

        prefixListDescription OBJECT-TYPE
    SYNTAX          OCTET STRING (SIZE(0..80))
    MAX-ACCESS      read-create
    STATUS          current
    DESCRIPTION
                "The description of the prefix list, size (0-80)"
    ::= { prefixListEntry 4 }

prefixListRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { prefixListEntry 5 }   

--
-- Nodes of prefixListRule entry table
--
prefixListRuleTable         OBJECT-TYPE
    SYNTAX          SEQUENCE OF PrefixListRuleEntry
    MAX-ACCESS      not-accessible
    STATUS          current
    DESCRIPTION
        "table of  prefix list entry."
    ::= { prefixList 2 }
            
prefixListRuleEntry    OBJECT-TYPE
    SYNTAX          PrefixListRuleEntry
    MAX-ACCESS      not-accessible
    STATUS          current
    DESCRIPTION
        "ip prefix list entry."
    INDEX   { prefixListRuleIpAddressType, prefixListRuleIndex, prefixListRuleSeq}
    ::= { prefixListRuleTable 1 }
            
PrefixListRuleEntry    ::=
    SEQUENCE
    {
        prefixListRuleIpAddressType 
            InetAddressType,
        prefixListRuleIndex
            Unsigned32,
        prefixListRuleSeq
            Unsigned32,
        prefixListRuleIpAddress   
            InetAddress,
        prefixListRuleMaskLen   
            Integer32,
        prefixListRuleType
            PrefixListType,
        prefixListRuleGe
            Integer32,
        prefixListRuleLe
            Integer32,    
        prefixListRuleRowStatus 
            RowStatus 
     }
prefixListRuleIpAddressType         OBJECT-TYPE
    SYNTAX          InetAddressType
    MAX-ACCESS      not-accessible
    STATUS          current
    DESCRIPTION
        "The ip type:ip or ipv6."
    ::= { prefixListRuleEntry 1 } 
            
prefixListRuleIndex         OBJECT-TYPE
    SYNTAX          Unsigned32 (0..4294967295) 
    MAX-ACCESS      not-accessible
    STATUS          current
    DESCRIPTION
        "prefix list index."
    ::= { prefixListRuleEntry 2 }
            
prefixListRuleSeq         OBJECT-TYPE
    SYNTAX          Unsigned32 (0..4294967295) 
    MAX-ACCESS      not-accessible
    STATUS          current
    DESCRIPTION
                "The sequence number of prefix list entry."
    ::= { prefixListRuleEntry 3 }            
                       
prefixListRuleIpAddress         OBJECT-TYPE
    SYNTAX          InetAddress
    MAX-ACCESS      read-create
    STATUS          current
    DESCRIPTION
        "ip or ipv6 address."
    ::= { prefixListRuleEntry 4 }
            
prefixListRuleMaskLen         OBJECT-TYPE
    SYNTAX          Integer32 (0..32)
    MAX-ACCESS      read-create
    STATUS          current
    DESCRIPTION
        "The ip address mask length."
    ::= { prefixListRuleEntry 5 }

prefixListRuleType         OBJECT-TYPE
    SYNTAX          PrefixListType
    MAX-ACCESS      read-create
    STATUS          current
    DESCRIPTION
        "The type of prefix list: permit or deny."
    ::= { prefixListRuleEntry 6 }   
                     
prefixListRuleGe         OBJECT-TYPE
    SYNTAX          Integer32 (0..32)
    MAX-ACCESS      read-create
    STATUS          current
    DESCRIPTION
        "The Minimum prefix length."
    ::= { prefixListRuleEntry 7 }

prefixListRuleLe         OBJECT-TYPE
    SYNTAX          Integer32 (0..32)
    MAX-ACCESS      read-create
    STATUS          current
    DESCRIPTION
        "The maximum prefix length."
    ::= { prefixListRuleEntry 8 } 
              
prefixListRuleRowStatus         OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { prefixListRuleEntry 9 }   


--
-- Nodes of prefixListClear
--         
prefixListClearTable         OBJECT-TYPE
    SYNTAX          SEQUENCE OF PrefixListClearEntry
    MAX-ACCESS      not-accessible
    STATUS          current
    DESCRIPTION
        "table of prefix list entry."
    ::= { prefixList 3 }
            
prefixListClearEntry   OBJECT-TYPE
    SYNTAX          PrefixListClearEntry
    MAX-ACCESS      not-accessible
    STATUS          current
    DESCRIPTION
        "ip prefix list clear entry."
    INDEX  { prefixListClearIpAddressType , prefixListClearIndex }
    ::= { prefixListClearTable 1 }   

PrefixListClearEntry    ::=
    SEQUENCE
    {
        prefixListClearIpAddressType 
            InetAddressType,
        prefixListClearIndex
            Integer32,
        prefixListClear   
            PrefixListClearValue
     }
prefixListClearIpAddressType         OBJECT-TYPE
    SYNTAX          InetAddressType
    MAX-ACCESS      not-accessible
    STATUS          current
    DESCRIPTION
        "The Clear type, ip or ipv6."
    ::= { prefixListClearEntry 1 } 
            
prefixListClearIndex  OBJECT-TYPE
    SYNTAX          Integer32 (0..65535)
    MAX-ACCESS      not-accessible
    STATUS          current
    DESCRIPTION
        "prefix list index."
    ::= { prefixListClearEntry 2 }         

prefixListClear       OBJECT-TYPE
    SYNTAX          PrefixListClearValue
    MAX-ACCESS      read-create
    STATUS          current
    DESCRIPTION
        "The prefix list clear value : the only valid value is 1."
    ::= { prefixListClearEntry 3 }


--
-- Nodes of prefixListDetail entry table
--
prefixListDetailTable         OBJECT-TYPE
    SYNTAX          SEQUENCE OF PrefixListDetailEntry
    MAX-ACCESS      not-accessible
    STATUS          current
    DESCRIPTION
        "table of  prefix list entry."
    ::= { prefixList 4 }
            
prefixListDetailEntry    OBJECT-TYPE
    SYNTAX          PrefixListDetailEntry
    MAX-ACCESS      not-accessible
    STATUS          current
    DESCRIPTION
        "ip prefix list detail entry."
    INDEX   { prefixListDetailIpAddressType, prefixListDetailIndex, prefixListDetailSeq}
    ::= { prefixListDetailTable 1 }
            
PrefixListDetailEntry    ::=
    SEQUENCE
    {
        prefixListDetailIpAddressType 
            InetAddressType,
        prefixListDetailIndex
            Unsigned32,
        prefixListDetailSeq
            Unsigned32,
        prefixListDetailLastOperEntry   
            OCTET STRING,
        prefixLisDetailCount   
            Integer32,
        prefixListDetailRangeEntries
            PrefixListType,
        prefixListDetailSequences
            OCTET STRING,
        prefixListDetailHitCount
            Integer32,    
        prefixListDetailRefcount 
            RowStatus 
     }
prefixListDetailIpAddressType         OBJECT-TYPE
    SYNTAX          InetAddressType
    MAX-ACCESS      not-accessible
    STATUS          current
    DESCRIPTION
        "The ip type:ip or ipv6."
    ::= { prefixListDetailEntry 1 } 
            
prefixListDetailIndex         OBJECT-TYPE
    SYNTAX          Unsigned32 (0..4294967295) 
    MAX-ACCESS      not-accessible
    STATUS          current
    DESCRIPTION
        "prefix list index."
    ::= { prefixListDetailEntry 2 }
            
prefixListDetailSeq         OBJECT-TYPE
    SYNTAX          Unsigned32 (0..4294967295) 
    MAX-ACCESS      not-accessible
    STATUS          current
    DESCRIPTION
        "The sequence number of prefix list entry."
    ::= { prefixListDetailEntry 3 }            
                       
prefixListDetailLastOperEntry         OBJECT-TYPE
    SYNTAX          OCTET STRING
    MAX-ACCESS      read-only
    STATUS          current
    DESCRIPTION
        "Prefix-list with the last deletion/insertion."
    ::= { prefixListDetailEntry 4 }
            
prefixLisDetailCount         OBJECT-TYPE
    SYNTAX          Integer32 (0..32)
    MAX-ACCESS      read-only
    STATUS          current
    DESCRIPTION
        "Prefix-list total Count."
    ::= { prefixListDetailEntry 5 }

prefixListDetailRangeEntries         OBJECT-TYPE
    SYNTAX          PrefixListType
    MAX-ACCESS      read-only
    STATUS          current
    DESCRIPTION
        "Prefix-list range entries."
    ::= { prefixListDetailEntry 6 }   
                     
prefixListDetailSequences         OBJECT-TYPE
    SYNTAX          OCTET STRING
    MAX-ACCESS      read-only
    STATUS          current
    DESCRIPTION
        "Prefix-list Sequences."
    ::= { prefixListDetailEntry 7 }

prefixListDetailHitCount         OBJECT-TYPE
    SYNTAX          Integer32 (0..32)
    MAX-ACCESS      read-only
    STATUS          current
    DESCRIPTION
        "some seq of prefix-list hit count."
    ::= { prefixListDetailEntry 8 } 
              
prefixListDetailRefcount         OBJECT-TYPE
    SYNTAX          RowStatus
    MAX-ACCESS      read-only
    STATUS          current
    DESCRIPTION
        "some seq of prefix-list refcount."
    ::= { prefixListDetailEntry 9 }   

-- Sub Module: IPUNICAST

    
ipUnicastStaticRouteTable OBJECT-TYPE
    SYNTAX          SEQUENCE OF IpUnicastStaticRouteEntry
    MAX-ACCESS      not-accessible
    STATUS          current
    DESCRIPTION
        "table of ip source guard binding entry."
    ::= { ipUnicast 1 }
    
ipUnicastStaticRouteEntry OBJECT-TYPE
    SYNTAX          IpUnicastStaticRouteEntry
    MAX-ACCESS      not-accessible
    STATUS          current
    DESCRIPTION
    "ip source guard binding entry."
    INDEX 
    { 
        ipUnicastStaticRouteVrfId,
        ipUnicastStaticRouteDestIpAddressType, 
        ipUnicastStaticRouteDestIpAddress,
        ipUnicastStaticRouteDestMask,
        ipUnicastStaticRouteGWIpAddressType,
        ipUnicastStaticRouteGWIpAddress
    }
    ::= { ipUnicastStaticRouteTable 1 }
      
IpUnicastStaticRouteEntry    ::=
    SEQUENCE
    {
        ipUnicastStaticRouteVrfId
            Integer32,
        ipUnicastStaticRouteDestIpAddressType
            InetAddressType,
        ipUnicastStaticRouteDestIpAddress
            InetAddress,
        ipUnicastStaticRouteDestMask
            Integer32,
        ipUnicastStaticRouteGWIpAddressType
            InetAddressType,
        ipUnicastStaticRouteGWIpAddress
            InetAddress,
        ipUnicastStaticRouteDistance
            Integer32,
        ipUnicastStaticRouteRowStatus
            RowStatus
    }
ipUnicastStaticRouteVrfId OBJECT-TYPE
    SYNTAX          Integer32 (0..65535)
    MAX-ACCESS      not-accessible
    STATUS          current
    DESCRIPTION 
        "Vrf id the default value is 0."
-- DEFVAL { ipv4 }
    ::= { ipUnicastStaticRouteEntry 1 }
  
ipUnicastStaticRouteDestIpAddressType OBJECT-TYPE
    SYNTAX          InetAddressType
    MAX-ACCESS      not-accessible
    STATUS          current
    DESCRIPTION 
        "IP addresses type (IPv4 or IPv6)."
-- DEFVAL { ipv4 }
    ::= { ipUnicastStaticRouteEntry 2 }

ipUnicastStaticRouteDestIpAddress OBJECT-TYPE
    SYNTAX          InetAddress
    MAX-ACCESS      not-accessible
    STATUS          current
    DESCRIPTION 
        "IP destination prefix."
    ::= { ipUnicastStaticRouteEntry 3 }

ipUnicastStaticRouteDestMask OBJECT-TYPE
    SYNTAX          Integer32(0..32)
    MAX-ACCESS      not-accessible
    STATUS          current
    DESCRIPTION 
        "DIP destination prefix mask."
    ::= { ipUnicastStaticRouteEntry 4 }
  
ipUnicastStaticRouteGWIpAddressType OBJECT-TYPE
    SYNTAX          InetAddressType
    MAX-ACCESS      not-accessible
    STATUS          current
    DESCRIPTION 
        "IP addresses type (IPv4 or IPv6)."
-- DEFVAL { ipv4 }
    ::= { ipUnicastStaticRouteEntry 5 }

ipUnicastStaticRouteGWIpAddress OBJECT-TYPE
    SYNTAX          InetAddress
    MAX-ACCESS      not-accessible
    STATUS          current
    DESCRIPTION 
        "IP gateway address."
    ::= { ipUnicastStaticRouteEntry 6 }
  
ipUnicastStaticRouteDistance OBJECT-TYPE
    SYNTAX          Integer32(1..255)
    MAX-ACCESS      read-write
    STATUS          current
    DESCRIPTION 
        "Distance value for this route."
    ::= { ipUnicastStaticRouteEntry 7 }
  
ipUnicastStaticRouteRowStatus  OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { ipUnicastStaticRouteEntry 8 }
          
          
--            
-- clear all the static route
--       
ipUnicastClrStaticRoute OBJECT-TYPE
		    SYNTAX          INTEGER
    {
        noUse(0),
        resetCount(1)
    }
    MAX-ACCESS      read-write
    STATUS          current
    DESCRIPTION 
        "clear all the static route."
    ::= { ipUnicast 2 }            
          

--
-- clear the static route on vrf
--
ipUnicastClrVrfStaticRouteTable OBJECT-TYPE
    SYNTAX          SEQUENCE OF IpUnicastClrVrfStaticRouteEntry
    MAX-ACCESS      not-accessible
    STATUS          current
    DESCRIPTION
        ""
    ::= { ipUnicast 3 }
  
ipUnicastClrVrfStaticRouteEntry OBJECT-TYPE
    SYNTAX          IpUnicastClrVrfStaticRouteEntry
    MAX-ACCESS      not-accessible
    STATUS          current
    DESCRIPTION
        ""
    INDEX { ipUnicastClrVrfStaticRouteIndex }
    ::= { ipUnicastClrVrfStaticRouteTable 1 }
      
IpUnicastClrVrfStaticRouteEntry    ::=
    SEQUENCE        
    {
        ipUnicastClrVrfStaticRouteIndex
            Integer32,
        ipUnicastClrVrfStaticRoute
            Integer32
    }
  
ipUnicastClrVrfStaticRouteIndex OBJECT-TYPE
    SYNTAX          Integer32(0..32)
    MAX-ACCESS      not-accessible
    STATUS          current
    DESCRIPTION 
        ""
    ::= { ipUnicastClrVrfStaticRouteEntry 1 }        
  
  
ipUnicastClrVrfStaticRoute OBJECT-TYPE
    SYNTAX          Integer32(0..32)
    MAX-ACCESS      read-write
    STATUS          current
    DESCRIPTION 
        ""
    ::= { ipUnicastClrVrfStaticRouteEntry 2 }

ipUnicastMaxStaticRoute OBJECT-TYPE
    SYNTAX          Integer32(1..65535)
    MAX-ACCESS      read-write
    STATUS          current
    DESCRIPTION
        "Allowed number of static routes."
    ::= { ipUnicast 4 }

ipUnicastMaxStaticV6Route OBJECT-TYPE
    SYNTAX          Integer32(1..65535)
    MAX-ACCESS      read-write
    STATUS          current
    DESCRIPTION
        "Allowed number of IPv6 static routes."
    ::= { ipUnicast 5 }

ipUnicastIcmpErrorInterval OBJECT-TYPE
    SYNTAX          Integer32(0..2147483647)
    MAX-ACCESS      read-write
    STATUS          current
    DESCRIPTION
        "Error message interval(ms) of ICMP."
    ::= { ipUnicast 6 }

ipUnicastIcmpv6ErrorInterval OBJECT-TYPE
    SYNTAX          Integer32(0..2147483647)
    MAX-ACCESS      read-write
    STATUS          current
    DESCRIPTION
        "Error message interval(ms) of ICMP."
    ::= { ipUnicast 7 }
    

-- Sub Module: AAA


-- ==================================================================
--
-- =====================object definition begin======================
--
-- ==================================================================
authenticationEnable OBJECT-TYPE
    SYNTAX          INTEGER
    {
        enable(1),
        disable(2)
    }
    MAX-ACCESS      read-write
    STATUS          current
    DESCRIPTION 
        "Enable or disable authentication function. enable:1 disable:2."
    ::= { aaa 1 }

authenticationLoginTable OBJECT-TYPE
    SYNTAX          SEQUENCE OF AuthenticationLoginEntry
    MAX-ACCESS      not-accessible
    STATUS          current
    DESCRIPTION
        "table of login entry."
    ::= { aaa 2 }

authenticationLoginEntry OBJECT-TYPE
    SYNTAX          AuthenticationLoginEntry
    MAX-ACCESS      not-accessible
    STATUS          current
    DESCRIPTION
        "Login entry        "
    INDEX { authenticationLoginIndex}
    ::= { authenticationLoginTable 1 }

AuthenticationLoginEntry    ::=
    SEQUENCE
    {
        authenticationLoginIndex
            Integer32,
        authenticationLoginName
            OCTET STRING,
        authenticationLoginOne
            INTEGER,
        authenticationLoginTwo
            INTEGER,
        authenticationLoginThree
            INTEGER,
        authenticationLoginFour
            INTEGER,
        authenticationLoginFive
            INTEGER,
        authenticationLoginSix
            INTEGER,
        authenticationLoginRowStatus
            RowStatus
    }

authenticationLoginIndex OBJECT-TYPE
    SYNTAX          Integer32 (0..15)
    MAX-ACCESS      not-accessible
    STATUS          current
    DESCRIPTION 
        "Login index."
    ::= { authenticationLoginEntry 1 }

authenticationLoginName OBJECT-TYPE
    SYNTAX          OCTET STRING (SIZE (1..32))
    MAX-ACCESS      read-create
    STATUS          current
    DESCRIPTION 
        "Login name. The default method list name is 'default'."
    ::= { authenticationLoginEntry 2 }

authenticationLoginOne OBJECT-TYPE
    SYNTAX          INTEGER
    {
        enable(1),
        line(2),
        none(3),
        radius(4),
        local(5),
        tacacs-plus(6)
    }
    MAX-ACCESS      read-create
    STATUS          current
    DESCRIPTION 
        "The first login type, enable(1),line(2),none(3),radius(4),local(5),tacacs-plus(6)."
    ::= { authenticationLoginEntry 3 }

authenticationLoginTwo OBJECT-TYPE
    SYNTAX          INTEGER
    {       
        disable(0),
        enable(1),
        line(2),
        none(3),
        radius(4),
        local(5),
        tacacs-plus(6)
    }
    MAX-ACCESS      read-create
    STATUS          current
    DESCRIPTION 
        "The second login type, disable(0),enable(1),line(2),none(3),radius(4),local(5),tacacs-plus(6)."
    ::= { authenticationLoginEntry 4 }

authenticationLoginThree OBJECT-TYPE
    SYNTAX          INTEGER
    {
        disable(0),
        enable(1),
        line(2),
        none(3),
        radius(4),
        local(5),
        tacacs-plus(6)
    }
    MAX-ACCESS      read-create
    STATUS          current
    DESCRIPTION 
        "The third login type, disable(0),enable(1),line(2),none(3),radius(4),local(5),tacacs-plus(6)."
    ::= { authenticationLoginEntry 5 }

authenticationLoginFour OBJECT-TYPE
    SYNTAX          INTEGER
    {
        disable(0),
        enable(1),
        line(2),
        none(3),
        radius(4),
        local(5),
        tacacs-plus(6)
    }
    MAX-ACCESS      read-create
    STATUS          current
    DESCRIPTION 
        "The fourth login type,disable(0),enable(1),line(2),none(3),radius(4),local(5),tacacs-plus(6)."
    ::= { authenticationLoginEntry 6 }

authenticationLoginFive OBJECT-TYPE
    SYNTAX          INTEGER
    {
        disable(0),
        enable(1),
        line(2),
        none(3),
        radius(4),
        local(5),
        tacacs-plus(6)
    }
    MAX-ACCESS      read-create
    STATUS          current
    DESCRIPTION 
        "The fifth login type, disable(0),enable(1),line(2),none(3),radius(4),local(5),tacacs-plus(6)."
    ::= { authenticationLoginEntry 7 }

authenticationLoginSix OBJECT-TYPE
    SYNTAX          INTEGER
    {
        disable(0),
        enable(1),
        line(2),
        none(3),
        radius(4),
        local(5),
        tacacs-plus(6)
    }
    MAX-ACCESS      read-create
    STATUS          current
    DESCRIPTION 
        "The fifth login type, disable(0),enable(1),line(2),none(3),radius(4),local(5),tacacs-plus(6)."
    ::= { authenticationLoginEntry 8 }
    
authenticationLoginRowStatus OBJECT-TYPE
    SYNTAX          RowStatus
    MAX-ACCESS      read-create
    STATUS          current
    DESCRIPTION 
        "The status of this conceptual row.Now only realize CreateAndGo and Destroy and Active.
        1 means Active
        4 means CreateAndGo
        6 means Destroy"
    ::= { authenticationLoginEntry 9 }

authenticationLineTable OBJECT-TYPE
    SYNTAX          SEQUENCE OF AuthenticationLineEntry
    MAX-ACCESS      not-accessible
    STATUS          current
    DESCRIPTION
        "table of login entry."
    ::= { aaa 3 }

authenticationLineEntry OBJECT-TYPE
    SYNTAX          AuthenticationLineEntry
    MAX-ACCESS      not-accessible
    STATUS          current
    DESCRIPTION
        "Login entry."
    INDEX { authenticationLineIndex}
    ::= { authenticationLineTable 1 }

AuthenticationLineEntry    ::=
    SEQUENCE
    {
        authenticationLineIndex
            Integer32,
        authenticationLineLoginName
            OCTET STRING
    }

authenticationLineIndex OBJECT-TYPE
    SYNTAX          Integer32 (0..7)
    MAX-ACCESS      not-accessible
    STATUS          current
    DESCRIPTION 
        "Login index."
    ::= { authenticationLineEntry 1 }

authenticationLineLoginName OBJECT-TYPE
    SYNTAX          OCTET STRING (SIZE (1..31))
    MAX-ACCESS      read-write
    STATUS          current
    DESCRIPTION 
        "Set an authentication list for login name. The default login name is 'default'. Starting with alphabetic and can only include [0-9a-zA-Z.-_]. Its length range is [1, 32)"
    ::= { authenticationLineEntry 2 }

-- Sub Module: EVC
evcTable OBJECT-TYPE
    SYNTAX  SEQUENCE OF EvcEntry
    MAX-ACCESS not-accessible
    STATUS   current
    DESCRIPTION "The table of EVC entry. An Ethernet virtual connection (EVC) is a 
    logical relationship between Ethernet user-to-network interfaces (UNI) in a 
    provider-based Ethernet service."
    ::= { evc 1 }
                           
evcEntry OBJECT-TYPE
    SYNTAX  EvcEntry
    MAX-ACCESS not-accessible
    STATUS current
    DESCRIPTION "The entry of EVC."
    INDEX   { evcIndex}
    ::= { evcTable 1 }

EvcEntry   ::=
    SEQUENCE {
        evcIndex             Integer32,
        evcName 	         OCTET STRING,
        evcRowstatus  		 RowStatus
        }

evcIndex OBJECT-TYPE
    SYNTAX  Integer32 (1..4094)
    MAX-ACCESS read-only
    STATUS current
    DESCRIPTION "The index of EVC table."
    ::= { evcEntry 1 }
        
evcName OBJECT-TYPE
    SYNTAX  OCTET STRING (SIZE (1..16))
    MAX-ACCESS read-write
    STATUS current
    DESCRIPTION "The name of EVC entry."
    ::= { evcEntry 2 }

evcRowstatus OBJECT-TYPE
	SYNTAX RowStatus
	MAX-ACCESS read-create
	STATUS current
	DESCRIPTION
        "The status of this conceptual row.Now only realize CreateAndGo and Destroy and Active.
        1 means Active
        4 means CreateAndGo
        6 means Destroy"
	::= { evcEntry 3 }

evcInfoTable OBJECT-TYPE
    SYNTAX  SEQUENCE OF EvcInfoEntry
    MAX-ACCESS not-accessible
    STATUS   current
    DESCRIPTION "The table of EVC information."
    ::= { evc 2 }
                           
evcInfoEntry OBJECT-TYPE
    SYNTAX  EvcInfoEntry
    MAX-ACCESS not-accessible
    STATUS current
    DESCRIPTION "One entry of EVC information."
    INDEX   { evcInfoIndex}
    ::= { evcInfoTable 1 }

EvcInfoEntry   ::=
    SEQUENCE {
        evcInfoIndex             Integer32,
        evcInfoMappedVlan        Integer32,
        evcInfoMappedDoubleVlan  OCTET STRING,
        evcInfoUsingNumber       Integer32
        }

evcInfoIndex OBJECT-TYPE
    SYNTAX  Integer32 (1..4094)
    MAX-ACCESS read-only
    STATUS current
    DESCRIPTION "The index of EVC information table."
    ::= { evcInfoEntry 1 }
        
evcInfoMappedVlan OBJECT-TYPE
    SYNTAX  Integer32 (0..4094)
    MAX-ACCESS read-write
    STATUS current
    DESCRIPTION "The vlan id of EVC mapped-vlan. The unset value is 0."
    ::= { evcInfoEntry 2 }
    
evcInfoMappedDoubleVlan OBJECT-TYPE
    SYNTAX  OCTET STRING (SIZE (0..9))
    MAX-ACCESS read-write
    STATUS current
    DESCRIPTION "The vlan id of EVC mapped-double-vlan.
    						The input value is like 2,3. 
    						The first vlan id is EVC mapped-inner-vlan ID.
    						The second vlan id is EVC mapped-outer-vlan ID.
    						The unset value is NULL."
    ::= { evcInfoEntry 3 }
    
evcInfoUsingNumber OBJECT-TYPE
    SYNTAX  Integer32 (1..64)
    MAX-ACCESS read-only
    STATUS current
    DESCRIPTION "Number of raw-vlan using this EVC."
    ::= { evcInfoEntry 4 }
    
-- Sub Module: QINQ

qinqVlanMappingTableObject OBJECT IDENTIFIER ::= { qinq 1 }  
      
--
--  add/remove a vlan mapping table
--

    qinqVlanMappingTable OBJECT-TYPE
        SYNTAX  SEQUENCE OF QinqVlanMappingEntry
        MAX-ACCESS not-accessible
        STATUS   current
        DESCRIPTION "The table containing information of vlan mapping table."
        ::= { qinqVlanMappingTableObject 1 }
                           
    qinqVlanMappingEntry OBJECT-TYPE
        SYNTAX  QinqVlanMappingEntry
        MAX-ACCESS not-accessible
        STATUS current
        DESCRIPTION "An entry containing information of vlan mapping table."
        INDEX   { qinqVlanMappingTableIndex}
        ::= { qinqVlanMappingTable 1 }

    QinqVlanMappingEntry   ::=
    SEQUENCE {
        qinqVlanMappingTableIndex             Integer32,
        qinqVlanMappingTableName 	            OCTET STRING,
        qinqVlanMappingTableRowstatus  		RowStatus
        }

    qinqVlanMappingTableIndex OBJECT-TYPE
        SYNTAX  Integer32 (1..64)
        MAX-ACCESS not-accessible
        STATUS current
        DESCRIPTION "vlan mapping table index."
        ::= { qinqVlanMappingEntry 1 }
        
    qinqVlanMappingTableName OBJECT-TYPE
        SYNTAX  OCTET STRING (SIZE (0..16))
        MAX-ACCESS read-create
        STATUS current
        DESCRIPTION "vlan mapping table name."
        ::= { qinqVlanMappingEntry 2 }

	qinqVlanMappingTableRowstatus OBJECT-TYPE
		SYNTAX RowStatus
		MAX-ACCESS read-create
		STATUS current
		DESCRIPTION
        "The status of this conceptual row.Now only realize CreateAndGo and Destroy and Active.
        1 means Active
        4 means CreateAndGo
        6 means Destroy"
		::= { qinqVlanMappingEntry 3 }		


--
-- Nodes of QinqVlanMappingTableRawVlanObject
--

qinqVlanMappingItemTable OBJECT-TYPE
    SYNTAX  SEQUENCE OF QinqVlanMappingItemEntry
    MAX-ACCESS not-accessible
    STATUS   current
    DESCRIPTION 
        "The table is used to describe the relation between raw-vlan and mapped-vlan."
    ::= { qinqVlanMappingTableObject 2 }
                           
qinqVlanMappingItemEntry OBJECT-TYPE
    SYNTAX  QinqVlanMappingItemEntry
    MAX-ACCESS not-accessible
    STATUS current
    DESCRIPTION 
        "The entry is used to describe one item of the relation between raw-vlan and mapped-vlan."
    INDEX   { qinqMappingEntryMappingTableIndex, qinqMappingEntryEvcIndex, qinqMappingEntryRawVid}
    ::= { qinqVlanMappingItemTable 1 }

QinqVlanMappingItemEntry   ::=
SEQUENCE {
    qinqMappingEntryMappingTableIndex    Integer32,
    qinqMappingEntryEvcIndex          Integer32,
    qinqMappingEntryRawVid       Integer32,
    qinqMappingEntryRowstatus  		     RowStatus
    }

qinqMappingEntryMappingTableIndex OBJECT-TYPE
    SYNTAX  Integer32 (1..64)
    MAX-ACCESS not-accessible
    STATUS current
    DESCRIPTION "The vlan mapping table index."
    ::= { qinqVlanMappingItemEntry 1 }
    
qinqMappingEntryEvcIndex OBJECT-TYPE
    SYNTAX  Integer32 (1..512)
    MAX-ACCESS not-accessible
    STATUS current
    DESCRIPTION "The EVC table index."
    ::= { qinqVlanMappingItemEntry 2 }
    
qinqMappingEntryRawVid OBJECT-TYPE
    SYNTAX  Integer32 (0..4095)
    MAX-ACCESS not-accessible
    STATUS current
    DESCRIPTION "Raw vlan tag for this entry.
                 Set to 0 to use for untagged mapped vlan tag.
                 Set to 4095 for out-of-range raw vlan."
    ::= { qinqVlanMappingItemEntry 3 }            

qinqMappingEntryRowstatus OBJECT-TYPE
	SYNTAX RowStatus
	MAX-ACCESS read-create
	STATUS current
	DESCRIPTION
        "The status of this conceptual row.Now only realize CreateAndGo and Destroy and Active.
        1 means Active
        4 means CreateAndGo
        6 means Destroy"
	::= { qinqVlanMappingItemEntry 4 }


-- below is for double tag qinq 
--
--  add/remove an untagged vlan mapping entry with evc to vlan mapping table
--

--    qinqVlanUntaggedMappingWithEvcTable OBJECT-TYPE
--        SYNTAX  SEQUENCE OF QinqVlanUntaggedMappingWithEvcEntry
--        MAX-ACCESS not-accessible
--        STATUS   current
--        DESCRIPTION "The table containing information of vlan mapping table."
--        ::= { qinqVlanMappingTableRawVlanObject 1 }
--                           
--    qinqVlanUntaggedMappingWithEvcEntry OBJECT-TYPE
--        SYNTAX  QinqVlanUntaggedMappingWithEvcEntry
--        MAX-ACCESS not-accessible
--        STATUS current
--        DESCRIPTION "An entry containing information of vlan mapping table."
--        INDEX   { qinqUntaggedWithEvcMappingTableIndex }
--        ::= { qinqVlanUntaggedMappingWithEvcTable 1 }
--
--    QinqVlanUntaggedMappingWithEvcEntry   ::=
--    SEQUENCE {
--        qinqUntaggedWithEvcMappingTableIndex  Integer32,
--        qinqUntaggedWithEvcName 	            OCTET STRING,
--        qinqUntaggedWithEvcFirstVlantag       Integer32,
--        qinqUntaggedWithEvcSecondVlantag      Integer32,
--        qinqUntaggedWithEvcRowstatus  		RowStatus
--        }
--
--    qinqUntaggedWithEvcMappingTableIndex OBJECT-TYPE
--        SYNTAX  Integer32 (1..64)
--        MAX-ACCESS not-accessible
--        STATUS current
--        DESCRIPTION "vlan mapping table index."
--        ::= { qinqVlanUntaggedMappingWithEvcEntry 1 }
--        
--    qinqUntaggedWithEvcName OBJECT-TYPE
--        SYNTAX  OCTET STRING (SIZE (0..16))
--        MAX-ACCESS read-write
--        STATUS current
--        DESCRIPTION "evc name related to this entry."
--        ::= { qinqVlanUntaggedMappingWithEvcEntry 2 }
--
--    qinqUntaggedWithEvcFirstVlantag OBJECT-TYPE
--        SYNTAX  Integer32 (1..4094)
--        MAX-ACCESS read-write
--        STATUS current
--        DESCRIPTION "first vlan tag for this entry if it need map double vlan.
--                    default is 0xFFFF to not use double vlan."
--        ::= { qinqVlanUntaggedMappingWithEvcEntry 3 }
--        
--    qinqUntaggedWithEvcSecondVlantag OBJECT-TYPE
--        SYNTAX  Integer32 (1..4094)
--        MAX-ACCESS read-write
--        STATUS current
--        DESCRIPTION "mapped vlan tag."
--        ::= { qinqVlanUntaggedMappingWithEvcEntry 4 }
--            
--	qinqUntaggedWithEvcRowstatus OBJECT-TYPE
--		SYNTAX RowStatus
--		MAX-ACCESS read-create
--		STATUS current
--		DESCRIPTION
--        "The status of this conceptual row.Now only realize CreateAndGo and Destroy and Active.
--        1 means Active
--        4 means CreateAndGo
--        6 means Destroy"
--		::= { qinqVlanUntaggedMappingWithEvcEntry 5 }


--
--  add/remove an tagged vlan mapping entry with evc to vlan mapping table
--

--    qinqVlanTaggedMappingWithEvcTable OBJECT-TYPE
--        SYNTAX  SEQUENCE OF QinqVlanTaggedMappingWithEvcEntry
--        MAX-ACCESS not-accessible
--        STATUS   current
--        DESCRIPTION "The infomation of vlan mapping table entry."
--        ::= { qinqVlanMappingTableRawVlanObject 2 }
--                           
--    qinqVlanTaggedMappingWithEvcEntry OBJECT-TYPE
--        SYNTAX  QinqVlanTaggedMappingWithEvcEntry
--        MAX-ACCESS not-accessible
--        STATUS current
--        DESCRIPTION "An entry containing information of vlan mapping table."
--        INDEX   { qinqTaggedWithEvcMappingTableIndex, qinqTaggedWithEvcMappingRawVlantag }
--        ::= { qinqVlanTaggedMappingWithEvcTable 1 }
--
--    QinqVlanTaggedMappingWithEvcEntry   ::=
--    SEQUENCE {
--        qinqTaggedWithEvcMappingTableIndex    Integer32,
--        qinqTaggedWithEvcMappingRawVlantag    Integer32,
--        qinqTaggedWithEvcName 	            OCTET STRING,
--        qinqTaggedWithEvcMappingVlantag       Integer32,
--        qinqTaggedWithEvcRowstatus  		    RowStatus
--        }
--
--    qinqTaggedWithEvcMappingTableIndex OBJECT-TYPE
--        SYNTAX  Integer32 (1..64)
--        MAX-ACCESS not-accessible
--        STATUS current
--        DESCRIPTION "vlan mapping table index."
--        ::= { qinqVlanTaggedMappingWithEvcEntry 1 }
--        
--    qinqTaggedWithEvcMappingRawVlantag OBJECT-TYPE
--        SYNTAX  Integer32 (1..4095)
--        MAX-ACCESS read-only
--        STATUS current
--        DESCRIPTION "raw vlan tag for this entry.
--                     set to 4095 to use for out of range mapped vlan tag."
--        ::= { qinqVlanTaggedMappingWithEvcEntry 2 }
--            
--    qinqTaggedWithEvcName OBJECT-TYPE
--        SYNTAX  OCTET STRING (SIZE (0..16))
--        MAX-ACCESS read-write
--        STATUS current
--        DESCRIPTION "evc name related to this entry."
--        ::= { qinqVlanTaggedMappingWithEvcEntry 3 }
--
--    qinqTaggedWithEvcMappingVlantag OBJECT-TYPE
--        SYNTAX  Integer32 (1..4094)
--        MAX-ACCESS read-write
--        STATUS current
--        DESCRIPTION "mapping vlan tag for this entry."
--        ::= { qinqVlanTaggedMappingWithEvcEntry 4 }
--            
--	qinqTaggedWithEvcRowstatus OBJECT-TYPE
--		SYNTAX RowStatus
--		MAX-ACCESS read-create
--		STATUS current
--		DESCRIPTION
--        "The status of this conceptual row.Now only realize CreateAndGo and Destroy and Active.
--        1 means Active
--        4 means CreateAndGo
--        6 means Destroy"
--		::= { qinqVlanTaggedMappingWithEvcEntry 5 }


--
--  add/remove an untagged or tagged vlan mapping entry without evc to vlan mapping table
--

--    qinqVlanMappingWithoutEvcTable OBJECT-TYPE
--        SYNTAX  SEQUENCE OF QinqVlanMappingWithoutEvcEntry
--        MAX-ACCESS not-accessible
--        STATUS   current
--        DESCRIPTION "The infomation of vlan mapping table entry."
--        ::= { qinqVlanMappingTableRawVlanObject 3 }
--                           
--    qinqVlanMappingWithoutEvcEntry OBJECT-TYPE
--        SYNTAX  QinqVlanMappingWithoutEvcEntry
--        MAX-ACCESS not-accessible
--        STATUS current
--        DESCRIPTION "The infomation of vlan mapping table entry."
--        INDEX   { qinqWithoutEvcMappingTableIndex }
--        ::= { qinqVlanMappingWithoutEvcTable 1 }
--
--    QinqVlanMappingWithoutEvcEntry   ::=
--    SEQUENCE {
--        qinqWithoutEvcMappingTableIndex    Integer32,
--        qinqWithoutEvcMappingRawVlantag    Integer32,
--        qinqWithoutEvcMappingVlantag       Integer32,
--        qinqWithoutEvcRowstatus  		     RowStatus
--        }
--
--    qinqWithoutEvcMappingTableIndex OBJECT-TYPE
--        SYNTAX  Integer32 (1..64)
--        MAX-ACCESS not-accessible
--        STATUS current
--        DESCRIPTION "vlan mapping table index."
--        ::= { qinqVlanMappingWithoutEvcEntry 1 }
--        
--    qinqWithoutEvcMappingRawVlantag OBJECT-TYPE
--        SYNTAX  Integer32 (0..4094)
--        MAX-ACCESS read-only
--        STATUS current
--        DESCRIPTION "raw vlan tag for this entry.
--                     set to 0 to use for untagged mapped vlan tag."
--        ::= { qinqVlanMappingWithoutEvcEntry 2 }            
--
--    qinqWithoutEvcMappingVlantag OBJECT-TYPE
--        SYNTAX  Integer32 (1..4094)
--        MAX-ACCESS read-write
--        STATUS current
--        DESCRIPTION "mapping vlan tag for this entry."
--        ::= { qinqVlanMappingWithoutEvcEntry 3 }
--            
--	qinqWithoutEvcRowstatus OBJECT-TYPE
--		SYNTAX RowStatus
--		MAX-ACCESS read-create
--		STATUS current
--		DESCRIPTION
--        "The status of this conceptual row.Now only realize CreateAndGo and Destroy and Active.
--        1 means Active
--        4 means CreateAndGo
--        6 means Destroy"
--		::= { qinqVlanMappingWithoutEvcEntry 4 }

        
--
--  Qinq Interface Object
--
    qinqIfObject OBJECT IDENTIFIER ::= { qinq 2 }     
            
--
--  set/unset an interface switch mode to dot1q tunnel
--

    qinqIfModeDot1qTunnelTable OBJECT-TYPE
            SYNTAX  SEQUENCE OF QinqIfModeDot1qTunnelEntry
            MAX-ACCESS not-accessible
            STATUS   current
            DESCRIPTION "The infomation of interface switchport mode."
            ::= { qinqIfObject 1 }
            
    qinqIfModeDot1qTunnelEntry OBJECT-TYPE
        SYNTAX  QinqIfModeDot1qTunnelEntry
        MAX-ACCESS not-accessible
        STATUS current
        DESCRIPTION "The infomation of interface switchport mode."
        INDEX   { qinqIfModeDot1qTunnelIfIndex }
        ::= { qinqIfModeDot1qTunnelTable 1 }        
    
    QinqIfModeDot1qTunnelEntry   ::=
    SEQUENCE {
        qinqIfModeDot1qTunnelIfIndex    Integer32,
        qinqIfModeDot1qTunnelRowstatus  RowStatus
        }    
    
    qinqIfModeDot1qTunnelIfIndex OBJECT-TYPE
        SYNTAX  Integer32      (1..65535)
        MAX-ACCESS not-accessible
        STATUS current
        DESCRIPTION "The index of the interface which want to set to dot1q-tunnel mode."
        ::= { qinqIfModeDot1qTunnelEntry 1 }
            
    qinqIfModeDot1qTunnelRowstatus OBJECT-TYPE
        SYNTAX RowStatus
        MAX-ACCESS read-create
        STATUS current
        DESCRIPTION
            "The status of this conceptual row.Now only realize CreateAndGo and Destroy and Active.
        1 means Active
        4 means CreateAndGo
        6 means Destroy"
        ::= { qinqIfModeDot1qTunnelEntry 2 }

--
--  set an interface switch dot1q tunnel type
--

    qinqIfDot1qTunnelTypeTable OBJECT-TYPE
            SYNTAX  SEQUENCE OF QinqIfDot1qTunnelTypeEntry
            MAX-ACCESS not-accessible
            STATUS   current
            DESCRIPTION "The infomation of interface switchport dot1q tunnel type."
            ::= { qinqIfObject 2 }
            
    qinqIfDot1qTunnelTypeEntry OBJECT-TYPE
        SYNTAX  QinqIfDot1qTunnelTypeEntry
        MAX-ACCESS not-accessible
        STATUS current
        DESCRIPTION "The infomation of interface switchport dot1q tunnel type."
        INDEX   { qinqIfDot1qTunnelTypeIfIndex }
        ::= { qinqIfDot1qTunnelTypeTable 1 }        
    
    QinqIfDot1qTunnelTypeEntry   ::=
    SEQUENCE {
        qinqIfDot1qTunnelTypeIfIndex    Integer32,
        qinqIfDot1qTunnelType           INTEGER
        }    
    
    qinqIfDot1qTunnelTypeIfIndex OBJECT-TYPE
        SYNTAX  Integer32        (1..65535)
        MAX-ACCESS not-accessible
        STATUS current
        DESCRIPTION "The index of the interface which want to set dot1q-tunnel type."
        ::= { qinqIfDot1qTunnelTypeEntry 1 }
            
    qinqIfDot1qTunnelType OBJECT-TYPE
        SYNTAX INTEGER
            {
                selective(1), 
                basic(2)
            }
        MAX-ACCESS read-write
        STATUS current
        DESCRIPTION
            "The do1q-tunnel type want to set.
            1 selective.
            2 basic."
        ::= { qinqIfDot1qTunnelTypeEntry 2 }
    
    
--
--  set an interface switch dot1q tunnel native vlan
--

    qinqIfDot1qTunnelNativeVlanTable OBJECT-TYPE
            SYNTAX  SEQUENCE OF QinqIfDot1qTunnelNativeVlanEntry
            MAX-ACCESS not-accessible
            STATUS   current
            DESCRIPTION "The infomation of interface switchport dot1q tunnel native vlan."
            ::= { qinqIfObject 3 }
            
    qinqIfDot1qTunnelNativeVlanEntry OBJECT-TYPE
        SYNTAX  QinqIfDot1qTunnelNativeVlanEntry
        MAX-ACCESS not-accessible
        STATUS current
        DESCRIPTION "The infomation of interface switchport dot1q tunnel native vlan."
        INDEX   { qinqIfDot1qTunnelNativeVlanIfIndex }
        ::= { qinqIfDot1qTunnelNativeVlanTable 1 }        
    
    QinqIfDot1qTunnelNativeVlanEntry   ::=
    SEQUENCE {
        qinqIfDot1qTunnelNativeVlanIfIndex    Integer32,
        qinqIfDot1qTunnelNativeVlanId         Integer32,
        qinqIfDot1qTunnelNativeIsInnerVlan    INTEGER,
        qinqIfDot1qTunnelNativeRowStatus      RowStatus
        }    
    
    qinqIfDot1qTunnelNativeVlanIfIndex OBJECT-TYPE
        SYNTAX  Integer32          (1..65535)
        MAX-ACCESS not-accessible
        STATUS current
        DESCRIPTION "The index of the interface which want to set dot1q-tunnel native vlan."
        ::= { qinqIfDot1qTunnelNativeVlanEntry 1 }
            
    qinqIfDot1qTunnelNativeVlanId OBJECT-TYPE
        SYNTAX Integer32 (1..4094)
        MAX-ACCESS read-create
        STATUS current
        DESCRIPTION
            "The do1q-tunnel native vlan id to set.
            1 means set to default native vlan"
        ::= { qinqIfDot1qTunnelNativeVlanEntry 2 }    
        
    qinqIfDot1qTunnelNativeIsInnerVlan OBJECT-TYPE
        SYNTAX INTEGER
        {
            yes(1),
            no(2)
        }
        MAX-ACCESS read-create
        STATUS current
        DESCRIPTION
            "Whether the do1q-tunnel native vlan is inner vlan.
            1:the vlan id is inner vlan id.
            2:default, the vlan id is not inner vlan id.
            "
        ::= { qinqIfDot1qTunnelNativeVlanEntry 3 }    

    qinqIfDot1qTunnelNativeRowStatus OBJECT-TYPE
        SYNTAX RowStatus
        MAX-ACCESS read-create
        STATUS current
        DESCRIPTION
            "The status of this conceptual row.Now only realize CreateAndGo and Destroy and Active.
        1 means Active
        4 means CreateAndGo
        6 means Destroy"
        ::= { qinqIfDot1qTunnelNativeVlanEntry 10 }    

--
--  set an interface switch dot1q tunnel allow vlan
--

    qinqIfDot1qTunnelAllowVlanTable OBJECT-TYPE
            SYNTAX  SEQUENCE OF QinqIfDot1qTunnelAllowVlanEntry
            MAX-ACCESS not-accessible
            STATUS   current
            DESCRIPTION "The infomation of interface switchport dot1q tunnel allow vlan."
            ::= { qinqIfObject 4 }
            
    qinqIfDot1qTunnelAllowVlanEntry OBJECT-TYPE
        SYNTAX  QinqIfDot1qTunnelAllowVlanEntry
        MAX-ACCESS not-accessible
        STATUS current
        DESCRIPTION "The infomation of interface switchport dot1q tunnel allow vlan."
        INDEX   { qinqIfDot1qTunnelAllowVlanIfIndex }
        ::= { qinqIfDot1qTunnelAllowVlanTable 1 }        
    
    QinqIfDot1qTunnelAllowVlanEntry   ::=
    SEQUENCE {
        qinqIfDot1qTunnelAllowVlanIfIndex    Integer32,
        qinqIfDot1qTunnelAllowVlanIdList     OCTET STRING,
        qinqIfDot1qTunnelAllowType           INTEGER, 
        qinqIfDot1qTunnelAllowVlanId         Integer32,
        qinqIfDot1qTunnelAllowRowstatus      RowStatus
        }    
    
    qinqIfDot1qTunnelAllowVlanIfIndex OBJECT-TYPE
        SYNTAX  Integer32             (1..65535)
        MAX-ACCESS not-accessible
        STATUS current
        DESCRIPTION "The index of the interface which want to set dot1q-tunnel allow vlan."
        ::= { qinqIfDot1qTunnelAllowVlanEntry 1 }
           
    qinqIfDot1qTunnelAllowVlanIdList OBJECT-TYPE
        SYNTAX  OCTET STRING (SIZE(0..256))
        MAX-ACCESS read-only
        STATUS current
        DESCRIPTION "The allowed vlan list belong to this dot1q tunnel port."
        ::= { qinqIfDot1qTunnelAllowVlanEntry 2 }
                
    qinqIfDot1qTunnelAllowType OBJECT-TYPE
        SYNTAX INTEGER
            {
                allowAll(1), 
                allowNone(2),
                allowAdd(3),
                allowRemove(4)
            }
        MAX-ACCESS read-create
        STATUS current
        DESCRIPTION
            "The do1q-tunnel type want to set.
            1 allowAll.
            2 allowNone.
            3 allowAdd.
            4 allowRemove. 
            This node is only use for set. The get value is always 0."
        ::= { qinqIfDot1qTunnelAllowVlanEntry 3 }
                
    qinqIfDot1qTunnelAllowVlanId OBJECT-TYPE
        SYNTAX Integer32 (1..4094)
        MAX-ACCESS read-create
        STATUS current
        DESCRIPTION
            "The do1q-tunnel allow vlan id to set.vlan id range 1~4094.
            This node is only use for set. The get value is always 0.
            Use 'qinqIfDot1qTunnelAllowVlanIdList' to get the dot1q vlan state of the interface."
        ::= { qinqIfDot1qTunnelAllowVlanEntry 4 }
        
    qinqIfDot1qTunnelAllowRowstatus OBJECT-TYPE
        SYNTAX RowStatus
        MAX-ACCESS read-create
        STATUS current
        DESCRIPTION
            "The status of this conceptual row. For this table, only realize CreateAndGo and Active.
             If want to remove allowed vlan, use do1q-tunnel type 4(allowRemove).
             1 means Active
             4 means CreateAndGo
             6 means Destroy"
        ::= { qinqIfDot1qTunnelAllowVlanEntry 5 }    
    
    
--
--  apply vlan mapping table on selective dot1q tunnel port
--

    qinqIfDot1qTunnelApplyVlanMappingTable OBJECT-TYPE
            SYNTAX  SEQUENCE OF QinqIfDot1qTunnelApplyVlanMappingEntry
            MAX-ACCESS not-accessible
            STATUS   current
            DESCRIPTION "The infomation of interface switchport dot1q tunnel applied vlan mapping table."
            ::= { qinqIfObject 5 }
            
    qinqIfDot1qTunnelApplyVlanMappingEntry OBJECT-TYPE
        SYNTAX  QinqIfDot1qTunnelApplyVlanMappingEntry
        MAX-ACCESS not-accessible
        STATUS current
        DESCRIPTION "The infomation of interface switchport dot1q tunnel applied vlan mapping table."
        INDEX   { qinqIfDot1qTunnelApplyIfIndex }
        ::= { qinqIfDot1qTunnelApplyVlanMappingTable 1 }        
    
    QinqIfDot1qTunnelApplyVlanMappingEntry   ::=
    SEQUENCE {
        qinqIfDot1qTunnelApplyIfIndex    Integer32,
        qinqIfDot1qTunnelApplyVlanMappingTableName         OCTET STRING,
        qinqIfDot1qTunnelApplyRowstatus      RowStatus
        }    
    
    qinqIfDot1qTunnelApplyIfIndex OBJECT-TYPE
        SYNTAX  Integer32          (1..65535)
        MAX-ACCESS not-accessible
        STATUS current
        DESCRIPTION "The index of the interface which want to apply vlan mapping table."
        ::= { qinqIfDot1qTunnelApplyVlanMappingEntry 1 }
            
    qinqIfDot1qTunnelApplyVlanMappingTableName OBJECT-TYPE
        SYNTAX  OCTET STRING (SIZE (0..16)) 
        MAX-ACCESS read-create
        STATUS current
        DESCRIPTION
            "The vlan mapping table name want to apply to this interface."
        ::= { qinqIfDot1qTunnelApplyVlanMappingEntry 2 }
        
    qinqIfDot1qTunnelApplyRowstatus OBJECT-TYPE
        SYNTAX RowStatus
        MAX-ACCESS read-create
        STATUS current
        DESCRIPTION
            "The status of this conceptual row.Now only realize CreateAndGo and Destroy and Active.
        1 means Active
        4 means CreateAndGo
        6 means Destroy"
        ::= { qinqIfDot1qTunnelApplyVlanMappingEntry 3 }
        

--
--  enable vlan translation on trunk port
--

    qinqIfVlanTranslationEnableTable OBJECT-TYPE
            SYNTAX  SEQUENCE OF QinqIfVlanTranslationEnableEntry
            MAX-ACCESS not-accessible
            STATUS   current
            DESCRIPTION "Enable/disable vlan translation of trunk port ."
            ::= { qinqIfObject 6 }
            
    qinqIfVlanTranslationEnableEntry OBJECT-TYPE
        SYNTAX  QinqIfVlanTranslationEnableEntry
        MAX-ACCESS not-accessible
        STATUS current
        DESCRIPTION "Enable/disable vlan translation of trunk port"
        INDEX   { qinqIfVlanTransIfIndex }
        ::= { qinqIfVlanTranslationEnableTable 1 }        
    
    QinqIfVlanTranslationEnableEntry   ::=
    SEQUENCE {
        qinqIfVlanTransIfIndex    Integer32,
        qinqIfVlanTransEnable     INTEGER
        }    
    
    qinqIfVlanTransIfIndex OBJECT-TYPE
        SYNTAX  Integer32           (1..65535)
        MAX-ACCESS not-accessible
        STATUS current
        DESCRIPTION "The index of the interface which want to enable or disable vlan translation."
        ::= { qinqIfVlanTranslationEnableEntry 1 }
                    
    qinqIfVlanTransEnable OBJECT-TYPE
        SYNTAX INTEGER
        {
            enable(1), 
            disable(2)
        }
        MAX-ACCESS read-write
        STATUS current
        DESCRIPTION
            "Enable/disable vlan translation of trunk port."
        ::= { qinqIfVlanTranslationEnableEntry 2 }


--
--  apply vlan mapping table on vlan translation port
--

    qinqIfVlanTransApplyVlanMappingTable OBJECT-TYPE
            SYNTAX  SEQUENCE OF QinqIfVlanTransApplyVlanMappingEntry
            MAX-ACCESS not-accessible
            STATUS   current
            DESCRIPTION "The infomation of interface switchport trunk vlan translation applied vlan mapping table."
            ::= { qinqIfObject 7 }
            
    qinqIfVlanTransApplyVlanMappingEntry OBJECT-TYPE
        SYNTAX  QinqIfVlanTransApplyVlanMappingEntry
        MAX-ACCESS not-accessible
        STATUS current
        DESCRIPTION "The infomation of interface switchport trunk vlan translation applied vlan mapping table."
        INDEX   { qinqIfVlanTransApplyIfIndex }
        ::= { qinqIfVlanTransApplyVlanMappingTable 1 }        
    
    QinqIfVlanTransApplyVlanMappingEntry   ::=
    SEQUENCE {
        qinqIfVlanTransApplyIfIndex    Integer32,
        qinqIfVlanTransApplyVlanMappingTableName         OCTET STRING,
        qinqIfVlanTransApplyRowstatus      RowStatus
        }    
    
    qinqIfVlanTransApplyIfIndex OBJECT-TYPE
        SYNTAX  Integer32     (1..65535)
        MAX-ACCESS not-accessible
        STATUS current
        DESCRIPTION "The index of the interface which want to apply vlan mapping table."
        ::= { qinqIfVlanTransApplyVlanMappingEntry 1 }
            
    qinqIfVlanTransApplyVlanMappingTableName OBJECT-TYPE
        SYNTAX  OCTET STRING (SIZE (0..16)) 
        MAX-ACCESS read-create
        STATUS current
        DESCRIPTION
            "The vlan mapping table name want to apply to this interface."
        ::= { qinqIfVlanTransApplyVlanMappingEntry 2 }
        
    qinqIfVlanTransApplyRowstatus OBJECT-TYPE
        SYNTAX RowStatus
        MAX-ACCESS read-create
        STATUS current
        DESCRIPTION
            "The status of this conceptual row.Now only realize CreateAndGo and Destroy and Active.
        1 means Active
        4 means CreateAndGo
        6 means Destroy"
        ::= { qinqIfVlanTransApplyVlanMappingEntry 3 }
        

--
--  set dot1q ethertype  
--

    qinqIfDot1qEthertypeTable OBJECT-TYPE
            SYNTAX  SEQUENCE OF QinqIfDot1qEthertypeEntry
            MAX-ACCESS not-accessible
            STATUS   current
            DESCRIPTION "The infomation of interface dot1q type."
            ::= { qinqIfObject 8 }
            
    qinqIfDot1qEthertypeEntry OBJECT-TYPE
        SYNTAX  QinqIfDot1qEthertypeEntry
        MAX-ACCESS not-accessible
        STATUS current
        DESCRIPTION "The infomation of interface dot1q type."
        INDEX   { qinqIfDot1qEthertypeIfIndex }
        ::= { qinqIfDot1qEthertypeTable 1 }        
    
    QinqIfDot1qEthertypeEntry   ::=
    SEQUENCE {
        qinqIfDot1qEthertypeIfIndex    Integer32,
        qinqIfDot1qEthertype         OCTET STRING
        }    
    
    qinqIfDot1qEthertypeIfIndex OBJECT-TYPE
        SYNTAX  Integer32          (1..65535)
        MAX-ACCESS not-accessible
        STATUS current
        DESCRIPTION "The index of the interface which want to set ether type."
        ::= { qinqIfDot1qEthertypeEntry 1 }
            
    qinqIfDot1qEthertype OBJECT-TYPE
        SYNTAX  OCTET STRING (SIZE (0..4)) 
        MAX-ACCESS read-write
        STATUS current
        DESCRIPTION
            "The ethertype want to set to this interface.
            the ethertype value, could be 0x0000 ~~ 0xFFFF"
        ::= { qinqIfDot1qEthertypeEntry 2 }        

--
--  Qinq Vlan Dot1q Object
--
    qinqVlanDot1qObject OBJECT IDENTIFIER ::= { qinq 3 }

--
--  Qinq Vlan Dot1q tag native Enable
--

    qinqVlanDot1qTagNativeEnableTable OBJECT-TYPE
        SYNTAX  SEQUENCE OF QinqVlanDot1qTagNativeEnableEntry
        MAX-ACCESS not-accessible
        STATUS   current
        DESCRIPTION "The infomation of tag native enable or not."
        ::= { qinqVlanDot1qObject 1 }
            
    qinqVlanDot1qTagNativeEnableEntry OBJECT-TYPE
        SYNTAX  QinqVlanDot1qTagNativeEnableEntry
        MAX-ACCESS not-accessible
        STATUS current
        DESCRIPTION "The infomation of tag native enable or not."
        INDEX   { interfaceIndex }
        ::= { qinqVlanDot1qTagNativeEnableTable 1 }        
    
    QinqVlanDot1qTagNativeEnableEntry   ::=
    SEQUENCE {
        qinqVlanDot1qTagNativeEnable           INTEGER
        }    

    qinqVlanDot1qTagNativeEnable OBJECT-TYPE
        SYNTAX INTEGER
        {
            enable(1), 
            disable(2)
        }
        MAX-ACCESS read-write
        STATUS current
        DESCRIPTION
            "Enable/disable Tag Native. enable(1), disable(2)."
        ::= { qinqVlanDot1qTagNativeEnableEntry 2 }


-- Sub Module: RMONEXTENSION
-- Sub Module: RMONEXTENSION


rmonExtTable OBJECT-TYPE 
    SYNTAX          SEQUENCE OF RmonExtEntry
    MAX-ACCESS      not-accessible
    STATUS          current
    DESCRIPTION
        "rmon extension table."
    ::= { rmonExt 1 }

rmonExtEntry OBJECT-TYPE
    SYNTAX          RmonExtEntry
    MAX-ACCESS      not-accessible
    STATUS          current
    DESCRIPTION
        "Rmon extension table entry."
    INDEX { rmonExtIfIndex }
    ::= { rmonExtTable 1 }

RmonExtEntry    ::=
    SEQUENCE
    {
        rmonExtIfIndex     Integer32,
        rmonExtClrCounter  INTEGER
    }

rmonExtIfIndex OBJECT-TYPE
    SYNTAX          Integer32 (0..65535)
    MAX-ACCESS      not-accessible
    STATUS          current
    DESCRIPTION        
        "Interface index."
    ::= { rmonExtEntry 1 }
            
rmonExtClrCounter OBJECT-TYPE
    SYNTAX          INTEGER
    {
        resetCount(1)
    }
    MAX-ACCESS      read-write
    STATUS          current
    DESCRIPTION
        "Reset rmon counters on interface; 1: resetCount and return value is always 0."
    ::= { rmonExtEntry 2 }

	

-- Sub Module: LDPEXT
ldpExtRouterLdp OBJECT-TYPE
    SYNTAX          INTEGER
    {
        destroy(1),
        create(2)
    }
    MAX-ACCESS      read-write
    STATUS          current
    DESCRIPTION
        "destroy or create ldp instance. destroy:1 create:2."
    ::= { ldpExt 1 }

    ldpExtGlobalConfig OBJECT IDENTIFIER    ::= { ldpExt 2 }


ldpExtGlobalConfigCtlMode OBJECT-TYPE
    SYNTAX          INTEGER
    {
        independent(1),
        ordered(2)
    }
    MAX-ACCESS      read-write
    STATUS          current
    DESCRIPTION
        "set the control mode for label processing.
        1 independent.
        2 ordered."
    ::= { ldpExtGlobalConfig 1 }


ldpExtGlobalConfigExplicitNull OBJECT-TYPE
    SYNTAX          INTEGER
    {
        disable(1),
        enable(2)
    }
    MAX-ACCESS      read-write
    STATUS          current
    DESCRIPTION
        "configure the router to send explicit-null labels for directly
        connected FECs instead of implicit-null labels. disable:1 enable:2."
    ::= { ldpExtGlobalConfig 2 }


ldpExtGlobalConfigHelloInterval OBJECT-TYPE
    SYNTAX          Integer32
    MAX-ACCESS      read-write
    STATUS          current
    DESCRIPTION
        "set the interval after which hello packets are sent out.Range 1~21845."
    ::= { ldpExtGlobalConfig 3 }


ldpExtGlobalConfigHoldTime OBJECT-TYPE
    SYNTAX          Integer32
    MAX-ACCESS      read-write
    STATUS          current
    DESCRIPTION
        "set the global value for the hold-time after which the LSR
        rejects adjacencies."
    ::= { ldpExtGlobalConfig 4 }


ldpExtGlobalConfigKeepAliveInterval OBJECT-TYPE
    SYNTAX          Integer32
    MAX-ACCESS      read-write
    STATUS          current
    DESCRIPTION
        "set the global value for the interval after which keep-alive
        packets are sent out."
    ::= { ldpExtGlobalConfig 5 }


ldpExtGlobalConfigKeepAliveTimeout OBJECT-TYPE
    SYNTAX          Integer32
    MAX-ACCESS      read-write
    STATUS          current
    DESCRIPTION
        "Set the global value for the time-out after which sessions are
        rejected."
    ::= { ldpExtGlobalConfig 6 }


ldpExtGlobalConfigMulticastHellos OBJECT-TYPE
    SYNTAX          INTEGER
    {
        disable(1),
        enable(2)
    }
    MAX-ACCESS      read-write
    STATUS          current
    DESCRIPTION
        "disable/enable the transmission of LDP Hello messages.
        disable:1 enable:2."
    ::= { ldpExtGlobalConfig 7 }


ldpExtGlobalConfigRouterId OBJECT-TYPE
    SYNTAX          IpAddress
    MAX-ACCESS      read-write
    STATUS          current
    DESCRIPTION
        "set the router-id to the supplied IP address."
    ::= { ldpExtGlobalConfig 8 }


ldpExtGlobalConfigTargetedPeerHelloInterval OBJECT-TYPE
    SYNTAX          Integer32
    MAX-ACCESS      read-write
    STATUS          current
    DESCRIPTION
        "set the interval for sending unicast hello packets to targeted peers."
    ::= { ldpExtGlobalConfig 9 }


ldpExtGlobalConfigTargetedPeerHelloReceipt OBJECT-TYPE
    SYNTAX          INTEGER
    {
        disable(1),
        enable(2)
    }
    MAX-ACCESS      read-write
    STATUS          current
    DESCRIPTION
        "toggle the receipt of targeted hello packets.disable:1 enable:2."
    ::= { ldpExtGlobalConfig 10 }


ldpExtGlobalConfigTargetedPeerHoldTime OBJECT-TYPE
    SYNTAX          Integer32
    MAX-ACCESS      read-write
    STATUS          current
    DESCRIPTION
        "Set the time-out value that is the time that the router waits
        before rejecting an adjacency with targeted peers."
    ::= { ldpExtGlobalConfig 11 }



ldpExtGlobalConfigClrLdpAdjacencyAll OBJECT-TYPE
    SYNTAX          INTEGER
    {
        noUse(0),
        resetCount(1)
    }
    MAX-ACCESS      read-write
    STATUS          current
    DESCRIPTION
        "clear all adjacencies for the current LSR."
    ::= { ldpExtGlobalConfig 12 }



ldpExtGlobalConfigClrLdpSessionAll OBJECT-TYPE
    SYNTAX          INTEGER
    {
        noUse(0),
        resetCount(1)
    }
    MAX-ACCESS      read-write
    STATUS          current
    DESCRIPTION
        "clear all sessions for the current LSR."
    ::= { ldpExtGlobalConfig 13 }




ldpExtGlobalConfigClrLdpStatic OBJECT-TYPE
    SYNTAX    INTEGER
    {
        noUse(0),
        resetCount(1)
    }
    MAX-ACCESS      read-write
    STATUS          current
    DESCRIPTION
        "clear LDP packet statistics."
    ::= { ldpExtGlobalConfig 14 }


ldpExtGlobalConfigClrLdpStaticAdvLbls OBJECT-TYPE
    SYNTAX          INTEGER
    {
        noUse(0),
        resetCount(1)
    }
    MAX-ACCESS      read-write
    STATUS          current
    DESCRIPTION
        "clear LDP advertise-labels statistics."
    ::= { ldpExtGlobalConfig 15 }



-- ===============================
-- ldpExtIfConfigTable
-- ===============================

  ldpExtIfConfigTable OBJECT-TYPE
    SYNTAX          SEQUENCE OF LdpExtIfConfigEntry
    MAX-ACCESS      not-accessible
    STATUS          current
    DESCRIPTION
        "ldp extention interface config table."
    ::= { ldpExt 3 }

  ldpExtIfConfigEntry OBJECT-TYPE
    SYNTAX          LdpExtIfConfigEntry
    MAX-ACCESS      not-accessible
    STATUS          current
    DESCRIPTION
        "ldp extension interface config table entry."
    INDEX {ldpExtIfConfigIfIndex }
    ::= { ldpExtIfConfigTable 1 }

LdpExtIfConfigEntry    ::=
    SEQUENCE
    {
        ldpExtIfConfigIfIndex
            Integer32,
        ldpExtIfConfigHelloInterval
            Integer32,
        ldpExtIfConfigHoldTime
            Integer32,
        ldpExtIfConfigKeepAliveInterval
            Integer32,
        ldpExtIfConfigKeepAliveTimeout
            Integer32,
        ldpExtIfConfigMulticastHellos
            INTEGER,
        ldpExtIfConfigTargetedPeerHelloInterval
            Integer32,
        ldpExtIfConfigTargetedPeerHoldTime
            Integer32,
        ldpExtIfConfigEnableLdp
            INTEGER
    }

ldpExtIfConfigIfIndex OBJECT-TYPE
    SYNTAX          Integer32 (0..65535)
    MAX-ACCESS      not-accessible
    STATUS          current
    DESCRIPTION
        "Interface index."
    ::= { ldpExtIfConfigEntry 1 }

ldpExtIfConfigHelloInterval OBJECT-TYPE
    SYNTAX          Integer32
    MAX-ACCESS      read-write
    STATUS          current
    DESCRIPTION
        "set the interval for sending multicast Hello packets
        via an interface."
    ::= { ldpExtIfConfigEntry 2 }


ldpExtIfConfigHoldTime OBJECT-TYPE
    SYNTAX          Integer32
    MAX-ACCESS      read-write
    STATUS          current
    DESCRIPTION
        "set the hold-time value after which the LSR rejects
        adjacencies via an interface."
    ::= { ldpExtIfConfigEntry 3 }


ldpExtIfConfigKeepAliveInterval OBJECT-TYPE
    SYNTAX          Integer32
    MAX-ACCESS      read-write
    STATUS          current
    DESCRIPTION
        "set the interval for sending keep-alive messages to
        the peer in order to maintain a session."
    ::= { ldpExtIfConfigEntry 4 }


ldpExtIfConfigKeepAliveTimeout OBJECT-TYPE
    SYNTAX          Integer32
    MAX-ACCESS      read-write
    STATUS          current
    DESCRIPTION
        "set the keep-alive time-out value for rejecting
        a session with a peer."
    ::= { ldpExtIfConfigEntry 5 }

ldpExtIfConfigMulticastHellos OBJECT-TYPE
    SYNTAX          INTEGER
    {
        disable(1),
        enable(2)
    }
    MAX-ACCESS      read-write
    STATUS          current
    DESCRIPTION
        "disable/enable multicast hello exchange on a specified interface.
        disable:1 enable:2."
    DEFVAL{ 2 }
    ::= { ldpExtIfConfigEntry 6 }


ldpExtIfConfigTargetedPeerHelloInterval OBJECT-TYPE
    SYNTAX          Integer32
    MAX-ACCESS      read-write
    STATUS          current
    DESCRIPTION
        "set the interval for sending unicast hello packets to targeted
        peers via this interface."
    ::= { ldpExtIfConfigEntry 7 }


ldpExtIfConfigTargetedPeerHoldTime OBJECT-TYPE
    SYNTAX          Integer32
    MAX-ACCESS      read-write
    STATUS          current
    DESCRIPTION
        "set the time-out value that is the time that the router waits
        before rejecting an adjacency with a targeted peer."
    ::= { ldpExtIfConfigEntry 8 }


ldpExtIfConfigEnableLdp OBJECT-TYPE
    SYNTAX          INTEGER
    {
        disable(1),
        enable(2)
    }
    MAX-ACCESS      read-write
    STATUS          current
    DESCRIPTION
        "disable/enable ldp function on a specified interface.
        disable:1 enable:2."
    ::= { ldpExtIfConfigEntry 9 }

-- ===========================
-- ldpExtConfigTargetPeerTable
-- ===========================

     ldpExtConfigTargetPeerTable OBJECT-TYPE
    SYNTAX          SEQUENCE OF LdpExtConfigTargetPeerEntry
    MAX-ACCESS      not-accessible
    STATUS          current
    DESCRIPTION
        "config target peer table."
    ::= { ldpExt 4 }


ldpExtConfigTargetPeerEntry OBJECT-TYPE
    SYNTAX          LdpExtConfigTargetPeerEntry
    MAX-ACCESS      not-accessible
    STATUS          current
    DESCRIPTION
        "ldp extension target peer table entry."
    INDEX { ldpExtConfigTargetPeerAddr }
    ::= { ldpExtConfigTargetPeerTable 1 }

LdpExtConfigTargetPeerEntry    ::=
    SEQUENCE
    {
        ldpExtConfigTargetPeerAddr
            IpAddress,
        ldpExtConfigTargetPeerStatus
            RowStatus
    }

ldpExtConfigTargetPeerAddr OBJECT-TYPE
    SYNTAX          IpAddress
    MAX-ACCESS      not-accessible
    STATUS          current
    DESCRIPTION
        "specify a targeted LDP peer."
    ::= { ldpExtConfigTargetPeerEntry 1 }


ldpExtConfigTargetPeerStatus OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { ldpExtConfigTargetPeerEntry 2 }          
   
   
-- ===================================================
-- transport address table
-- ===================================================
     ldpExtConfigTransAddrTable OBJECT-TYPE 
    SYNTAX          SEQUENCE OF LdpExtConfigTransAddrEntry
    MAX-ACCESS      not-accessible
    STATUS          current
    DESCRIPTION
        "config transport address table."
    ::= { ldpExt 5 }

ldpExtConfigTransAddrEntry OBJECT-TYPE
    SYNTAX          LdpExtConfigTransAddrEntry
    MAX-ACCESS      not-accessible
    STATUS          current
    DESCRIPTION
        "ldp extension transport address table entry."
    INDEX { ldpExtGlobalConfigTransportAddress }
    ::= { ldpExtConfigTransAddrTable 1 }

LdpExtConfigTransAddrEntry    ::=
    SEQUENCE
    {
        ldpExtGlobalConfigTransportAddress    
            IpAddress,
        ldpExtGlobalConfigTransportAddressStatus  
            RowStatus
    }            
                 
ldpExtGlobalConfigTransportAddress OBJECT-TYPE
    SYNTAX          IpAddress
    MAX-ACCESS      not-accessible
    STATUS          current
    DESCRIPTION
        "configure the transport address for a label space."
    ::= { ldpExtConfigTransAddrEntry 1 }             
            
            
ldpExtGlobalConfigTransportAddressStatus OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { ldpExtConfigTransAddrEntry 2 }                      
                 
                 
-- ==================================================
-- Advertise-Labels Table
-- ==================================================

     ldpExtConfigAdvLblsTable OBJECT-TYPE 
    SYNTAX          SEQUENCE OF LdpExtConfigAdvLblsEntry
    MAX-ACCESS      not-accessible
    STATUS          current
    DESCRIPTION
        "config advertise label table."
    ::= { ldpExt 6 }



ldpExtConfigAdvLblsEntry OBJECT-TYPE
    SYNTAX          LdpExtConfigAdvLblsEntry
    MAX-ACCESS      not-accessible
    STATUS          current
    DESCRIPTION
        "ldp advertise label table entry."
    INDEX
    {
        ldpExtAdvLblsPrefixIndex,
        ldpExtAdvLblsPeerIndex
    }
    ::= { ldpExtConfigAdvLblsTable 1 }

LdpExtConfigAdvLblsEntry    ::=
    SEQUENCE
     {
        ldpExtAdvLblsPrefixIndex    
            Integer32,
        ldpExtAdvLblsPeerIndex    
            Integer32,
        ldpExtAdvLblsPrefixName     
            OCTET STRING,
        ldpExtAdvLblsPeerName    
            OCTET STRING,
        ldpExtAdvLblsStatus  
            RowStatus
     }

ldpExtAdvLblsPrefixIndex  OBJECT-TYPE
    SYNTAX          Integer32 (0..65535)
    MAX-ACCESS      not-accessible
    STATUS          current
    DESCRIPTION
        "Advertise-Labels Table prefix index."
    ::= { ldpExtConfigAdvLblsEntry 1 }     
            
           
ldpExtAdvLblsPeerIndex OBJECT-TYPE
    SYNTAX          Integer32 (0..65535)
    MAX-ACCESS      not-accessible
    STATUS          current
    DESCRIPTION
        "Advertise-Labels Table peer index."
    ::= { ldpExtConfigAdvLblsEntry 2 }                
    
    
ldpExtAdvLblsPrefixName OBJECT-TYPE
    SYNTAX          OCTET STRING (SIZE(0..256))
    MAX-ACCESS      read-create
    STATUS          current
    DESCRIPTION
        "specify Advertise-Labels Table prefix name."
    ::= { ldpExtConfigAdvLblsEntry 3 }         
              
              
ldpExtAdvLblsPeerName OBJECT-TYPE
    SYNTAX          OCTET STRING (SIZE(0..256))
    MAX-ACCESS      read-create
    STATUS          current
    DESCRIPTION
        "specify Advertise-Labels Table peer name."
    ::= { ldpExtConfigAdvLblsEntry 4 }  
              
              
ldpExtAdvLblsStatus OBJECT-TYPE
    SYNTAX          RowStatus
    MAX-ACCESS      read-write
    STATUS          current
    DESCRIPTION
        "The status of this conceptual row.Now only realize CreateAndGo 
        and Destroy and Active.
        1 means Active
        4 means CreateAndGo
        6 means Destroy"
    ::= { ldpExtConfigAdvLblsEntry 5 }        
            
           
            
-- ==================================================            
-- Advertise-label to any table           
-- ==================================================           

ldpExtConfigAdvLblsToAnyTable OBJECT-TYPE 
    SYNTAX          SEQUENCE OF LdpExtConfigAdvLblsToAnyEntry
    MAX-ACCESS      not-accessible
    STATUS          current
    DESCRIPTION
        "config advertise label to any table."
    ::= { ldpExt 7 }

ldpExtConfigAdvLblsToAnyEntry OBJECT-TYPE
    SYNTAX          LdpExtConfigAdvLblsToAnyEntry
    MAX-ACCESS      not-accessible
    STATUS          current
    DESCRIPTION
        "ldp advertise label to any table entry."
    INDEX { ldpExtAdvLblsPrefixIndex }
    ::= { ldpExtConfigAdvLblsToAnyTable 1 }

LdpExtConfigAdvLblsToAnyEntry    ::=
    SEQUENCE
    {
        ldpExtAdvLblsToAnyPrefixIndex    
            Integer32,
        ldpExtAdvLblsToAnyPrefixName     
            OCTET STRING,
        ldpExtAdvLblsToAnyStatus  
            RowStatus
    }
                 
ldpExtAdvLblsToAnyPrefixIndex  OBJECT-TYPE
    SYNTAX          Integer32
    MAX-ACCESS      not-accessible
    STATUS          current
    DESCRIPTION
        "Advertise-Labels to any Table prefix index."
    ::= { ldpExtConfigAdvLblsToAnyEntry 1 }   
            

ldpExtAdvLblsToAnyPrefixName OBJECT-TYPE
    SYNTAX          OCTET STRING (SIZE(0..256))
    MAX-ACCESS      read-write
    STATUS          current
    DESCRIPTION
        "specify which destinations have their labels advertised to 
        all LDP neighbors."
    ::= { ldpExtConfigAdvLblsToAnyEntry 2 }
            
            
ldpExtAdvLblsToAnyStatus OBJECT-TYPE
    SYNTAX          RowStatus
    MAX-ACCESS      read-write
    STATUS          current
    DESCRIPTION
        "The status of this conceptual row.Now only realize CreateAndGo 
        and Destroy and Active.
        1 means Active
        4 means CreateAndGo
        6 means Destroy"
    ::= { ldpExtConfigAdvLblsToAnyEntry 3 }   
            
-- Sub Module: BGP4EXT

--
-- bgpLocalAs
--

bgpLocalAs OBJECT-TYPE
    SYNTAX          Integer32 (0..65535)
    MAX-ACCESS      read-write
    STATUS          current
    DESCRIPTION 
        "The local autonomous system number."
    ::= { bgp 1 }
        
        
--
-- bgpMibBindingVrf
--
bgpMibBinding     OBJECT IDENTIFIER    ::= { bgp 2 }

bgpMibBindingVrf OBJECT-TYPE
    SYNTAX          Integer32 (0..60)
    MAX-ACCESS      read-write
    STATUS          current
    DESCRIPTION        
        "BGP mib binding vrf."
    ::= { bgpMibBinding 1 }    
        
bgpMibBindingVpnv4 OBJECT-TYPE
    SYNTAX          TruthValue
    MAX-ACCESS      read-write
    STATUS          current
    DESCRIPTION        
        "BGP mib binding vpnv4."
    ::= { bgpMibBinding 2 }                

--
--BGP Global config
--        
bgpGlobalConfig     OBJECT IDENTIFIER    ::= { bgp 3 }
		
bgpAlwaysCompareMed OBJECT-TYPE
    SYNTAX          TruthValue
    MAX-ACCESS      read-write
    STATUS          current
    DESCRIPTION        
        "Allow comparing MED from different neighbors."
    ::= { bgpGlobalConfig 1 }           

bgpDeterministicMed OBJECT-TYPE
    SYNTAX          TruthValue
    MAX-ACCESS      read-write
    STATUS          current
    DESCRIPTION        
        "Pick the best-MED path among paths advertised from the 
        neighboring AS."
    ::= { bgpGlobalConfig 2 }          

bgpFastExternalFailover OBJECT-TYPE
    SYNTAX          TruthValue
    MAX-ACCESS      read-write
    STATUS          current
    DESCRIPTION        
        "Immediately reset session if a link to a directly
        connected external peer goes down."
    ::= { bgpGlobalConfig 3 }      
        
bgpEnforceFirstAS OBJECT-TYPE
    SYNTAX          TruthValue
    MAX-ACCESS      read-write
    STATUS          current
    DESCRIPTION        
        "Enforce the first AS for EBGP routes."
    ::= { bgpGlobalConfig 4 }        

bgpBestpathCompareRouterid OBJECT-TYPE
    SYNTAX          TruthValue
    MAX-ACCESS      read-write
    STATUS          current
    DESCRIPTION        
        "Compare router-id for identical EBGP paths."
    ::= { bgpGlobalConfig 5 }          

bgpBestpathCompareConfedASpath OBJECT-TYPE
    SYNTAX          TruthValue
    MAX-ACCESS      read-write
    STATUS          current
    DESCRIPTION        
        "Allow comparing confederation AS path length."
    ::= { bgpGlobalConfig 6 }              

bgpBestpathASPathIgnore OBJECT-TYPE
    SYNTAX          TruthValue
    MAX-ACCESS      read-write
    STATUS          current
    DESCRIPTION        
        "Ignore as-path length in selecting a route."
    ::= { bgpGlobalConfig 7 }          

bgpBestpathMed OBJECT-TYPE
    SYNTAX          INTEGER
    {
        confed(1),
        missing(2),
        confedAndMissing(3),
        none(4)
    }
    MAX-ACCESS      read-write
    STATUS          current
    DESCRIPTION        
        "Change the default bestpath selection MED attribute."
    ::= { bgpGlobalConfig 8 }                  

bgpDefaultIpv4Unicast OBJECT-TYPE
    SYNTAX          TruthValue
    MAX-ACCESS      read-write
    STATUS          current
    DESCRIPTION        
        "Activate ipv4-unicast for a peer by default."
    ::= { bgpGlobalConfig 9 }          

bgpDefaultLocalPreference OBJECT-TYPE
    SYNTAX          Unsigned32 (0..4294967295)
    MAX-ACCESS      read-write
    STATUS          current
    DESCRIPTION        
        "Configure default local preference value."
    ::= { bgpGlobalConfig 10 }                 

bgpLogNeighborChanges OBJECT-TYPE
    SYNTAX          TruthValue
    MAX-ACCESS      read-write
    STATUS          current
    DESCRIPTION        
        "Log neighbor up/down and reset reason."
    ::= { bgpGlobalConfig 11 }             

bgpConfederationIdentifier OBJECT-TYPE
    SYNTAX          Integer32 (0..65535)
    MAX-ACCESS      read-write
    STATUS          current
    DESCRIPTION        
        "Set routing domain confederation AS."
    ::= { bgpGlobalConfig 12 }          

bgpDistanceExternalRoutes OBJECT-TYPE
    SYNTAX          Integer32 (1..255)
    MAX-ACCESS      read-write
    STATUS          current
    DESCRIPTION        
        "Distance for routes external to the AS. Default: 20."
    ::= { bgpGlobalConfig 13 }          

bgpDistanceInternalRoutes OBJECT-TYPE
    SYNTAX          Integer32 (1..255)
    MAX-ACCESS      read-write
    STATUS          current
    DESCRIPTION        
        "Distance for routes internal to the AS. Default: 200."
    ::= { bgpGlobalConfig 14 }    
                        
 bgpDistancelocalRoutes OBJECT-TYPE
    SYNTAX          Integer32 (1..255)
    MAX-ACCESS      read-write
    STATUS          current
    DESCRIPTION        
        "Distance for routes local to the AS. Default: 200."
    ::= { bgpGlobalConfig 15 }         

 bgpClientToClientReflection OBJECT-TYPE
    SYNTAX          TruthValue
    MAX-ACCESS      read-write
    STATUS          current
    DESCRIPTION        
        "Configure client to client route reflection."
    ::= { bgpGlobalConfig 16 }        

 bgpScanTime OBJECT-TYPE
    SYNTAX          Integer32 (0..60)
    MAX-ACCESS      read-write
    STATUS          current
    DESCRIPTION        
        "Configure background scan interval(sec) [Default:60; Disable:0]."
    ::= { bgpGlobalConfig 17 } 
                      
bgpClusterIDDigit OBJECT-TYPE
    SYNTAX          Unsigned32 (1..65535)
    MAX-ACCESS      read-write
    STATUS          current
    DESCRIPTION        
        "Configure Route-Reflector Cluster-id as 32 bit quantity.
        set to 0 to unset this node."
    ::= { bgpGlobalConfig 18 }
        
bgpClusterIDIp OBJECT-TYPE
    SYNTAX          IpAddress
    MAX-ACCESS      read-write
    STATUS          current
    DESCRIPTION        
        "Configure Route-Reflector Cluster-id in IP address format.
        set to 0 to unset this node."
    ::= { bgpGlobalConfig 19 }                 
                  
--
-- BGP4 Received Peers 
-- 

bgpPeerExtTable OBJECT-TYPE
    SYNTAX          SEQUENCE OF BgpPeerExtEntry
    MAX-ACCESS      not-accessible
    STATUS          current
    DESCRIPTION
        "This table contains information about routes to 
        destination networks from all BGP4 peers.  Since 
        BGP4 can carry routes for multiple Network Layer 
        protocols, this table has the Address Family 
        Identifier(AFI) of the Network Layer protocol as the 
        first index. Further for a given AFI, routes carried
        by BGP4 are distinguished based on Subsequent Address 
        Family Identifiers(SAFI).  Hence that is used as the
        second index.  Conceptually there is a separate Loc-RIB
        maintained by the BGP speaker for each combination of 
        AFI and SAFI supported by it." 
    REFERENCE 
        "RFC-1771: A Border Gateway Protocol 4 (BGP-4),
        RFC-2858: Multiprotocol Extensions for BGP-4,
        RFC-2547: BGP/MPLS VPNs." 
    ::= { bgp 4 }

bgpPeerExtEntry OBJECT-TYPE
    SYNTAX          BgpPeerExtEntry
    MAX-ACCESS      not-accessible
    STATUS          current
    DESCRIPTION
        "Information about a path to a network received from a peer."
    INDEX { bgpPeerExtPeer }
    ::= { bgpPeerExtTable 1 }

BgpPeerExtEntry    ::=    
    SEQUENCE {
        bgpPeerExtPeer
            InetAddress,
        bgpPeerExtRemoteAS
            INTEGER,
        bgpPeerExtRowStats
            RowStatus,
        bgpPeerExtActivate
            TruthValue,
        bgpPeerExtPassive
            TruthValue,
        bgpPeerExtDescription
            OCTET STRING,
        bgpPeerExtCapabilityRouteRefresh
            TruthValue,
        bgpPeerExtCapabilityDynamic
            TruthValue,
        bgpPeerExtDontCapabilityNegotiate
            TruthValue,
        bgpPeerExtCapabilityOrf
            INTEGER,
        bgpPeerExtNextHopSelf
            TruthValue,
        bgpPeerExtRemovePrivateAS
            TruthValue,
        bgpPeerExtSendCommunity
            INTEGER,
        bgpPeerExtSoftReconfig
            TruthValue,
        bgpPeerExtRouteReflectorClient
            TruthValue,
        bgpPeerExtRouteServerClient
            TruthValue,
        bgpPeerExtAttrUnchangedASPath
            TruthValue,
        bgpPeerExtAttrUnchangedNexthop
            TruthValue,
        bgpPeerExtAttrUnchangedMed
            TruthValue,
        bgpPeerExtUpdateSource
            Integer32,
        bgpPeerExtDefaultOriginate
            TruthValue,
        bgpPeerExtPort
            Integer32,
        bgpPeerExtWeight
            Integer32,
        bgpPeerExtCollideEstablished
            TruthValue,
        bgpPeerExtOverrideCapability
            TruthValue,
        bgpPeerExtStrictCapabilityMatch
            TruthValue,
        bgpPeerExtAllowasIn
            Integer32,
        bgpPeerExtAsOverride
            TruthValue,
        bgpPeerExtMemberOfPeerGroupIndex
            Integer32
    }

bgpPeerExtPeer OBJECT-TYPE
    SYNTAX          InetAddress
    MAX-ACCESS      not-accessible
    STATUS          current
    DESCRIPTION
        "The Network Layer address of the peer where the route
        information was learned. An implementation is only 
        required to support an IPv4 peer."
    ::= { bgpPeerExtEntry 1 }

bgpPeerExtRemoteAS OBJECT-TYPE
    SYNTAX          INTEGER (1..65535)
    MAX-ACCESS      read-write
    STATUS          current
    DESCRIPTION
        "Specify AS number of BGP peer."
    ::= { bgpPeerExtEntry 2 }
    
bgpPeerExtRowStats OBJECT-TYPE
    SYNTAX          RowStatus
    MAX-ACCESS      read-write
    STATUS          current
    DESCRIPTION
        "The status of this conceptual row.Now only realize CreateAndGo 
        and Destroy and Active.
        1 means Active
        4 means CreateAndGo
        6 means Destroy"
    ::= { bgpPeerExtEntry 3 }
        
bgpPeerExtActivate OBJECT-TYPE
    SYNTAX          TruthValue
    MAX-ACCESS      read-write
    STATUS          current
    DESCRIPTION
        "Enable the Address Family for this Neighbor."
    ::= { bgpPeerExtEntry 4 }

bgpPeerExtPassive OBJECT-TYPE
    SYNTAX          TruthValue
    MAX-ACCESS      read-write
    STATUS          current
    DESCRIPTION
        "Don't send open messages to this peer."
    ::= { bgpPeerExtEntry 5 }

bgpPeerExtDescription OBJECT-TYPE
    SYNTAX          OCTET STRING (SIZE(0..80))
    MAX-ACCESS      read-write
    STATUS          current
    DESCRIPTION
        "Up to 80 characters describing this peer."
    ::= { bgpPeerExtEntry 6 }        

bgpPeerExtCapabilityRouteRefresh OBJECT-TYPE
    SYNTAX          TruthValue
    MAX-ACCESS      read-write
    STATUS          current
    DESCRIPTION
        "Advertise route-refresh capability to this peer."
    ::= { bgpPeerExtEntry 7 }

bgpPeerExtCapabilityDynamic OBJECT-TYPE
    SYNTAX          TruthValue
    MAX-ACCESS      read-write
    STATUS          current
    DESCRIPTION
        "Advertise dynamic capability to this peer."
    ::= { bgpPeerExtEntry 8 }
        
bgpPeerExtDontCapabilityNegotiate OBJECT-TYPE
    SYNTAX          TruthValue
    MAX-ACCESS      read-write
    STATUS          current
    DESCRIPTION
        "Do not perform capability negotiation."
    ::= { bgpPeerExtEntry 9 }

bgpPeerExtCapabilityOrf OBJECT-TYPE
    SYNTAX          INTEGER
    {
        send(1),
        receive(2),
        both(3),
        none(4)
    }
    MAX-ACCESS      read-write
    STATUS          current
    DESCRIPTION
        "Advertise prefixlist ORF capability to this peer."
    ::= { bgpPeerExtEntry 10 }        

bgpPeerExtNextHopSelf OBJECT-TYPE
    SYNTAX          TruthValue
    MAX-ACCESS      read-write
    STATUS          current
    DESCRIPTION
        "Disable the next hop calculation for this neighbor."
    ::= { bgpPeerExtEntry 11 }

bgpPeerExtRemovePrivateAS OBJECT-TYPE
    SYNTAX          TruthValue
    MAX-ACCESS      read-write
    STATUS          current
    DESCRIPTION
        "Remove private AS number from outbound updates."
    ::= { bgpPeerExtEntry 12 }

bgpPeerExtSendCommunity OBJECT-TYPE
    SYNTAX          INTEGER
    {
        standard(1),
        extended(2),
        both(3),
        none(4)
    }
    MAX-ACCESS      read-write
    STATUS          current
    DESCRIPTION
        "Send Community attribute to this neighbor."
    ::= { bgpPeerExtEntry 13 }        

bgpPeerExtSoftReconfig OBJECT-TYPE
    SYNTAX          TruthValue
    MAX-ACCESS      read-write
    STATUS          current
    DESCRIPTION
        "Allow inbound soft reconfiguration for this peer."
    ::= { bgpPeerExtEntry 14 }  
        
bgpPeerExtRouteReflectorClient OBJECT-TYPE
    SYNTAX          TruthValue
    MAX-ACCESS      read-write
    STATUS          current
    DESCRIPTION
        "Configure a neighbor as Route Reflector client."
    ::= { bgpPeerExtEntry 15 }        

bgpPeerExtRouteServerClient OBJECT-TYPE
    SYNTAX          TruthValue
    MAX-ACCESS      read-write
    STATUS          current
    DESCRIPTION
        "Configure a neighbor as Route Server client."
    ::= { bgpPeerExtEntry 16 }           

bgpPeerExtAttrUnchangedASPath OBJECT-TYPE
    SYNTAX          TruthValue
    MAX-ACCESS      read-write
    STATUS          current
    DESCRIPTION
        "BGP As-path attribute is propagated unchanged to this neighbor."
    ::= { bgpPeerExtEntry 17 }       

bgpPeerExtAttrUnchangedNexthop OBJECT-TYPE
    SYNTAX          TruthValue
    MAX-ACCESS      read-write
    STATUS          current
    DESCRIPTION
        "BGP Next-hop attribute is propagated unchanged to this neighbor."
    ::= { bgpPeerExtEntry 18 }    

bgpPeerExtAttrUnchangedMed OBJECT-TYPE
    SYNTAX          TruthValue
    MAX-ACCESS      read-write
    STATUS          current
    DESCRIPTION
        "BGP Med attribute is propagated unchanged to this neighbor."
    ::= { bgpPeerExtEntry 19 }    

bgpPeerExtUpdateSource OBJECT-TYPE
    SYNTAX          Integer32
    MAX-ACCESS      read-write
    STATUS          current
    DESCRIPTION
        "Interface ifindex."
    ::= { bgpPeerExtEntry 20 }  

bgpPeerExtDefaultOriginate OBJECT-TYPE
    SYNTAX          TruthValue
    MAX-ACCESS      read-write
    STATUS          current
    DESCRIPTION
        "Originate default route to this peer."
    ::= { bgpPeerExtEntry 21 }  

bgpPeerExtPort OBJECT-TYPE
    SYNTAX          Integer32
    MAX-ACCESS      read-write
    STATUS          current
    DESCRIPTION
        "Neighbor's BGP TCP port number."
    ::= { bgpPeerExtEntry 22 }  

bgpPeerExtWeight OBJECT-TYPE
    SYNTAX          Integer32
    MAX-ACCESS      read-write
    STATUS          current
    DESCRIPTION
        "Set default weight for routes from this peer. Default: 0."
    ::= { bgpPeerExtEntry 23 }  

bgpPeerExtCollideEstablished OBJECT-TYPE
    SYNTAX          TruthValue
    MAX-ACCESS      read-write
    STATUS          current
    DESCRIPTION
        "Include Neighbor in Established State for Collision Detection."
    ::= { bgpPeerExtEntry 24 }  

bgpPeerExtOverrideCapability OBJECT-TYPE
    SYNTAX          TruthValue
    MAX-ACCESS      read-write
    STATUS          current
    DESCRIPTION
        "Override capability negotiation result."
    ::= { bgpPeerExtEntry 25 }          

bgpPeerExtStrictCapabilityMatch OBJECT-TYPE
    SYNTAX          TruthValue
    MAX-ACCESS      read-write
    STATUS          current
    DESCRIPTION
        "Strict capability negotiation match."
    ::= { bgpPeerExtEntry 26 }       

bgpPeerExtAllowasIn OBJECT-TYPE
    SYNTAX          Integer32 (0..10)
    MAX-ACCESS      read-write
    STATUS          current
    DESCRIPTION
        "Strict capability negotiation match."
    ::= { bgpPeerExtEntry 27 }     

bgpPeerExtAsOverride OBJECT-TYPE
    SYNTAX          TruthValue
    MAX-ACCESS      read-write
    STATUS          current
    DESCRIPTION
        "override AS path."
    ::= { bgpPeerExtEntry 28 }     
        
bgpPeerExtMemberOfPeerGroupIndex OBJECT-TYPE
    SYNTAX          Integer32
    MAX-ACCESS      read-write
    STATUS          current
    DESCRIPTION
        "override AS path."
    ::= { bgpPeerExtEntry 29 }     

--
-- BGP4 Peer group
-- 

bgpPeerGroupTable OBJECT-TYPE
    SYNTAX          SEQUENCE OF BgpPeerGroupEntry
    MAX-ACCESS      not-accessible
    STATUS          current
    DESCRIPTION
        "Configure peer-group." 
    ::= { bgp 5 }

bgpPeerGroupEntry OBJECT-TYPE
    SYNTAX          BgpPeerGroupEntry
    MAX-ACCESS      not-accessible
    STATUS          current
    DESCRIPTION
        "Information about a path to a network received from a peer."
    INDEX { bgpPeerGroupIndex }
    ::= { bgpPeerGroupTable 1 }

BgpPeerGroupEntry    ::=    
    SEQUENCE {
        bgpPeerGroupIndex
            Integer32,
        bgpPeerGroupName
            OCTET STRING,
        bgpPeerGroupRowStats
            RowStatus,
        bgpPeerGroupRemoteAS
            INTEGER,
        bgpPeerGroupActivate
            TruthValue,
        bgpPeerGroupPassive
            TruthValue,
        bgpPeerGroupDescription
            OCTET STRING,
        bgpPeerGroupCapabilityRouteRefresh
            TruthValue,
        bgpPeerGroupCapabilityDynamic
            TruthValue,
        bgpPeerGroupDontCapabilityNegotiate
            TruthValue,
        bgpPeerGroupCapabilityOrf
            INTEGER,
        bgpPeerGroupNextHopSelf
            TruthValue,
        bgpPeerGroupRemovePrivateAS
            TruthValue,
        bgpPeerGroupSendCommunity
            INTEGER,
        bgpPeerGroupSoftReconfig
            TruthValue,
        bgpPeerGroupRouteReflectorClient
            TruthValue,
        bgpPeerGroupRouteServerClient       
            TruthValue,
        bgpPeerGroupAttrUnchangedASPath     
            TruthValue,
        bgpPeerGroupAttrUnchangedNexthop    
            TruthValue,
        bgpPeerGroupAttrUnchangedMed        
            TruthValue,
        bgpPeerGroupUpdateSource        		
            Integer32,
        bgpPeerGroupDefaultOriginate        
            TruthValue,
        bgpPeerGroupPort        						
            Integer32,
        bgpPeerGroupWeight        					
            Integer32,
        bgpPeerGroupCollideEstablished      
            TruthValue,
        bgpPeerGroupOverrideCapability      
            TruthValue,
        bgpPeerGroupStrictCapabilityMatch   
            TruthValue,
        bgpPeerGroupAllowasIn        				
            Integer32,
        bgpPeerGroupAsOverride        			
            TruthValue 
    }

bgpPeerGroupIndex OBJECT-TYPE
    SYNTAX          Integer32 (1..65535)
    MAX-ACCESS      not-accessible
    STATUS          current
    DESCRIPTION
        "Peer group index."
    ::= { bgpPeerGroupEntry 1 }

bgpPeerGroupName OBJECT-TYPE
    SYNTAX          OCTET STRING (SIZE(1..20))
    MAX-ACCESS      read-write
    STATUS          current
    DESCRIPTION
        "Peer group name."
    ::= { bgpPeerGroupEntry 2 }        
    
bgpPeerGroupRowStats OBJECT-TYPE
    SYNTAX          RowStatus
    MAX-ACCESS      read-write
    STATUS          current
    DESCRIPTION
        "The status of this conceptual row.Now only realize CreateAndGo 
        and Destroy and Active.
        1 means Active
        4 means CreateAndGo
        6 means Destroy"
    ::= { bgpPeerGroupEntry 3 } 
            
bgpPeerGroupRemoteAS OBJECT-TYPE
    SYNTAX          INTEGER (1..65535)
    MAX-ACCESS      read-write
    STATUS          current
    DESCRIPTION
        "Specify AS number of BGP peer."
    ::= { bgpPeerGroupEntry 4 }

bgpPeerGroupActivate OBJECT-TYPE
    SYNTAX          TruthValue
    MAX-ACCESS      read-write
    STATUS          current
    DESCRIPTION
        "Enable the Address Family for this Neighbor."
    ::= { bgpPeerGroupEntry 5 }

bgpPeerGroupPassive OBJECT-TYPE
    SYNTAX          TruthValue
    MAX-ACCESS      read-write
    STATUS          current
    DESCRIPTION
        "Don't send open messages to this peer."
    ::= { bgpPeerGroupEntry 6 }
    
bgpPeerGroupDescription OBJECT-TYPE
    SYNTAX          OCTET STRING (SIZE(0..80))
    MAX-ACCESS      read-write
    STATUS          current
    DESCRIPTION
        "Up to 80 characters describing this peer."
    ::= { bgpPeerGroupEntry 7 }
        
bgpPeerGroupCapabilityRouteRefresh OBJECT-TYPE
    SYNTAX          TruthValue
    MAX-ACCESS      read-write
    STATUS          current
    DESCRIPTION
        "Advertise route-refresh capability to this peer."
    ::= { bgpPeerGroupEntry 8 }

bgpPeerGroupCapabilityDynamic OBJECT-TYPE
    SYNTAX          TruthValue
    MAX-ACCESS      read-write
    STATUS          current
    DESCRIPTION
        "Advertise dynamic capability to this peer."
    ::= { bgpPeerGroupEntry 9 }
        
bgpPeerGroupDontCapabilityNegotiate OBJECT-TYPE
    SYNTAX          TruthValue
    MAX-ACCESS      read-write
    STATUS          current
    DESCRIPTION
        "Do not perform capability negotiation."
    ::= { bgpPeerGroupEntry 10 }

bgpPeerGroupCapabilityOrf OBJECT-TYPE
    SYNTAX          INTEGER
    {
        send(1),
        receive(2),
        both(3),
        none(4)
    }
    MAX-ACCESS      read-write
    STATUS          current
    DESCRIPTION
        "Advertise prefixlist ORF capability to this peer."
    ::= { bgpPeerGroupEntry 11 }        

bgpPeerGroupNextHopSelf OBJECT-TYPE
    SYNTAX          TruthValue
    MAX-ACCESS      read-write
    STATUS          current
    DESCRIPTION
        "Disable the next hop calculation for this neighbor."
    ::= { bgpPeerGroupEntry 12 }

bgpPeerGroupRemovePrivateAS OBJECT-TYPE
    SYNTAX          TruthValue
    MAX-ACCESS      read-write
    STATUS          current
    DESCRIPTION
        "Remove private AS number from outbound updates."
    ::= { bgpPeerGroupEntry 13 }

bgpPeerGroupSendCommunity OBJECT-TYPE
    SYNTAX          INTEGER
    {
        standard(1),
        extended(2),
        both(3),
        none(4)
    }
    MAX-ACCESS      read-write
    STATUS          current
    DESCRIPTION
        "Send Community attribute to this neighbor."
    ::= { bgpPeerGroupEntry 14 }        

bgpPeerGroupSoftReconfig OBJECT-TYPE
    SYNTAX          TruthValue
    MAX-ACCESS      read-write
    STATUS          current
    DESCRIPTION
        "Allow inbound soft reconfiguration for this peer."
    ::= { bgpPeerGroupEntry 15 }  
        
bgpPeerGroupRouteReflectorClient OBJECT-TYPE
    SYNTAX          TruthValue
    MAX-ACCESS      read-write
    STATUS          current
    DESCRIPTION
        "Configure a neighbor as Route Reflector client."
    ::= { bgpPeerGroupEntry 16 }        

bgpPeerGroupRouteServerClient OBJECT-TYPE
    SYNTAX          TruthValue
    MAX-ACCESS      read-write
    STATUS          current
    DESCRIPTION
        "Configure a neighbor as Route Server client."
    ::= { bgpPeerGroupEntry 17 }           

bgpPeerGroupAttrUnchangedASPath OBJECT-TYPE
    SYNTAX          TruthValue
    MAX-ACCESS      read-write
    STATUS          current
    DESCRIPTION
        "BGP As-path attribute is propagated unchanged to this neighbor."
    ::= { bgpPeerGroupEntry 18 }       

bgpPeerGroupAttrUnchangedNexthop OBJECT-TYPE
    SYNTAX          TruthValue
    MAX-ACCESS      read-write
    STATUS          current
    DESCRIPTION
        "BGP Next-hop attribute is propagated unchanged to this neighbor."
    ::= { bgpPeerGroupEntry 19 }    

bgpPeerGroupAttrUnchangedMed OBJECT-TYPE
    SYNTAX          TruthValue
    MAX-ACCESS      read-write
    STATUS          current
    DESCRIPTION
        "BGP Med attribute is propagated unchanged to this neighbor."
    ::= { bgpPeerGroupEntry 20 }    

bgpPeerGroupUpdateSource OBJECT-TYPE
    SYNTAX          Integer32
    MAX-ACCESS      read-write
    STATUS          current
    DESCRIPTION
        "Interface ifindex."
    ::= { bgpPeerGroupEntry 21 }  

bgpPeerGroupDefaultOriginate OBJECT-TYPE
    SYNTAX          TruthValue
    MAX-ACCESS      read-write
    STATUS          current
    DESCRIPTION
        "Originate default route to this peer."
    ::= { bgpPeerGroupEntry 22 }  

bgpPeerGroupPort OBJECT-TYPE
    SYNTAX          Integer32
    MAX-ACCESS      read-write
    STATUS          current
    DESCRIPTION
        "Neighbor's BGP TCP port number."
    ::= { bgpPeerGroupEntry 23 }  

bgpPeerGroupWeight OBJECT-TYPE
    SYNTAX          Integer32
    MAX-ACCESS      read-write
    STATUS          current
    DESCRIPTION
        "Set default weight for routes from this peer."
    ::= { bgpPeerGroupEntry 24 }  

bgpPeerGroupCollideEstablished OBJECT-TYPE
    SYNTAX          TruthValue
    MAX-ACCESS      read-write
    STATUS          current
    DESCRIPTION
        "Include Neighbor in Established State for Collision Detection."
    ::= { bgpPeerGroupEntry 25 }  

bgpPeerGroupOverrideCapability OBJECT-TYPE
    SYNTAX          TruthValue
    MAX-ACCESS      read-write
    STATUS          current
    DESCRIPTION
        "Override capability negotiation result."
    ::= { bgpPeerGroupEntry 26 }          

bgpPeerGroupStrictCapabilityMatch OBJECT-TYPE
    SYNTAX          TruthValue
    MAX-ACCESS      read-write
    STATUS          current
    DESCRIPTION
        "Strict capability negotiation match."
    ::= { bgpPeerGroupEntry 27 }       

bgpPeerGroupAllowasIn OBJECT-TYPE
    SYNTAX          Integer32 (0..10)
    MAX-ACCESS      read-write
    STATUS          current
    DESCRIPTION
        "Strict capability negotiation match."
    ::= { bgpPeerGroupEntry 28 }     

bgpPeerGroupAsOverride OBJECT-TYPE
    SYNTAX          TruthValue
    MAX-ACCESS      read-write
    STATUS          current
    DESCRIPTION
        "override AS path."
    ::= { bgpPeerGroupEntry 29 }     
        

--
--BGP address family
--        
bgpAddressFamily     OBJECT IDENTIFIER    ::= { bgp 6 }
		
bgpAddressFamilyName OBJECT-TYPE
    SYNTAX          OCTET STRING (SIZE(0..80))
    MAX-ACCESS      read-only
    STATUS          current
    DESCRIPTION 
        "address family name."
    ::= { bgpAddressFamily 1 }

bgpAddressFamilyRouterId OBJECT-TYPE
    SYNTAX          OCTET STRING (SIZE(0..80))
    MAX-ACCESS      read-write
    STATUS          current
    DESCRIPTION
        "Manually configured router identifier."
    ::= { bgpAddressFamily 2 }

bgpAddressFamilyRedistConnect OBJECT-TYPE
    SYNTAX          TruthValue
    MAX-ACCESS      read-write
    STATUS          current
    DESCRIPTION
        "Redistribute connect information from another routing protocol."
    ::= { bgpAddressFamily 3 }

bgpAddressFamilyRedistStatic OBJECT-TYPE
    SYNTAX          TruthValue
    MAX-ACCESS      read-write
    STATUS          current
    DESCRIPTION
        "Redistribute static information from another routing protocol."
    ::= { bgpAddressFamily 4 }

bgpAddressFamilyRedistRip OBJECT-TYPE
    SYNTAX          TruthValue
    MAX-ACCESS      read-write
    STATUS          current
    DESCRIPTION
        "Redistribute RIP information from another routing protocol."
    ::= { bgpAddressFamily 5 }

bgpAddressFamilyRedistOspf OBJECT-TYPE
    SYNTAX          TruthValue
    MAX-ACCESS      read-write
    STATUS          current
    DESCRIPTION
        "Redistribute OSPF information from another routing protocol."
    ::= { bgpAddressFamily 6 }

bgpAddressFamilySynchronization OBJECT-TYPE
    SYNTAX          TruthValue
    MAX-ACCESS      read-write
    STATUS          current
    DESCRIPTION
        "Perform IGP synchronization."
    ::= { bgpAddressFamily 7 }

bgpAddressFamilyDefaultInfoOrig OBJECT-TYPE
    SYNTAX          TruthValue
    MAX-ACCESS      read-write
    STATUS          current
    DESCRIPTION
        "Control distribution of default information."
    ::= { bgpAddressFamily 8 }

bgpAddressFamilyNetworkSynch OBJECT-TYPE
    SYNTAX          TruthValue
    MAX-ACCESS      read-write
    STATUS          current
    DESCRIPTION
        "Perform IGP synchronization on network routes."
    ::= { bgpAddressFamily 9 }


--
--BGP clear table
--
bgpClearTable     OBJECT IDENTIFIER    ::= { bgp 7 }

bgpClearAll OBJECT-TYPE
    SYNTAX          TruthValue
    MAX-ACCESS      read-write
    STATUS          current
    DESCRIPTION
        "This node only supports set operation.
        If the value is true, it will clear all of statistics."
    ::= { bgpClearTable 1 }

bgpClearExternalPeers OBJECT-TYPE
    SYNTAX          TruthValue
    MAX-ACCESS      read-write
    STATUS          current
    DESCRIPTION
        "This node only supports set operation.
        If the value is true, it will clear all of statistics."
    ::= { bgpClearTable 2 }

bgpClearUnicastSoftOut OBJECT-TYPE
    SYNTAX          TruthValue
    MAX-ACCESS      read-write
    STATUS          current
    DESCRIPTION
        "This node only supports set operation.
        If the value is true, it will clear all of statistics."
    ::= { bgpClearTable 3 }

bgpClearMulticastSoftOut OBJECT-TYPE
    SYNTAX          TruthValue
    MAX-ACCESS      read-write
    STATUS          current
    DESCRIPTION
        "This node only supports set operation.
        If the value is true, it will clear all of statistics."
    ::= { bgpClearTable 4 }

bgpClearVpnv4UnicastSoftOut OBJECT-TYPE
    SYNTAX          TruthValue
    MAX-ACCESS      read-write
    STATUS          current
    DESCRIPTION
        "This node only supports set operation.
        If the value is true, it will clear all of statistics."
    ::= { bgpClearTable 5 }

bgpClearExternalSoftOut OBJECT-TYPE
    SYNTAX          TruthValue
    MAX-ACCESS      read-write
    STATUS          current
    DESCRIPTION
        "This node only supports set operation.
        If the value is true, it will clear all of statistics."
    ::= { bgpClearTable 6 }

bgpClearExternalUnicastSoftOut OBJECT-TYPE
    SYNTAX          TruthValue
    MAX-ACCESS      read-write
    STATUS          current
    DESCRIPTION
        "This node only supports set operation.
        If the value is true, it will clear all of statistics."
    ::= { bgpClearTable 7 }

bgpClearExternalMulticastSoftOut OBJECT-TYPE
    SYNTAX          TruthValue
    MAX-ACCESS      read-write
    STATUS          current
    DESCRIPTION
        "This node only supports set operation.
        If the value is true, it will clear all of statistics."
    ::= { bgpClearTable 8 }

bgpClearSoftIn OBJECT-TYPE
    SYNTAX          TruthValue
    MAX-ACCESS      read-write
    STATUS          current
    DESCRIPTION
        "This node only supports set operation.
        If the value is true, it will clear all of statistics."
    ::= { bgpClearTable 9 }

bgpClearInPrefixFilter OBJECT-TYPE
    SYNTAX          TruthValue
    MAX-ACCESS      read-write
    STATUS          current
    DESCRIPTION
        "This node only supports set operation.
        If the value is true, it will clear all of statistics."
    ::= { bgpClearTable 10 }

bgpClearUnicastSoftIn OBJECT-TYPE
    SYNTAX          TruthValue
    MAX-ACCESS      read-write
    STATUS          current
    DESCRIPTION
        "This node only supports set operation.
        If the value is true, it will clear all of statistics."
    ::= { bgpClearTable 11 }

bgpClearMulticastSoftIn OBJECT-TYPE
    SYNTAX          TruthValue
    MAX-ACCESS      read-write
    STATUS          current
    DESCRIPTION
        "This node only supports set operation.
        If the value is true, it will clear all of statistics."
    ::= { bgpClearTable 12 }

bgpClearUnicastInPrefixFilter OBJECT-TYPE
    SYNTAX          TruthValue
    MAX-ACCESS      read-write
    STATUS          current
    DESCRIPTION
        "This node only supports set operation.
        If the value is true, it will clear all of statistics."
    ::= { bgpClearTable 13 }

bgpClearMulticastInPrefixFilter OBJECT-TYPE
    SYNTAX          TruthValue
    MAX-ACCESS      read-write
    STATUS          current
    DESCRIPTION
        "This node only supports set operation.
        If the value is true, it will clear all of statistics."
    ::= { bgpClearTable 14 }

bgpClearVpnv4UnicastSoftIn OBJECT-TYPE
    SYNTAX          TruthValue
    MAX-ACCESS      read-write
    STATUS          current
    DESCRIPTION
        "This node only supports set operation.
        If the value is true, it will clear all of statistics."
    ::= { bgpClearTable 15 }

bgpClearExternalSoftIn OBJECT-TYPE
    SYNTAX          TruthValue
    MAX-ACCESS      read-write
    STATUS          current
    DESCRIPTION
        "This node only supports set operation.
        If the value is true, it will clear all of statistics."
    ::= { bgpClearTable 16 }

bgpClearExternalInPrefixFilter OBJECT-TYPE
    SYNTAX          TruthValue
    MAX-ACCESS      read-write
    STATUS          current
    DESCRIPTION
        "This node only supports set operation.
        If the value is true, it will clear all of statistics."
    ::= { bgpClearTable 17 }

bgpClearExternalUnicastSoftIn OBJECT-TYPE
    SYNTAX          TruthValue
    MAX-ACCESS      read-write
    STATUS          current
    DESCRIPTION
        "This node only supports set operation.
        If the value is true, it will clear all of statistics."
    ::= { bgpClearTable 18 }

bgpClearExternalMulticastSoftIn OBJECT-TYPE
    SYNTAX          TruthValue
    MAX-ACCESS      read-write
    STATUS          current
    DESCRIPTION
        "This node only supports set operation.
        If the value is true, it will clear all of statistics."
    ::= { bgpClearTable 19 }

bgpClearExternalUnicastInPrefixFilter OBJECT-TYPE
    SYNTAX          TruthValue
    MAX-ACCESS      read-write
    STATUS          current
    DESCRIPTION
        "This node only supports set operation.
        If the value is true, it will clear all of statistics."
    ::= { bgpClearTable 20 }

bgpClearExternalMulticastInPrefixFilter OBJECT-TYPE
    SYNTAX          TruthValue
    MAX-ACCESS      read-write
    STATUS          current
    DESCRIPTION
        "This node only supports set operation.
        If the value is true, it will clear all of statistics."
    ::= { bgpClearTable 21 }

bgpClearUnicastSoft OBJECT-TYPE
    SYNTAX          TruthValue
    MAX-ACCESS      read-write
    STATUS          current
    DESCRIPTION
        "This node only supports set operation.
        If the value is true, it will clear all of statistics."
    ::= { bgpClearTable 22 }

bgpClearMulticastSoft OBJECT-TYPE
    SYNTAX          TruthValue
    MAX-ACCESS      read-write
    STATUS          current
    DESCRIPTION
        "This node only supports set operation.
        If the value is true, it will clear all of statistics."
    ::= { bgpClearTable 23 }

bgpClearVpnv4UnicastSoft OBJECT-TYPE
    SYNTAX          TruthValue
    MAX-ACCESS      read-write
    STATUS          current
    DESCRIPTION
        "This node only supports set operation.
        If the value is true, it will clear all of statistics."
    ::= { bgpClearTable 24 }

bgpClearExternalUnicastSoft OBJECT-TYPE
    SYNTAX          TruthValue
    MAX-ACCESS      read-write
    STATUS          current
    DESCRIPTION
        "This node only supports set operation.
        If the value is true, it will clear all of statistics."
    ::= { bgpClearTable 25 }

bgpClearExternalMulticastSoft OBJECT-TYPE
    SYNTAX          TruthValue
    MAX-ACCESS      read-write
    STATUS          current
    DESCRIPTION
        "This node only supports set operation.
             If the value is true, it will clear all of statistics."
    ::= { bgpClearTable 26 }

bgpClearDampening OBJECT-TYPE
    SYNTAX          TruthValue
    MAX-ACCESS      read-write
    STATUS          current
    DESCRIPTION
        "This node only supports set operation.
        If the value is true, it will clear all of statistics."
    ::= { bgpClearTable 27 }

-- Sub Module: MPLS
mplsLspTunnelingTable OBJECT-TYPE
    SYNTAX  SEQUENCE OF MplsLspTunnelingEntry
    MAX-ACCESS not-accessible
    STATUS   current
    DESCRIPTION
     "Tunnel a transit LSP."
    ::= { mpls 1 }

mplsLspTunnelingEntry OBJECT-TYPE
    SYNTAX  MplsLspTunnelingEntry
    MAX-ACCESS not-accessible
    STATUS current
    DESCRIPTION
     "Entry of mplsLspTunnelingTable."
    INDEX   { mplsLspTunnelingInLabel}
    ::= { mplsLspTunnelingTable 1 }

MplsLspTunnelingEntry ::=
    SEQUENCE {
        mplsLspTunnelingInLabel         Integer32,
        mplsLspTunnelingOutLabel  Integer32,
        mplsLspTunnelingDestAddr IpAddress,
        mplsLspTunnelingMaskLen  Integer32,
        mplsLspTunnelingRowStatus RowStatus,
        mplsLspTunnelingState   INTEGER
        }

mplsLspTunnelingInLabel OBJECT-TYPE
    SYNTAX  Integer32 (16..1048575)
    MAX-ACCESS not-accessible
    STATUS current
    DESCRIPTION
     "Incoming Label Value between 16 and 1048575."
    ::= { mplsLspTunnelingEntry 1 }


mplsLspTunnelingOutLabel OBJECT-TYPE
    SYNTAX  Integer32 (16..1048575)
    MAX-ACCESS read-write
    STATUS current
    DESCRIPTION
     "Outgoing label of the transit lsp,0,3,16-1048575."
    ::= { mplsLspTunnelingEntry 2 }

mplsLspTunnelingDestAddr OBJECT-TYPE
    SYNTAX  IpAddress
    MAX-ACCESS read-write
    STATUS current
    DESCRIPTION
     "IPv4 network FEC for identifying tunnel LSP."
    ::= { mplsLspTunnelingEntry 3 }

mplsLspTunnelingMaskLen OBJECT-TYPE
    SYNTAX  Integer32
    MAX-ACCESS read-write
    STATUS current
    DESCRIPTION
     "Length of iPv4 network FEC mask for identifying tunnel LSP,
      between 0 and 32."
    ::= { mplsLspTunnelingEntry 4 }
        
mplsLspTunnelingRowStatus OBJECT-TYPE
    SYNTAX RowStatus
    MAX-ACCESS read-create
    STATUS current
    DESCRIPTION
        "The status of this conceptual row.Now only realize CreateAndGo 
            and Destroy and Active.
            1 means Active
            4 means CreateAndGo
            6 means Destroy"
	::= { mplsLspTunnelingEntry 10 }

mplsLspTunnelingState OBJECT-TYPE
    SYNTAX INTEGER {selected(1),non-selected(2)}
    MAX-ACCESS read-only
    STATUS current
    DESCRIPTION
       "The state of the LSP tunneling entry.The meanings of the values are:
        selected(1)     -  the LSP tunneling entry is selected;
        non-selected(2) -  the LSP tunneling entry is not selected;"
    ::= { mplsLspTunnelingEntry 11 }   

mplsMapRouteTable OBJECT-TYPE
    SYNTAX  SEQUENCE OF MplsMapRouteEntry
    MAX-ACCESS not-accessible
    STATUS   current
    DESCRIPTION 
    	"mpls map-route A.B.C.D N F.G.H.I N."
    ::= { mpls 2 }

mplsMapRouteEntry OBJECT-TYPE
    SYNTAX  MplsMapRouteEntry
    MAX-ACCESS not-accessible
    STATUS current
    DESCRIPTION 
    	"Entry of mplsMapRouteTable."
    INDEX   { mplsMapRouteSrcAddr, mplsMapRouteSrcMaskLen}
    ::= { mplsMapRouteTable 1 }

MplsMapRouteEntry ::=
    SEQUENCE 
    {
        mplsMapRouteSrcAddr             IpAddress,
        mplsMapRouteSrcMaskLen		Integer32,
        mplsMapRouteDestAddr 	        IpAddress,
        mplsMapRouteDestMaskLen		Integer32,
        mplsMapRouteTunnelName          OCTET STRING,
        mplsMapRouteRowStatus  		RowStatus
        }

mplsMapRouteSrcAddr OBJECT-TYPE
    SYNTAX  IpAddress
    MAX-ACCESS not-accessible
    STATUS current
    DESCRIPTION 
    	"IpAddress of IPv4 prefix to be mapped."
    ::= { mplsMapRouteEntry 1 }
       
mplsMapRouteSrcMaskLen OBJECT-TYPE
    SYNTAX  Integer32(0..32) 
    MAX-ACCESS not-accessible
    STATUS current
    DESCRIPTION 
    	"Mask length of IPv4 prefix to be mapped.Must be between 0 and 32."
    ::= { mplsMapRouteEntry 2 }
           
mplsMapRouteDestAddr OBJECT-TYPE
    SYNTAX  IpAddress
    MAX-ACCESS read-write
    STATUS current
    DESCRIPTION 
    	"IPv4 Forwarding Equivalence Class for route to be mapped to."
    ::= { mplsMapRouteEntry 3 }

mplsMapRouteDestMaskLen OBJECT-TYPE
    SYNTAX  Integer32 
    MAX-ACCESS read-write
    STATUS current
    DESCRIPTION 
    	"Mask length for IPv4 Forwarding Equivalence Class."
    ::= { mplsMapRouteEntry 4 }

mplsMapRouteTunnelName OBJECT-TYPE
    SYNTAX  OCTET STRING(SIZE(1..20)) 
    MAX-ACCESS read-write
    STATUS current
    DESCRIPTION 
    	"MPLS tunnel for route to be mapped to. If this node is set, 
    	mplsMapRouteDestAddr and mplsMapRouteDestMaskLen are invalid."
    ::= { mplsMapRouteEntry 5 }
        
mplsMapRouteRowStatus OBJECT-TYPE
    SYNTAX RowStatus
    MAX-ACCESS read-create
    STATUS current
    DESCRIPTION
        "The status of this conceptual row.Now only realize CreateAndGo 
            and Destroy and Active.
            1 means Active
            4 means CreateAndGo
            6 means Destroy"
    ::= { mplsMapRouteEntry 10 }

mplsEnableAllInterfaces OBJECT-TYPE
    SYNTAX INTEGER
    {
       enable(1), 
       disable(2)
    }
    MAX-ACCESS read-write
    STATUS current
    DESCRIPTION
       "Enable/disable all interfaces for MPLS.
       1 is enable, 2 is disable."
    ::= { mpls 3 }   

-- mplsPropagateTtl OBJECT-TYPE
--     SYNTAX INTEGER
--     {
--        enable(1), 
--        disable(2)
--     }
--     MAX-ACCESS read-write
--     STATUS current
--     DESCRIPTION
--         "Enable/disable mpls PropagateTtl.
--         1 is enable, 2 is disable."
--     ::= { mpls 4}   

        
mplsVpwsTable OBJECT-TYPE
    SYNTAX  SEQUENCE OF MplsVpwsEntry
    MAX-ACCESS not-accessible
    STATUS   current
    DESCRIPTION 
     "Specify an MPLS Layer-2 Virtual Circuit."
    ::= { mpls 5 }

mplsVpwsEntry OBJECT-TYPE
    SYNTAX  MplsVpwsEntry
    MAX-ACCESS not-accessible
    STATUS current
    DESCRIPTION 
    	"Entry of mplsVpwsTable."
    INDEX   { mplsVpwsVcId}
    ::= { mplsVpwsTable 1 }

MplsVpwsEntry   ::=
    SEQUENCE {
        mplsVpwsVcId         	    Unsigned32,
        mplsVpwsVcName 		    OCTET STRING,
        mplsVpwsPeerAddr		    IpAddress,
        mplsVpwsIsManual		    Integer32,
        mplsVpwsMtu		    Integer32,
        mplsVpwsPwMode		    Integer32,
        mplsVpwsControlWord	    INTEGER,
        mplsVpwsStats     	    INTEGER,
        mplsVpwsRowStatus		    RowStatus,
        mplsVpwsState		    INTEGER         
        }

mplsVpwsVcId OBJECT-TYPE
    SYNTAX  Unsigned32(1..4294967295)
    MAX-ACCESS not-accessible
    STATUS current
    DESCRIPTION 
    	"Identifying value for MPLS Layer-2 Virtual Circuit."
    ::= { mplsVpwsEntry 1 }

mplsVpwsVcName OBJECT-TYPE
    SYNTAX  OCTET STRING(SIZE(1..20))
    MAX-ACCESS read-create
    STATUS current
    DESCRIPTION 
    	"Identifying string for MPLS Layer-2 Virtual Circuit.
    	Only 20 octets is accepted.."
    ::= { mplsVpwsEntry 2 }

mplsVpwsPeerAddr OBJECT-TYPE
    SYNTAX  IpAddress
    MAX-ACCESS read-create
    STATUS current
    DESCRIPTION 
    	"IPv4 Address for end-point for MPLS Layer-2 Virtual Circuit."
    ::= { mplsVpwsEntry 3 }

mplsVpwsIsManual OBJECT-TYPE
    SYNTAX  Integer32
    MAX-ACCESS read-create
    STATUS current
    DESCRIPTION 
    	"If this value is set , vc will be configured by manual.
    	1 means manual is set,2 means not."
    ::= { mplsVpwsEntry 4 }

mplsVpwsMtu OBJECT-TYPE
    SYNTAX  Integer32(576..65535)
    MAX-ACCESS read-create
    STATUS current
    DESCRIPTION 
    	"Specify l2-circuit mtu,l2-circuit mtu value <576-65535>"
    ::= { mplsVpwsEntry 5 }

mplsVpwsPwMode OBJECT-TYPE
    SYNTAX  Integer32
    MAX-ACCESS read-create
    STATUS current
    DESCRIPTION 
    	"PW raw/tagged mode.0 means default mode, 1 means raw,2 means tagged mode."
    DEFVAL { 0 }    	
    ::= { mplsVpwsEntry 6 }

mplsVpwsControlWord OBJECT-TYPE
    SYNTAX  INTEGER {enable(1),disable(2)}
    MAX-ACCESS read-create
    STATUS current
    DESCRIPTION 
       "Set control word for mpls layer2 circuit. The meanings of the values are:
        enable(1)  -  enable control word;
        disable(2) -  disable control word;"  
    DEFVAL { 2 }
    ::= { mplsVpwsEntry 7 }

mplsVpwsStats OBJECT-TYPE
    SYNTAX  INTEGER {enable(1),disable(2)}
    MAX-ACCESS read-create
    STATUS current
    DESCRIPTION 
       "Set statstics status for mpls layer2 circuit. The meanings of the values are:
        enable(1)  -  enable statistics;
        disable(2) -  disable statistics;"  
    DEFVAL { 2 }
    ::= { mplsVpwsEntry 8 }
        
mplsVpwsRowStatus OBJECT-TYPE
    SYNTAX RowStatus
    MAX-ACCESS read-create
    STATUS current
    DESCRIPTION
        "The status of this conceptual row.Now only realize CreateAndGo and Destroy and Active.
        1 means Active
        4 means CreateAndGo
        6 means Destroy"
    ::= { mplsVpwsEntry 15 }

mplsVpwsState OBJECT-TYPE
    SYNTAX  INTEGER {active(1),inactive(2)}
    MAX-ACCESS read-only
    STATUS current
    DESCRIPTION
       "The state of the mpls layer2 circuit. The meanings of the values are:
        active(1)   -  the l2 circuit is active;
        inactive(2) -  the l2 circuit is inactive;"
    ::= { mplsVpwsEntry 16 }     

-- mplsVpwsIngressPkts         OBJECT-TYPE
--     SYNTAX          Counter64
--     MAX-ACCESS      read-only
--     STATUS          current
--     DESCRIPTION
--         "Ingress packets number of mpls vpws."
--     ::= { mplsVpwsEntry 17 }
-- 
-- mplsVpwsIngressbytes         OBJECT-TYPE
--     SYNTAX          Counter64
--     MAX-ACCESS      read-only
--     STATUS          current
--     DESCRIPTION
--         "Ingress bytes number of mpls vpws."
--     ::= { mplsVpwsEntry 18 }
-- 
-- mplsVpwsEgressPkts         OBJECT-TYPE
--     SYNTAX          Counter64
--     MAX-ACCESS      read-only
--     STATUS          current
--     DESCRIPTION
--         "Egress packets number of mpls vpws."
--     ::= { mplsVpwsEntry 19 }
--     
-- mplsVpwsEgressBytes         OBJECT-TYPE
--     SYNTAX          Counter64
--     MAX-ACCESS      read-only
--     STATUS          current
--     DESCRIPTION
--         "Egress bytes number of mpls vpws."
--     ::= { mplsVpwsEntry 20 }            
        	
mplsVpwsFibTable OBJECT-TYPE
    SYNTAX  SEQUENCE OF MplsVpwsFibEntry
    MAX-ACCESS not-accessible
    STATUS   current
    DESCRIPTION
     "Table of Layer-2 MPLS Virtual Circuit FIB entry."
    ::= { mpls 6 }

mplsVpwsFibEntry OBJECT-TYPE
    SYNTAX  MplsVpwsFibEntry
    MAX-ACCESS not-accessible
    STATUS current
    DESCRIPTION 
    	"A Layer-2 MPLS Virtual Circuit FIB entry."
    INDEX   { mplsVpwsFibVcId}
    ::= { mplsVpwsFibTable 1 }

MplsVpwsFibEntry   ::=
    SEQUENCE {
        mplsVpwsFibVcId         	Unsigned32,
        mplsVpwsFibInLabel 	Integer32,
        mplsVpwsFibOutLabel	Integer32,
        mplsVpwsFibRowStatus	RowStatus
        }

mplsVpwsFibVcId OBJECT-TYPE
    SYNTAX Unsigned32(1..4294967295)
    MAX-ACCESS not-accessible
    STATUS current
    DESCRIPTION 
    	"Virtual Circuit Identifier."
    ::= { mplsVpwsFibEntry 1 }


mplsVpwsFibInLabel OBJECT-TYPE
    SYNTAX Integer32 (16..1048575)
    MAX-ACCESS read-write
    STATUS current
    DESCRIPTION 
    	"In-coming Label <16-1048575>."
    ::= { mplsVpwsFibEntry 2 }

mplsVpwsFibOutLabel OBJECT-TYPE
    SYNTAX Integer32 (16..1048575)
    MAX-ACCESS read-write
    STATUS current
    DESCRIPTION 
    	"Out-going Label <16-1048575>."
    ::= { mplsVpwsFibEntry 3 }

mplsVpwsFibRowStatus OBJECT-TYPE
    SYNTAX RowStatus
    MAX-ACCESS read-create
    STATUS current
    DESCRIPTION
        "The status of this conceptual row.Now only realize CreateAndGo and Destroy and Active.
        1 means Active
        4 means CreateAndGo
        6 means Destroy"
    ::= { mplsVpwsFibEntry 4 }
	
--mplsVplsVlanTable OBJECT-TYPE
--    SYNTAX OCTET STRING
--    MAX-ACCESS read-write
--    STATUS current
--    DESCRIPTION 
--    	"This defines the minnum and maxnum of vlan id.The string must be 'min,max',
--    	and '0,0' means set vpls vlan id range to default(0,0).
--    	Minnum,maxnum must be between 2 and 4096."
--    ::= { mpls 7 }

mplsVplsTable OBJECT-TYPE
    SYNTAX  SEQUENCE OF MplsVplsEntry
    MAX-ACCESS not-accessible
    STATUS   current
    DESCRIPTION 
     "Instance of MPLS based Virtual Private Lan Service (VPLS)."
    ::= { mpls 8 }

mplsVplsEntry OBJECT-TYPE
    SYNTAX  MplsVplsEntry
    MAX-ACCESS not-accessible
    STATUS current
    DESCRIPTION 
    	"The entry of mplsVplsTable."
    INDEX   { mplsVplsId }
    ::= { mplsVplsTable 1 }

MplsVplsEntry   ::=
    SEQUENCE {
        mplsVplsId         	Unsigned32,
        mplsVplsName 		OCTET STRING,
        mplsVplsWhiteList     INTEGER,        
--        mplsVplsEtreeType		INTEGER,
        mplsVplsRowStatus	RowStatus,
        mplsVplsDescription	OCTET STRING,
        mplsVplsMtu		Integer32,
        mplsVplsMacLearning INTEGER,
        mplsVplsMacLimitNum Unsigned32,
        mplsVplsMacLimitAction INTEGER,
        mplsVplsAllowFlooding INTEGER,
--        mplsVplsAllowUnknownUnicast INTEGER,
--        mplsVplsAllowMulticast INTEGER,
        mplsVplsState INTEGER
--        mplsVplsMPeerR Integer32,
--        mplsVplsMPeerT Integer32,
--        mplsVplsSPeer Integer32
        }

mplsVplsId OBJECT-TYPE
    SYNTAX  Unsigned32(1..4294967295)
    MAX-ACCESS not-accessible
    STATUS current
    DESCRIPTION 
    	"Identifying value for VPLS."
    ::= { mplsVplsEntry 1 }

mplsVplsName OBJECT-TYPE
    SYNTAX  OCTET STRING (SIZE(0..256))
    MAX-ACCESS read-write
    STATUS current
    DESCRIPTION 
        "Identifying string for VPLS."
    ::= { mplsVplsEntry 2 }

-- mplsVplsEtreeType     OBJECT-TYPE
--     SYNTAX          INTEGER {root(1),leaf(2)}
--     MAX-ACCESS      read-write
--     STATUS          current
--     DESCRIPTION
--         "Specify the E-tree type the VSI is emulating. The meanings of the values are:
--         root(1)  -  All AC in the VSI on this node will be root-ACs;
--         leaf(2) -  All AC in the VSI on this node will be leaf-ACs;"  
--     DEFVAL { 1 }
--     ::= { mplsVplsEntry 3 }

mplsVplsWhiteList     OBJECT-TYPE
    SYNTAX          INTEGER {enable(1),disable(2)}
    MAX-ACCESS      read-write
    STATUS          current
    DESCRIPTION
        "Set whitelist for the MPLS VPLS. The meanings of the values are:
        enable(1)  -  Enable whitelist mode;
        disable(2) -  Disable whitelist mode;;"  
    DEFVAL { 2 }
    ::= { mplsVplsEntry 5 }
        
mplsVplsRowStatus OBJECT-TYPE
    SYNTAX RowStatus
    MAX-ACCESS read-create
    STATUS current
    DESCRIPTION
        "The status of this conceptual row.Now only realize CreateAndGo and Destroy and Active.
        1 means Active
        4 means CreateAndGo
        6 means Destroy"
    ::= { mplsVplsEntry 10 }	

mplsVplsDescription OBJECT-TYPE
    SYNTAX  OCTET STRING (SIZE(0..20))
    MAX-ACCESS read-write
    STATUS current
    DESCRIPTION 
    	"Characters describing this VPLS instance.Only less than 20 octets is accepted."
    ::= { mplsVplsEntry 11 }

mplsVplsMtu OBJECT-TYPE
    SYNTAX  Integer32 (576..65535)
    MAX-ACCESS read-write
    STATUS current
    DESCRIPTION 
    	"Mtu value of a vpls instance ."
    ::= { mplsVplsEntry 12 }

mplsVplsMacLearning     OBJECT-TYPE
    SYNTAX          INTEGER {enable(1),disable(2)}
    MAX-ACCESS      read-write
    STATUS          current
    DESCRIPTION
        "Set mac learning for the MPLS VPLS. The meanings of the values are:
        enable(1)  -  Enable mac learning;
        disable(2) -  Disable mac learning;"  
    DEFVAL { 1 }
    ::= { mplsVplsEntry 13 }
    
mplsVplsMacLimitNum OBJECT-TYPE
    SYNTAX  Unsigned32 (0..4294967295)
    MAX-ACCESS read-write
    STATUS current
    DESCRIPTION 
    	"Maximum fdb number of the MPLS VPLS."
    ::= { mplsVplsEntry 14 }    

mplsVplsMacLimitAction     OBJECT-TYPE
    SYNTAX          INTEGER {default(1),warn(2), discard(3)}
    MAX-ACCESS      read-write
    STATUS          current
    DESCRIPTION
        "Set warning log when learning is disabled. The meanings of the values are:
        default(1)  -  farward packets with mac learning disable;
        warn(2) -   warning log and discard packets;
        discard(3) - discard packets."  
    DEFVAL { 1 }
    ::= { mplsVplsEntry 15 }    
    
mplsVplsAllowFlooding     OBJECT-TYPE
    SYNTAX          INTEGER {enable(1),disable(2)}
    MAX-ACCESS      read-write
    STATUS          current
    DESCRIPTION
        "Set flooding broadcast, multicast and unicast packets. The meanings of the values are:
        enable(1)  -  Enable flooding unknown unicast;
        disable(2) -  Disable flooding unknown unicast;"  
    DEFVAL { 1 }
    ::= { mplsVplsEntry 16 }    

--mplsVplsAllowUnknownUnicast     OBJECT-TYPE
--    SYNTAX          INTEGER {enable(1),disable(2)}
--    MAX-ACCESS      read-write
--    STATUS          current
--    DESCRIPTION
--        "Set flooding unknown unicast packets. The meanings of the values are:
--        enable(1)  -  Enable flooding unknown unicast;
--        disable(2) -  Disable flooding unknown unicast;"  
--    DEFVAL { 1 }
--    ::= { mplsVplsEntry 17 }    
--  
--mplsVplsAllowMulticast     OBJECT-TYPE
--    SYNTAX          INTEGER {enable(1),disable(2)}
--    MAX-ACCESS      read-write
--    STATUS          current
--    DESCRIPTION
--        "Set flooding multicast packets. The meanings of the values are:
--        enable(1)  -  Enable flooding multicast;
--        disable(2) -  Disable flooding multicast;"  
--    DEFVAL { 1 }
--    ::= { mplsVplsEntry 18 }                

mplsVplsState     OBJECT-TYPE
    SYNTAX          INTEGER {active(1),inactive(2)}
    MAX-ACCESS      read-only
    STATUS          current
    DESCRIPTION
        "VPLS instance state. The meanings of the values are:
        active(1)  -  VPLS instance is active;
        inactive(2) -  VPLS instance is inactive;" 
    ::= { mplsVplsEntry 20 }         
  
-- mplsVplsRawMeshPeerNum     OBJECT-TYPE
--     SYNTAX          Integer32
--     MAX-ACCESS      read-only
--     STATUS          current
--     DESCRIPTION
--         "Indicates the number the vpls raw mesh peers."  
--     ::= { mplsVplsEntry 21 }   
--     
-- mplsVplsTaggedMeshPeerNum     OBJECT-TYPE
--     SYNTAX          Integer32
--     MAX-ACCESS      read-only
--     STATUS          current
--     DESCRIPTION
--         "Indicates the number the vpls tagged mesh peer."  
--     ::= { mplsVplsEntry 22 }   
--     
-- mplsVplsSpokePeerNum     OBJECT-TYPE
--     SYNTAX          Integer32
--     MAX-ACCESS      read-only
--     STATUS          current
--     DESCRIPTION
--         "Indicates the number the vpls spoke peers."  
--     ::= { mplsVplsEntry 23 }               
            
mplsVplsPeerTable OBJECT-TYPE
    SYNTAX  SEQUENCE OF MplsVplsPeerEntry
    MAX-ACCESS not-accessible
    STATUS   current
    DESCRIPTION 
    	"Peers to VPLS domains."
    ::= { mpls 9 }

mplsVplsPeerEntry OBJECT-TYPE
    SYNTAX  MplsVplsPeerEntry
    MAX-ACCESS not-accessible
    STATUS current
    DESCRIPTION
     "Entry of mplsVplsPeerTable."
    INDEX   { mplsVplsPeerVplsId, mplsVplsPeerPeerAddr}
    ::= { mplsVplsPeerTable 1 }

MplsVplsPeerEntry   ::=
    SEQUENCE {
        mplsVplsPeerVplsId                  Unsigned32,
        mplsVplsPeerPeerAddr 		    IpAddress,
        mplsVplsPeerType		    Integer32,
        mplsVplsPeerIsManul		    Integer32,     
        mplsVplsPeerControlWord		    INTEGER,               
        mplsVplsPeerStats     		    INTEGER,  
        mplsVplsPeerPEType     		    INTEGER,         
        mplsVplsPeerRowStatus		    RowStatus,
        mplsVplsPeerState		    INTEGER                
        }

mplsVplsPeerVplsId OBJECT-TYPE
    SYNTAX  Unsigned32(1..4294967295)
    MAX-ACCESS not-accessible
    STATUS current
    DESCRIPTION
    	"Identifying value for VPLS."
    ::= { mplsVplsPeerEntry 1 }
        
mplsVplsPeerPeerAddr OBJECT-TYPE
    SYNTAX  IpAddress
    MAX-ACCESS not-accessible
    STATUS current
    DESCRIPTION 
    	"IP address of the peer node to be added."
    ::= { mplsVplsPeerEntry 2 }
    
mplsVplsPeerType OBJECT-TYPE
    SYNTAX Integer32
    MAX-ACCESS read-create
    STATUS current
    DESCRIPTION
        "Set 1, if Peer Virtual Circuits type is Raw mode;
        Set 2, if Peer Virtual Circuits type is Tagged mode."
    ::= { mplsVplsPeerEntry 3 }	

mplsVplsPeerIsManul OBJECT-TYPE
    SYNTAX  Integer32
    MAX-ACCESS read-write
    STATUS current
    DESCRIPTION 
    	"No signaling is used to set-up the Virtual Circuit.
    	1 means manual is set, 2 means not."
    ::= { mplsVplsPeerEntry 4 }
    
mplsVplsPeerControlWord OBJECT-TYPE
    SYNTAX  INTEGER {enable(1),disable(2)}
    MAX-ACCESS read-write
    STATUS current
    DESCRIPTION 
       "Set control word for mpls vpls peer. The meanings of the values are:
        enable(1)  -  enable control word;
        disable(2) -  disable control word;"  
    DEFVAL { 2 }
    ::= { mplsVplsPeerEntry 5 }

mplsVplsPeerStats OBJECT-TYPE
    SYNTAX  INTEGER {enable(1),disable(2)}
    MAX-ACCESS read-create
    STATUS current
    DESCRIPTION 
       "Set statistics for mpls vpls peer. The meanings of the values are:
        enable(1)  -  enable statistics;
        disable(2) -  disable statistics;"  
    DEFVAL { 2 }
    ::= { mplsVplsPeerEntry 6 }

mplsVplsPeerPEType OBJECT-TYPE
    SYNTAX  INTEGER {spe(1),upe(2)}
    MAX-ACCESS read-create
    STATUS current
    DESCRIPTION 
       "Set PW type for mpls vpls peer. The meanings of the values are:
        spe(1)  -  Superstarum PE;
        upe(2)  -  Underlayer PE;"  
    DEFVAL { 1 }
    ::= { mplsVplsPeerEntry 7 }
            
mplsVplsPeerRowStatus OBJECT-TYPE
    SYNTAX  RowStatus
    MAX-ACCESS read-create
    STATUS current
    DESCRIPTION 
        "The status of this conceptual row.Now only realize CreateAndGo and Destroy and Active.
        1 means Active
        4 means CreateAndGo
        6 means Destroy"
    ::= { mplsVplsPeerEntry 15 }

mplsVplsPeerState OBJECT-TYPE
    SYNTAX  INTEGER {up(1),down(2)}
    MAX-ACCESS read-only
    STATUS current
    DESCRIPTION
       "The state of mpls vpls peer. The meanings of the values are:
        up(1)   -  the vpls peer is up;
        down(2) -  the vpls peer is down;"
    DEFVAL { 2 }
    ::= { mplsVplsPeerEntry 16 }

-- mplsVplsPeerIngressPkts         OBJECT-TYPE
--     SYNTAX          Counter64
--     MAX-ACCESS      read-only
--     STATUS          current
--     DESCRIPTION
--         "Ingress packets number of mpls vpls peer."
--     ::= { mplsVplsPeerEntry 17 }
-- 
-- mplsVplsPeerIngressbytes         OBJECT-TYPE
--     SYNTAX          Counter64
--     MAX-ACCESS      read-only
--     STATUS          current
--     DESCRIPTION
--         "Ingress bytes number of mpls vpls peer."
--     ::= { mplsVplsPeerEntry 18 }
-- 
-- mplsVplsPeerEgressPkts         OBJECT-TYPE
--     SYNTAX          Counter64
--     MAX-ACCESS      read-only
--     STATUS          current
--     DESCRIPTION
--         "Egress packets number of mpls vpls peer."
--     ::= { mplsVplsPeerEntry 19 }
--     
-- mplsVplsPeerEgressBytes         OBJECT-TYPE
--     SYNTAX          Counter64
--     MAX-ACCESS      read-only
--     STATUS          current
--     DESCRIPTION
--         "Egress bytes number of mpls vpls peer."
--     ::= { mplsVplsPeerEntry 20 }     
        	        
mplsVplsFibAddTable OBJECT-TYPE
    SYNTAX  SEQUENCE OF MplsVplsFibAddEntry
    MAX-ACCESS not-accessible
    STATUS   current
    DESCRIPTION
     "Vpls fib table."
    ::= { mpls 10 }

mplsVplsFibAddEntry OBJECT-TYPE
    SYNTAX  MplsVplsFibAddEntry
    MAX-ACCESS not-accessible
    STATUS current
    DESCRIPTION
     "VPLS Fib entrys."
    INDEX   { mplsVplsFibAddVplsId, mplsVplsFibAddPeerAddr}
    ::= { mplsVplsFibAddTable 1 }

MplsVplsFibAddEntry   ::=
    SEQUENCE {
        mplsVplsFibAddVplsId          Integer32,
        mplsVplsFibAddPeerAddr   IpAddress,
        mplsVplsFibAddInLabel  Integer32,
        mplsVplsFibAddOutLabel  Integer32,
        mplsVplsFibAddRowStatus  RowStatus
        }

mplsVplsFibAddVplsId OBJECT-TYPE
    SYNTAX  Integer32 (1..2147483647)
    MAX-ACCESS not-accessible
    STATUS current
    DESCRIPTION
     "Identifying value for VPLS."
    ::= { mplsVplsFibAddEntry 1 }

mplsVplsFibAddPeerAddr OBJECT-TYPE
    SYNTAX  IpAddress
    MAX-ACCESS not-accessible
    STATUS current
    DESCRIPTION
     "Mesh Peer IPv4 Address."
    ::= { mplsVplsFibAddEntry 2 }

mplsVplsFibAddInLabel OBJECT-TYPE
    SYNTAX Integer32(16..2063)
    MAX-ACCESS read-create
    STATUS current
    DESCRIPTION
 "In-coming Label <16-2063>."
    ::= { mplsVplsFibAddEntry 3 }

mplsVplsFibAddOutLabel OBJECT-TYPE
    SYNTAX  Integer32(16..1048575)
    MAX-ACCESS read-write
    STATUS current
    DESCRIPTION
     "Out-going Label <16-1048575>."
    ::= { mplsVplsFibAddEntry 4 }

mplsVplsFibAddRowStatus OBJECT-TYPE
    SYNTAX  RowStatus
    MAX-ACCESS read-create
    STATUS current
    DESCRIPTION 
        "The status of this conceptual row.Now only realize CreateAndGo and Destroy and Active.
        1 means Active
        4 means CreateAndGo
        6 means Destroy"
    ::= { mplsVplsFibAddEntry 5 }
    
 mplsInterfaceMplsVpwsTable OBJECT-TYPE
    SYNTAX  SEQUENCE OF MplsInterfaceMplsVpwsEntry
    MAX-ACCESS not-accessible
    STATUS   current
    DESCRIPTION 
    	"One MPLS layer-2 virtual circuit can only band to one interface,
    	but one interface may be banded to many VCs."
    ::= { mpls 11 }

 mplsInterfaceMplsVpwsEntry OBJECT-TYPE
    SYNTAX  MplsInterfaceMplsVpwsEntry
    MAX-ACCESS not-accessible
    STATUS current
    DESCRIPTION 
    	"Entry of mplsInterfaceMplsVpwsTable."
    INDEX   { mplsInterfaceMplsVpwsIfIndex, mplsInterfaceMplsVpwsVcName, mplsInterfaceMplsVpwsVlanId}
    ::= { mplsInterfaceMplsVpwsTable 1 }

MplsInterfaceMplsVpwsEntry   ::=
    SEQUENCE {
        mplsInterfaceMplsVpwsIfIndex   Integer32,
        mplsInterfaceMplsVpwsVcName 	OCTET STRING,
        mplsInterfaceMplsVpwsVlanId	Integer32,
        mplsInterfaceMplsVpwsBundling		INTEGER,
        mplsInterfaceMplsVpwsStatisticEn		INTEGER,  
        mplsInterfaceMplsVpwsReplaceDscp		INTEGER,
        mplsInterfaceMplsVpwsReplaceCos		INTEGER,
	mplsInterfaceMplsVpwsVlanOperation 	OCTET STRING,
        mplsInterfaceMplsVpwsRowStatus	RowStatus
        }

mplsInterfaceMplsVpwsIfIndex OBJECT-TYPE
    SYNTAX  Integer32 (1..48)
    MAX-ACCESS not-accessible
    STATUS current
    DESCRIPTION 
    	"Interface index."
    ::= { mplsInterfaceMplsVpwsEntry 1 }

mplsInterfaceMplsVpwsVcName OBJECT-TYPE
    SYNTAX  OCTET STRING (SIZE(1..20))
    MAX-ACCESS not-accessible
    STATUS current
    DESCRIPTION 
    	"Identifying string for MPLS layer-2 virtual circuit."
    ::= { mplsInterfaceMplsVpwsEntry 2 }	

mplsInterfaceMplsVpwsVlanId OBJECT-TYPE
    SYNTAX  Integer32(0..4094)
    MAX-ACCESS not-accessible
    STATUS current
    DESCRIPTION 
    	"Vlan identifier."
    ::= { mplsInterfaceMplsVpwsEntry 3 }

mplsInterfaceMplsVpwsBundling OBJECT-TYPE
    SYNTAX  INTEGER {enable(1), disable(2)}
    MAX-ACCESS read-create
    STATUS current
    DESCRIPTION 
    	"State of bundling."
    DEFVAL { disable }
    ::= { mplsInterfaceMplsVpwsEntry 4 }

mplsInterfaceMplsVpwsStatisticEn OBJECT-TYPE
    SYNTAX  INTEGER {enable(1), disable(2)}
    MAX-ACCESS read-create
    STATUS current
    DESCRIPTION 
    	"State of statistic enable."
    DEFVAL { disable }
    ::= { mplsInterfaceMplsVpwsEntry 5 }    

mplsInterfaceMplsVpwsReplaceDscp OBJECT-TYPE
    SYNTAX  INTEGER {enable(1), disable(2)}
    MAX-ACCESS read-create
    STATUS current
    DESCRIPTION 
    	"State of replace dscp enable."
    DEFVAL { disable }
    ::= { mplsInterfaceMplsVpwsEntry 6 } 

mplsInterfaceMplsVpwsReplaceCos OBJECT-TYPE
    SYNTAX  INTEGER {enable(1), disable(2)}
    MAX-ACCESS read-create
    STATUS current
    DESCRIPTION 
    	"State of replace cos enable."
    DEFVAL { disable }
    ::= { mplsInterfaceMplsVpwsEntry 7 }     
	
mplsInterfaceMplsVpwsVlanOperation OBJECT-TYPE
    SYNTAX  OCTET STRING (SIZE(1..16))
    MAX-ACCESS read-create
    STATUS current
    DESCRIPTION 
    	"Identifying vlan operation table name for MPLS layer-2 virtual circuit."
    ::= { mplsInterfaceMplsVpwsEntry 8 }
	
mplsInterfaceMplsVpwsRowStatus OBJECT-TYPE
    SYNTAX  RowStatus
    MAX-ACCESS read-create
    STATUS current
    DESCRIPTION 
        "The status of this conceptual row.Now only realize CreateAndGo and Destroy and Active.
        1 means Active
        4 means CreateAndGo
        6 means Destroy"
    ::= { mplsInterfaceMplsVpwsEntry 10 }

mplsInterfacePropertyTable OBJECT-TYPE
    SYNTAX  SEQUENCE OF   MplsInterfacePropertyEntry
    MAX-ACCESS not-accessible
    STATUS   current
    DESCRIPTION 
    	"Interface property table.Including label-switching and configuration of MPLS-TP P2P MAC."
    ::= { mpls 12 }

mplsInterfacePropertyEntry OBJECT-TYPE
    SYNTAX  MplsInterfacePropertyEntry
    MAX-ACCESS not-accessible
    STATUS current
    DESCRIPTION 
    	"Configuration of interface label-switching and MPLS-TP P2P MAC."
    INDEX   { mplsInterfacePropertyIfIndex}
    ::= { mplsInterfacePropertyTable 1 }

MplsInterfacePropertyEntry   ::=
    SEQUENCE {
        mplsInterfacePropertyIfIndex    Integer32,
        mplsInterfaceLabelSwitching     INTEGER,
        mplsInterfaceTPP2PTxMac					MacAddress,
        mplsInterfaceCRCNumberThresholdRising 	OCTET STRING,
        mplsInterfaceCRCNumberThresholdFalling 	OCTET STRING,
        mplsInterfaceCRCRateThresholdRising 	Integer32,
        mplsInterfaceCRCRateThresholdFalling 	Integer32,
        mplsInterfaceCRCAlarmStatus     INTEGER                       
        }

mplsInterfacePropertyIfIndex OBJECT-TYPE
    SYNTAX  Integer32(2..48)
    MAX-ACCESS not-accessible
    STATUS current
    DESCRIPTION 
    	"Interface index."
    ::= { mplsInterfacePropertyEntry 1 }

mplsInterfaceLabelSwitching     OBJECT-TYPE
    SYNTAX          INTEGER {enable(1),disable(2)}
    MAX-ACCESS      read-write
    STATUS          current
    DESCRIPTION
        "Set label-switching of the interface. This node is 
        valid when the interface is a routed interface. 
        The meanings of the values are:
        enable(1)  -  Enable label-switching;
        disable(2) -  Disable label-switching;"  
    DEFVAL { 2 }
    ::= { mplsInterfacePropertyEntry 4 }        

mplsInterfaceTPP2PTxMac     OBJECT-TYPE
    SYNTAX          MacAddress
    MAX-ACCESS      read-write
    STATUS          current
    DESCRIPTION
        "Transmit mac address for mpls-tp non-ip system."  
    ::= { mplsInterfacePropertyEntry 5 }    

mplsInterfaceCRCNumberThresholdRising  OBJECT-TYPE
    SYNTAX          OCTET STRING
    MAX-ACCESS      read-write
    STATUS          current
    DESCRIPTION
        "Rising threshold for CRC error number."
    ::= { mplsInterfacePropertyEntry 6 }       

mplsInterfaceCRCNumberThresholdFalling  OBJECT-TYPE
    SYNTAX          OCTET STRING
    MAX-ACCESS      read-write
    STATUS          current
    DESCRIPTION
        "Falling threshold for CRC error number."
    ::= { mplsInterfacePropertyEntry 7 } 
    
mplsInterfaceCRCRateThresholdRising  OBJECT-TYPE
    SYNTAX          Integer32(1..100)
    MAX-ACCESS      read-write
    STATUS          current
    DESCRIPTION
        "Rising threshold for CRC error rate."
    ::= { mplsInterfacePropertyEntry 8 } 
    
mplsInterfaceCRCRateThresholdFalling  OBJECT-TYPE
    SYNTAX          Integer32(0..99)
    MAX-ACCESS      read-write
    STATUS          current
    DESCRIPTION
        "Falling threshold for CRC error rate."
    ::= { mplsInterfacePropertyEntry 9 } 

mplsInterfaceCRCAlarmStatus  OBJECT-TYPE
    SYNTAX          INTEGER {active(1),inactive(2)}
    MAX-ACCESS      read-only
    STATUS          current
    DESCRIPTION
        "Interface CRC alarm status."
    ::= { mplsInterfacePropertyEntry 10 } 
                    
mplsInterfaceMplsVplsTable OBJECT-TYPE
    SYNTAX  SEQUENCE OF   MplsInterfaceMplsVplsEntry
    MAX-ACCESS not-accessible
    STATUS   current
    DESCRIPTION 
    	"Table of relationship of Vpls instance and interface."
    ::= { mpls 13 }

mplsInterfaceMplsVplsEntry OBJECT-TYPE
    SYNTAX  MplsInterfaceMplsVplsEntry
    MAX-ACCESS not-accessible
    STATUS current
    DESCRIPTION 
    	"Entry of mplsInterfaceMplsVplsTable."
    INDEX   { mplsInterfaceMplsVplsIfIndex, mplsInterfaceMplsVplsVplsName, mplsInterfaceMplsVplsVlanId}
    ::= { mplsInterfaceMplsVplsTable 1 }

MplsInterfaceMplsVplsEntry   ::=
    SEQUENCE {
        mplsInterfaceMplsVplsIfIndex         	Integer32,
        mplsInterfaceMplsVplsVplsName 		OCTET STRING,    
        mplsInterfaceMplsVplsVlanId 		Integer32,
        mplsInterfaceMplsVplsBundling		INTEGER,
        mplsInterfaceMplsVplsStatisticEn		INTEGER,        
        mplsInterfaceMplsVplsETreeACType		INTEGER,
        mplsInterfaceMplsVplsReplaceDscp		INTEGER,     
        mplsInterfaceMplsVplsReplaceCos		INTEGER,    
        mplsInterfaceMplsVplsVlanOperation 		OCTET STRING, 		
        mplsInterfaceMplsVplsRowStatus 		RowStatus
        }

mplsInterfaceMplsVplsIfIndex OBJECT-TYPE
    SYNTAX  Integer32 (1..48)
    MAX-ACCESS not-accessible
    STATUS current
    DESCRIPTION 
    	"Interface index."
    ::= { mplsInterfaceMplsVplsEntry 1 }
       
mplsInterfaceMplsVplsVplsName OBJECT-TYPE
    SYNTAX  OCTET STRING (SIZE(1..20))
    MAX-ACCESS not-accessible
    STATUS current
    DESCRIPTION 
    	"Identifying value for vlan."
    ::= { mplsInterfaceMplsVplsEntry 2 }
     
mplsInterfaceMplsVplsVlanId OBJECT-TYPE
    SYNTAX  Integer32(0..4094)
    MAX-ACCESS not-accessible
    STATUS current
    DESCRIPTION 
    	"Identifying value for vlan.."
    ::= { mplsInterfaceMplsVplsEntry 3 }	

mplsInterfaceMplsVplsBundling OBJECT-TYPE
    SYNTAX  INTEGER {enable(1), disable(2)}
    MAX-ACCESS read-create
    STATUS current
    DESCRIPTION 
    	"State of bundling."
    DEFVAL { disable }
    ::= { mplsInterfaceMplsVplsEntry 4 }

mplsInterfaceMplsVplsStatisticEn OBJECT-TYPE
    SYNTAX  INTEGER {enable(1), disable(2)}
    MAX-ACCESS read-create
    STATUS current
    DESCRIPTION 
    	"State of statistics enable."
    DEFVAL { disable }    	
    ::= { mplsInterfaceMplsVplsEntry 5 }    

mplsInterfaceMplsVplsETreeACType OBJECT-TYPE
    SYNTAX  INTEGER {leaf(1), root(2)}
    MAX-ACCESS read-create
    STATUS current
    DESCRIPTION 
    	"Etree AC type."
    DEFVAL { root }    	
    ::= { mplsInterfaceMplsVplsEntry 6 }    
    
mplsInterfaceMplsVplsReplaceDscp   OBJECT-TYPE
    SYNTAX  INTEGER {enable(1), disable(2)}
    MAX-ACCESS read-create
    STATUS current
    DESCRIPTION 
    	"State of replace dscp."
    DEFVAL { disable }    	
    ::= { mplsInterfaceMplsVplsEntry 7 } 

mplsInterfaceMplsVplsReplaceCos OBJECT-TYPE
    SYNTAX  INTEGER {enable(1), disable(2)}
    MAX-ACCESS read-create
    STATUS current
    DESCRIPTION 
    	"State of replace cos enable."
    DEFVAL { disable }    	
    ::= { mplsInterfaceMplsVplsEntry 8 }    
	
mplsInterfaceMplsVplsVlanOperation OBJECT-TYPE
    SYNTAX  OCTET STRING (SIZE(1..16))
    MAX-ACCESS read-create
    STATUS current
    DESCRIPTION 
    	"Identifying vlan operation table name."
    ::= { mplsInterfaceMplsVplsEntry 9 }
    
mplsInterfaceMplsVplsRowStatus OBJECT-TYPE
    SYNTAX  RowStatus
    MAX-ACCESS read-create
    STATUS current
    DESCRIPTION 
        "The status of this conceptual row.Now only realize CreateAndGo and Destroy and Active.
        1 means Active
        4 means CreateAndGo
        6 means Destroy"
    ::= { mplsInterfaceMplsVplsEntry 10 }

mplsLspPeTable OBJECT-TYPE
    SYNTAX  SEQUENCE OF   MplsLspPeEntry
    MAX-ACCESS not-accessible
    STATUS   current
    DESCRIPTION 
    	"Table of all mpls lsp-pe instances."
    ::= { mpls 14 }
    
mplsLspPeEntry OBJECT-TYPE
    SYNTAX  MplsLspPeEntry
    MAX-ACCESS not-accessible
    STATUS current
    DESCRIPTION 
     "Entry of mplsLspPeTable."
    INDEX   { mplsLspPeName}
    ::= { mplsLspPeTable 1 }

MplsLspPeEntry   ::=
    SEQUENCE {
        mplsLspPeName 		  					OCTET STRING,
        mplsLspPeRowStatus  					RowStatus,
        mplsLspPeState  							INTEGER,
        mplsLspPeDescription	        OCTET STRING,
        mplsLspPeOAMMegLevel          Integer32,        
        mplsLspPeOAMMegId							OCTET STRING,
        mplsLspPeOAMMegIdIcc          Integer32,
        mplsLspPeOAMMepId							Integer32,
        mplsLspPeOAMMepInterval				INTEGER,
        mplsLspPeOAMMepExp						Integer32,
        mplsLspPeOAMRMepId						Integer32,        
        mplsLspPeOAMCCState						INTEGER,                
        mplsLspPeOAMEventCacheSize		Integer32,
        mplsLspPeOAM1dmCacheSize			Integer32,
        mplsLspPeOAMAisInterval			  Integer32,              
        mplsLspPeOAMAisClientSupress	INTEGER,
        mplsLspPeOAMLckInterval 			Integer32,
        mplsLspPeOAMLck         			INTEGER,
        mplsLspPeOAMEvtLOC            INTEGER,
        mplsLspPeOAMEvtUMP            INTEGER,
        mplsLspPeOAMEvtUIN            INTEGER,
        mplsLspPeOAMEvtUMG            INTEGER,
        mplsLspPeOAMEvtULV            INTEGER,
        mplsLspPeOAMEvtW1ST           INTEGER,
        mplsLspPeOAMEvtRDIR           INTEGER,
        mplsLspPeOAMEvtRDIT           INTEGER,
        mplsLspPeOAMEvtAISR           INTEGER,
        mplsLspPeOAMEvtAIST           INTEGER,
        mplsLspPeOAMEvtAISD           INTEGER,
        mplsLspPeOAMEvtLCKR           INTEGER,
        mplsLspPeOAMEvtLCKT           INTEGER,
        mplsLspPeOAMEvtLCKD           INTEGER,
        mplsLspPeOAMLckTxEnable       INTEGER,
        mplsLspPeOAMEvtCRC            INTEGER,        
        mplsLspPeOAMState             INTEGER,
        mplsLspPeIngressPkts          Counter64,
        mplsLspPeIngressBytes         Counter64,
        mplsLspPeEgressPkts           Counter64,
        mplsLspPeEgressBytes          Counter64,
        mplsLspPeStats                INTEGER,
        mplsLspPeBandwidth            Integer32,                
        mplsLspPeOAMLmDualExp          Integer32,
        mplsLspPeOAMLmDualStatInterval Integer32,
        mplsLspPeOAMLmDualCacheSize    Integer32,
        mplsLspPeOAMLmSingleExp        Integer32,
        mplsLspPeOAMLmSingleInterval   INTEGER,
        mplsLspPeOAMLmSingleCacheSize  Integer32,            
        mplsLspPeOAMLmEnableState      INTEGER,
        mplsLspPeOAMLmLocalLossThreshold   Integer32,
        mplsLspPeOAMLmRemoteLossThreshold  Integer32,
        mplsLspPeOAMLmSingleRxCount        Integer32,
        mplsLspPeOAMLmSingleTxCount        Integer32,
        mplsLspPeOAMLmSingleSuccessRate    Integer32,
        mplsLspPeOAMLmSingleStartTime      OCTET STRING,	
        mplsLspPeOAMLmSingleEndTime        OCTET STRING		
        }

mplsLspPeName OBJECT-TYPE
    SYNTAX  OCTET STRING(SIZE(1..20))
    MAX-ACCESS not-accessible
    STATUS current
    DESCRIPTION
    	"Identifying value for MPLS Lsp-pe."
    ::= { mplsLspPeEntry 1 }

mplsLspPeRowStatus OBJECT-TYPE
    SYNTAX RowStatus
    MAX-ACCESS read-create
    STATUS current
    DESCRIPTION
        "The status of this conceptual row.Now only realize CreateAndGo and Destroy and Active.
        1 means Active
        4 means CreateAndGo
        6 means Destroy"
    ::= { mplsLspPeEntry 10 }     
    
mplsLspPeState     OBJECT-TYPE
    SYNTAX          INTEGER {active(1),inactive(2)}
    MAX-ACCESS      read-only
    STATUS          current
    DESCRIPTION
        "The state of the lsp-pe. The meanings of the values are:
        active(1)   -  the lsp-pe is active;
        inactive(2) -  the lsp-pe is inactive;"  
    ::= { mplsLspPeEntry 11 }   

mplsLspPeDescription OBJECT-TYPE
    SYNTAX  OCTET STRING (SIZE(1..20))
    MAX-ACCESS read-write
    STATUS current
    DESCRIPTION 
    	"Characters describing of this pe type LSP.
    	 Only less than 20 octets is accepted."
    ::= { mplsLspPeEntry 12 }
    
mplsLspPeOAMMegLevel OBJECT-TYPE
    SYNTAX Integer32 (0..7)
    MAX-ACCESS read-write
    STATUS current
    DESCRIPTION
      "OAM level."
    DEFVAL { 7 }
    ::= { mplsLspPeEntry 20 }	
        
mplsLspPeOAMMegId OBJECT-TYPE
    SYNTAX OCTET STRING (SIZE (1..12))
    MAX-ACCESS read-write
    STATUS current
    DESCRIPTION
      "MEG ID of the lsp-pe."  
    ::= { mplsLspPeEntry 21 }	   

mplsLspPeOAMMegIdIcc OBJECT-TYPE
    SYNTAX Integer32 (1..6)
    MAX-ACCESS read-write
    STATUS current
    DESCRIPTION
      "ICC length of MEG ID."
    DEFVAL { 6 }
    ::= { mplsLspPeEntry 22 }	

mplsLspPeOAMMepId OBJECT-TYPE
    SYNTAX Integer32 (1..8191)
    MAX-ACCESS read-write
    STATUS current
    DESCRIPTION
      "MEP ID."  
    ::= { mplsLspPeEntry 23 }	    
    
mplsLspPeOAMMepInterval OBJECT-TYPE
    SYNTAX INTEGER 
    {
        three-point-three-ms(1), 
        ten-ms(2),
        one-hundred-ms(3),
        one-sec(4),
        ten-sec(5),
        one-min(6),
        ten-min(7)
    }
    MAX-ACCESS read-write
    STATUS current
    DESCRIPTION
      "MEP Interval."  
    ::= { mplsLspPeEntry 24 }

mplsLspPeOAMMepExp OBJECT-TYPE
    SYNTAX Integer32 (0..7)
    MAX-ACCESS read-write
    STATUS current
    DESCRIPTION
      "EXP value, default is 7."
    DEFVAL { 7 }  
    ::= { mplsLspPeEntry 25 }	 

mplsLspPeOAMRMepId OBJECT-TYPE
    SYNTAX Integer32 (1..8191)
    MAX-ACCESS read-write
    STATUS current
    DESCRIPTION
      "Remote MEP ID."  
    ::= { mplsLspPeEntry 26 }	      

mplsLspPeOAMCCState OBJECT-TYPE
    SYNTAX INTEGER {enable(1), disable(2)}
    MAX-ACCESS read-write
    STATUS current
    DESCRIPTION
      "CC state."
    DEFVAL { disable }  
    ::= { mplsLspPeEntry 27 }	      
    
mplsLspPeOAMEventCacheSize OBJECT-TYPE
    SYNTAX Integer32 (8..256)
    MAX-ACCESS read-write
    STATUS current
    DESCRIPTION
      "Event entry cache size."  
    DEFVAL { 8 }        
    ::= { mplsLspPeEntry 28 }	          
         
mplsLspPeOAM1dmCacheSize OBJECT-TYPE
    SYNTAX Integer32 (8..256)
    MAX-ACCESS read-write
    STATUS current
    DESCRIPTION
      "1dm entry cache size."  
    DEFVAL { 8 }        
    ::= { mplsLspPeEntry 29 }	      

mplsLspPeOAMAisInterval OBJECT-TYPE
    SYNTAX Integer32 (0|1|60)
    MAX-ACCESS read-write
    STATUS current
    DESCRIPTION
      "Interval of AIS PDU.
      0:no oam-y1731 ais server enable."  
    ::= { mplsLspPeEntry 30 }   
    
mplsLspPeOAMAisClientSupress OBJECT-TYPE
    SYNTAX INTEGER {enable(1), disable(2)}
    MAX-ACCESS read-write
    STATUS current
    DESCRIPTION
      "AIS client supress state."    
    DEFVAL { disable }  
    ::= { mplsLspPeEntry 31 }	    

mplsLspPeOAMLckInterval OBJECT-TYPE
    SYNTAX Integer32 (0|1|60)
    MAX-ACCESS read-write
    STATUS current
    DESCRIPTION
      "Lsp-pe lock interval.
      0:no oam-y1731 lck server enable."    
    DEFVAL { 0 }  
    ::= { mplsLspPeEntry 32 }	    

mplsLspPeOAMLck OBJECT-TYPE
    SYNTAX INTEGER {enable(1), disable(2)}
    MAX-ACCESS read-write
    STATUS current
    DESCRIPTION
      "Lck state."    
    DEFVAL { disable }  
    ::= { mplsLspPeEntry 33 }	     

mplsLspPeOAMEvtLOC OBJECT-TYPE
    SYNTAX INTEGER {enable(1), disable(2)}
    MAX-ACCESS read-only
    STATUS current
    DESCRIPTION
      "Loc state."    
    DEFVAL { disable }  
    ::= { mplsLspPeEntry 34 }

mplsLspPeOAMEvtUMP OBJECT-TYPE
    SYNTAX INTEGER {enable(1), disable(2)}
    MAX-ACCESS read-only
    STATUS current
    DESCRIPTION
      "Unexp RMEPID state."    
    DEFVAL { disable }  
    ::= { mplsLspPeEntry 35 }

mplsLspPeOAMEvtUIN OBJECT-TYPE
    SYNTAX INTEGER {enable(1), disable(2)}
    MAX-ACCESS read-only
    STATUS current
    DESCRIPTION
      "Unexp interval state."    
    DEFVAL { disable }  
    ::= { mplsLspPeEntry 36 }

mplsLspPeOAMEvtUMG OBJECT-TYPE
    SYNTAX INTEGER {enable(1), disable(2)}
    MAX-ACCESS read-only
    STATUS current
    DESCRIPTION
      "Unexp MEGID state."    
    DEFVAL { disable }  
    ::= { mplsLspPeEntry 37 }

mplsLspPeOAMEvtULV OBJECT-TYPE
    SYNTAX INTEGER {enable(1), disable(2)}
    MAX-ACCESS read-only
    STATUS current
    DESCRIPTION
      "Unexp Level state."    
    DEFVAL { disable } 
    ::= { mplsLspPeEntry 38 }

mplsLspPeOAMEvtW1ST OBJECT-TYPE
    SYNTAX INTEGER {enable(1), disable(2)}
    MAX-ACCESS read-only
    STATUS current
    DESCRIPTION
      "Wait 1st CCM state."    
    DEFVAL { disable } 
    ::= { mplsLspPeEntry 39 }

mplsLspPeOAMEvtRDIR OBJECT-TYPE
    SYNTAX INTEGER {enable(1), disable(2)}
    MAX-ACCESS read-only
    STATUS current
    DESCRIPTION
      "RDI RX state."    
    DEFVAL { disable } 
    ::= { mplsLspPeEntry 40 }

mplsLspPeOAMEvtRDIT OBJECT-TYPE
    SYNTAX INTEGER {enable(1), disable(2)}
    MAX-ACCESS read-only
    STATUS current
    DESCRIPTION
      "RDI TX state."    
    DEFVAL { disable } 
    ::= { mplsLspPeEntry 41 }

mplsLspPeOAMEvtAISR OBJECT-TYPE
    SYNTAX INTEGER {enable(1), disable(2)}
    MAX-ACCESS read-only
    STATUS current
    DESCRIPTION
      "AIS RX state."    
    DEFVAL { disable } 
    ::= { mplsLspPeEntry 42 }

mplsLspPeOAMEvtAIST OBJECT-TYPE
    SYNTAX INTEGER {enable(1), disable(2)}
    MAX-ACCESS read-only
    STATUS current
    DESCRIPTION
      "AIS RX state."    
    DEFVAL { disable } 
    ::= { mplsLspPeEntry 43 }

mplsLspPeOAMEvtAISD OBJECT-TYPE
    SYNTAX INTEGER {enable(1), disable(2)}
    MAX-ACCESS read-only
    STATUS current
    DESCRIPTION
      "AIS RX state."    
    DEFVAL { disable } 
    ::= { mplsLspPeEntry 44 }

mplsLspPeOAMEvtLCKR OBJECT-TYPE
    SYNTAX INTEGER {enable(1), disable(2)}
    MAX-ACCESS read-only
    STATUS current
    DESCRIPTION
      "LCK RX state."    
    DEFVAL { disable } 
    ::= { mplsLspPeEntry 45 }

mplsLspPeOAMEvtLCKT OBJECT-TYPE
    SYNTAX INTEGER {enable(1), disable(2)}
    MAX-ACCESS read-only
    STATUS current
    DESCRIPTION
      "LCK RX state."    
    DEFVAL { disable } 
    ::= { mplsLspPeEntry 46 }

mplsLspPeOAMEvtLCKD OBJECT-TYPE
    SYNTAX INTEGER {enable(1), disable(2)}
    MAX-ACCESS read-only
    STATUS current
    DESCRIPTION
      "LCK RX state."    
    DEFVAL { disable } 
    ::= { mplsLspPeEntry 47 }   

mplsLspPeOAMLckTxEnable OBJECT-TYPE
    SYNTAX INTEGER {enable(1), disable(2)}
    MAX-ACCESS read-only
    STATUS current
    DESCRIPTION
      "oam-y1731 lck server enable."    
    DEFVAL { 2 }  
    ::= { mplsLspPeEntry 48 }		

mplsLspPeOAMEvtCRC OBJECT-TYPE
    SYNTAX INTEGER {enable(1), disable(2)}
    MAX-ACCESS read-only
    STATUS current
    DESCRIPTION
      "CRC RX state."    
    DEFVAL { disable } 
    ::= { mplsLspPeEntry 49 }   
    
mplsLspPeOAMState OBJECT-TYPE
    SYNTAX INTEGER {init(0), fail(1), ok(2)}
    MAX-ACCESS read-only
    STATUS current
    DESCRIPTION
      "oam-y1731 Rmep state."    
    ::= { mplsLspPeEntry 50 }	
    
mplsLspPeIngressPkts             OBJECT-TYPE
    SYNTAX          Counter64
    MAX-ACCESS      read-only
    STATUS          current
    DESCRIPTION
        "Ingress packtes number of lsp-pe."
    ::= { mplsLspPeEntry 51 }
    
mplsLspPeIngressBytes             OBJECT-TYPE
    SYNTAX          Counter64
    MAX-ACCESS      read-only
    STATUS          current
    DESCRIPTION
        "Ingress bytes number of lsp-pe."
    ::= { mplsLspPeEntry 52 }

mplsLspPeEgressPkts               OBJECT-TYPE
    SYNTAX          Counter64
    MAX-ACCESS      read-only
    STATUS          current
    DESCRIPTION
        "Egress packtes number of lsp-pe."
    ::= { mplsLspPeEntry 53 }
    
mplsLspPeEgressBytes             OBJECT-TYPE
    SYNTAX          Counter64
    MAX-ACCESS      read-only
    STATUS          current
    DESCRIPTION
        "Egress bytes number of lsp-pe."
    ::= { mplsLspPeEntry 54 }

mplsLspPeStats OBJECT-TYPE
    SYNTAX INTEGER {enable(1), disable(2)}
    MAX-ACCESS read-write
    STATUS current
    DESCRIPTION
      "statistics enable."    
    DEFVAL { disable }  
    ::= { mplsLspPeEntry 55 }		

mplsLspPeBandwidth OBJECT-TYPE
    SYNTAX Integer32 (-1..1000000)
    MAX-ACCESS read-write
    STATUS current
    DESCRIPTION
      "lsp-pe bandwidth in kbps. -1 means no limitation"
    ::= { mplsLspPeEntry 56 }
        
mplsLspPeOAMLmDualExp OBJECT-TYPE
    SYNTAX Integer32 (0..9)
    MAX-ACCESS read-write
    STATUS current
    DESCRIPTION
      "Configure dual-ended loss measurment packets with specified exp will be counted.
      <0-7> specified exp; 8 means Packets with different exp will be counted separately;
      9 means All packets with different exp will be counted together."
    ::= { mplsLspPeEntry 61 }
    
mplsLspPeOAMLmDualStatInterval OBJECT-TYPE
    SYNTAX Integer32 (1..10)
    MAX-ACCESS read-write
    STATUS current
    DESCRIPTION
      "Configure dual-ended loss measurment interval value."
    DEFVAL { 1 } 
    ::= { mplsLspPeEntry 62 }

mplsLspPeOAMLmDualCacheSize    OBJECT-TYPE
    SYNTAX Integer32 (1..512)
    MAX-ACCESS read-write
    STATUS current
    DESCRIPTION
      "Configure dual-ended loss measurment cache size."
    DEFVAL { 128 } 
    ::= { mplsLspPeEntry 63 }

mplsLspPeOAMLmSingleExp OBJECT-TYPE
    SYNTAX Integer32 (0..9)
    MAX-ACCESS read-write
    STATUS current
    DESCRIPTION
      "Configure single-ended loss measurment packets with specified exp will be counted.
      <0-7> specified exp; 8 means Packets with different exp will be counted separately;
      9 means All packets with different exp will be counted together."
    ::= { mplsLspPeEntry 66 }

mplsLspPeOAMLmSingleInterval OBJECT-TYPE
    SYNTAX INTEGER         
    {    
        one-hundred-ms(1),
        one-sec(2),
        ten-sec(3)
    }
    MAX-ACCESS read-write
    STATUS current
    DESCRIPTION
      "Config Interval."
    ::= { mplsLspPeEntry 67 }	

mplsLspPeOAMLmSingleCacheSize    OBJECT-TYPE
    SYNTAX Integer32 (1..512)
    MAX-ACCESS read-write
    STATUS current
    DESCRIPTION
      "Configure single-ended loss measurment cache size."
    DEFVAL { 128 } 
    ::= { mplsLspPeEntry 68 }
    
mplsLspPeOAMLmEnableState OBJECT-TYPE
    SYNTAX INTEGER {enable-dual(1), enable-single(2), disable(3)}
    MAX-ACCESS read-write
    STATUS current
    DESCRIPTION
      "Enable or disable oam-y1731 loss measurment."    
    DEFVAL { disable } 
    ::= { mplsLspPeEntry 70 }   

mplsLspPeOAMLmLocalLossThreshold    OBJECT-TYPE
    SYNTAX Integer32 (0..100)
    MAX-ACCESS read-write
    STATUS current
    DESCRIPTION
      "Local packet loss percentage, 0 means threshold not enabled."
    DEFVAL { 0 } 
    ::= { mplsLspPeEntry 71 }
    
mplsLspPeOAMLmRemoteLossThreshold    OBJECT-TYPE
    SYNTAX Integer32 (0..100)
    MAX-ACCESS read-write
    STATUS current
    DESCRIPTION
      "Local packet loss percentage, 0 means threshold not enabled."
    DEFVAL { 0 } 
    ::= { mplsLspPeEntry 72 }   

mplsLspPeOAMLmSingleRxCount    OBJECT-TYPE
    SYNTAX Integer32 (0..255)
    MAX-ACCESS read-only
    STATUS current
    DESCRIPTION
      "LMM single-ended packet Rx count."
    ::= { mplsLspPeEntry 73 } 

mplsLspPeOAMLmSingleTxCount    OBJECT-TYPE
    SYNTAX Integer32 (0..255)
    MAX-ACCESS read-only
    STATUS current
    DESCRIPTION
      "LMM single-ended packet Tx count."
    ::= { mplsLspPeEntry 74 } 

mplsLspPeOAMLmSingleSuccessRate    OBJECT-TYPE
    SYNTAX Integer32 (0..100)
    MAX-ACCESS read-only
    STATUS current
    DESCRIPTION
      "LMM single-ended success rate."
    ::= { mplsLspPeEntry 75 } 

mplsLspPeOAMLmSingleStartTime OBJECT-TYPE
    SYNTAX  OCTET STRING(SIZE(1..50))
    MAX-ACCESS read-only
    STATUS current
    DESCRIPTION
    	"LMM proactive single-ended start time."
    ::= { mplsLspPeEntry 76 }
	
mplsLspPeOAMLmSingleEndTime OBJECT-TYPE
    SYNTAX  OCTET STRING(SIZE(1..50))
    MAX-ACCESS read-only
    STATUS current
    DESCRIPTION
    	"LMM proactive single-ended end time."
    ::= { mplsLspPeEntry 77 }
	
mplsLspPeIngressTable OBJECT-TYPE
    SYNTAX  SEQUENCE OF   MplsLspPeIngressEntry
    MAX-ACCESS not-accessible
    STATUS   current
    DESCRIPTION
     "Table of mpls lsp-pe ingress configure."
    ::= { mpls 15 }

mplsLspPeIngressEntry OBJECT-TYPE
    SYNTAX  MplsLspPeIngressEntry
    MAX-ACCESS not-accessible
    STATUS current
    DESCRIPTION
     "Entry of mplsLspPeIngressTable."
    INDEX   { mplsLspPeIngressLspName }
    ::= { mplsLspPeIngressTable 1 }

MplsLspPeIngressEntry   ::=
    SEQUENCE {
        mplsLspPeIngressLspName  OCTET STRING,
        mplsLspPeIngressInlabel  Integer32,
        mplsLspPeIngressRowStatus RowStatus
        }

mplsLspPeIngressLspName OBJECT-TYPE
    SYNTAX  OCTET STRING(SIZE(1..20))
    MAX-ACCESS not-accessible
    STATUS current
    DESCRIPTION
     "Identifying value for MPLS Lsp-pe."
    ::= { mplsLspPeIngressEntry 1 }

mplsLspPeIngressInlabel OBJECT-TYPE
    SYNTAX  Integer32(16..1048575)
    MAX-ACCESS read-write
    STATUS current
    DESCRIPTION
     "Incoming label of the Lsp-pe."
    ::= { mplsLspPeIngressEntry 2 }

mplsLspPeIngressRowStatus OBJECT-TYPE
    SYNTAX RowStatus
    MAX-ACCESS read-create
    STATUS current
    DESCRIPTION
        "The status of this conceptual row.Now only realize CreateAndGo and Destroy and Active.
        1 means Active
        4 means CreateAndGo
        6 means Destroy"
    ::= { mplsLspPeIngressEntry 10 }   

mplsLspPeEgressTable OBJECT-TYPE
    SYNTAX  SEQUENCE OF   MplsLspPeEgressEntry
    MAX-ACCESS not-accessible
    STATUS   current
    DESCRIPTION 
    	"Table of mpls lsp-pe egress configure."
    ::= { mpls 16 }
    
mplsLspPeEgressEntry OBJECT-TYPE
    SYNTAX  MplsLspPeEgressEntry
    MAX-ACCESS not-accessible
    STATUS current
    DESCRIPTION 
    	"Entries of mplsLspPeEgressTable."
    INDEX   { mplsLspPeEgressLspName }
    ::= { mplsLspPeEgressTable 1 }

MplsLspPeEgressEntry   ::=
    SEQUENCE {
        mplsLspPeEgressLspName 		OCTET STRING,
        mplsLspPeEgressOutlabel		Integer32,
        mplsLspPeEgressNextHop  	  IpAddress,
        mplsLspPeEgressOutIfindex		Integer32,
        mplsLspPeEgressOutMemIfindex	Integer32,
        mplsLspPeEgressRowStatus   RowStatus   
        }

mplsLspPeEgressLspName OBJECT-TYPE
    SYNTAX  OCTET STRING(SIZE(1..20))
    MAX-ACCESS not-accessible
    STATUS current
    DESCRIPTION 
    	"Identifying value for MPLS Lsp-pe."
    ::= { mplsLspPeEgressEntry 1 }

mplsLspPeEgressOutlabel OBJECT-TYPE
    SYNTAX  Integer32(16..1048575)
    MAX-ACCESS read-create
    STATUS current
    DESCRIPTION 
    	"Outgoing label of the Lsp-pe."
    ::= { mplsLspPeEgressEntry 2 }

mplsLspPeEgressNextHop OBJECT-TYPE
    SYNTAX  IpAddress
    MAX-ACCESS read-create
    STATUS current
    DESCRIPTION 
    	"Nexthop Address(IPV4) for the Lsp-pe. Out-going 
    	 interface and nexthop ip address can not be configured
    	 at the same time."
    ::= { mplsLspPeEgressEntry 3 }

mplsLspPeEgressOutIfindex OBJECT-TYPE
    SYNTAX  Integer32(0..65535)
    MAX-ACCESS read-create
    STATUS current
    DESCRIPTION 
    	"Outgoing interface for the Lsp-pe. Out-going 
    	 interface and nexthop ip address can not be configured
    	 at the same time."
    ::= { mplsLspPeEgressEntry 4 }
    
mplsLspPeEgressOutMemIfindex OBJECT-TYPE
    SYNTAX  Integer32(0..65535)
    MAX-ACCESS read-create
    STATUS current
    DESCRIPTION 
    	"Member port index, this field is required only when 
    	 out-going interface is vlan interface."
    ::= { mplsLspPeEgressEntry 5 }
            
mplsLspPeEgressRowStatus OBJECT-TYPE
    SYNTAX RowStatus
    MAX-ACCESS read-create
    STATUS current
    DESCRIPTION
        "The status of this conceptual row.Now only realize CreateAndGo and Destroy and Active.
        1 means Active
        4 means CreateAndGo
        6 means Destroy"
    ::= { mplsLspPeEgressEntry 10 }   

mplsLspPTable OBJECT-TYPE
    SYNTAX  SEQUENCE OF   MplsLspPEntry
    MAX-ACCESS not-accessible
    STATUS   current
    DESCRIPTION 
    	"Table of all mpls lsp-p instances."
    ::= { mpls 17 }

mplsLspPEntry OBJECT-TYPE
    SYNTAX  MplsLspPEntry
    MAX-ACCESS not-accessible
    STATUS current
    DESCRIPTION
     "Entry of mplsLspPTable."
    INDEX   { mplsLspPName}
    ::= { mplsLspPTable 1 }

MplsLspPEntry   ::=
    SEQUENCE {
        mplsLspPName 		      OCTET STRING,
        mplsLspPRowStatus		  RowStatus,
        mplsLspPOAMMegId			OCTET STRING,
        mplsLspPOAMMegIdIcc   Integer32,
        mplsLspPOAMMipState		INTEGER,
        mplsLspPOAMMegLevel   Integer32,
        mplsLspPDescription	  OCTET STRING,
        mplsLspPStats         INTEGER                
        }

mplsLspPName OBJECT-TYPE
    SYNTAX  OCTET STRING(SIZE(1..20))
    MAX-ACCESS not-accessible
    STATUS current
    DESCRIPTION
     "Identifying value for MPLS Lsp-p."
    ::= { mplsLspPEntry 1 }

mplsLspPRowStatus OBJECT-TYPE
    SYNTAX RowStatus
    MAX-ACCESS read-create
    STATUS current
    DESCRIPTION
        "The status of this conceptual row.Now only realize CreateAndGo and Destroy and Active.
        1 means Active
        4 means CreateAndGo
        6 means Destroy"
    ::= { mplsLspPEntry 10 }  
      
mplsLspPOAMMegId OBJECT-TYPE
    SYNTAX OCTET STRING (SIZE (1..12))
    MAX-ACCESS read-write
    STATUS current
    DESCRIPTION
      "MEG ID of the lsp-p."  
    ::= { mplsLspPEntry 11 }	   

mplsLspPOAMMegIdIcc OBJECT-TYPE
    SYNTAX Integer32 (1..6)
    MAX-ACCESS read-write
    STATUS current
    DESCRIPTION
      "ICC length of MEG ID."
    DEFVAL { 6 }
    ::= { mplsLspPEntry 12 }	
    
mplsLspPOAMMipState OBJECT-TYPE
    SYNTAX INTEGER {enable(1), disable(2)}
    MAX-ACCESS read-write
    STATUS current
    DESCRIPTION
       "MIP state of the lsp."
    DEFVAL { disable }       
    ::= { mplsLspPEntry 13 }    
    
mplsLspPOAMMegLevel OBJECT-TYPE
    SYNTAX Integer32 (0..7)
    MAX-ACCESS read-write
    STATUS current
    DESCRIPTION
      "OAM level."
    DEFVAL { 7 }
    ::= { mplsLspPEntry 14 }	    

mplsLspPDescription OBJECT-TYPE
    SYNTAX  OCTET STRING (SIZE(1..20))
    MAX-ACCESS read-write
    STATUS current
    DESCRIPTION 
    	"Characters describing of this p type LSP.
    	 Only less than 20 octets is accepted."
    ::= { mplsLspPEntry 15 }
    
mplsLspPStats OBJECT-TYPE
    SYNTAX  INTEGER {enable(1),disable(2)}
    MAX-ACCESS read-write
    STATUS current
    DESCRIPTION 
       "Set statistics for mpls lsp-p. The meanings of the values are:
        enable(1)  -  enable statistics;
        disable(2) -  disable statistics;"  
    DEFVAL { 2 }
    ::= { mplsLspPEntry 16 }    
      
mplsLspPEastTable OBJECT-TYPE
    SYNTAX  SEQUENCE OF   MplsLspPEastEntry
    MAX-ACCESS not-accessible
    STATUS   current
    DESCRIPTION
     "Table of east configuration of all mpls lsp-p instances."
    ::= { mpls 18 }

mplsLspPEastEntry OBJECT-TYPE
    SYNTAX  MplsLspPEastEntry
    MAX-ACCESS not-accessible
    STATUS current
    DESCRIPTION
     "Entry of mplsLspPfEastTable."
    INDEX   { mplsLspPEastLspName}
    ::= { mplsLspPEastTable 1 }

MplsLspPEastEntry   ::=
    SEQUENCE {
        mplsLspPEastLspName 		OCTET STRING,
        mplsLspPEastInlabel		  Integer32,
        mplsLspPEastOutlabel	  Integer32,
        mplsLspPEastNextHop  	  IpAddress,
        mplsLspPEastTunnel			OCTET STRING, 
        mplsLspPEastOutIfindex		Integer32,
        mplsLspPEastOutMemIfindex	Integer32,   
        mplsLspPEastReplaceExp	INTEGER,                
        mplsLspPEastRowStatus		RowStatus,
        mplsLspPEastState		INTEGER,
        mplsLspPEastIngressPkts		Counter64,
        mplsLspPEastIngressbytes	Counter64,
        mplsLspPEastEgressPkts		Counter64,
        mplsLspPEastEgressBytes		Counter64                                        
        }

mplsLspPEastLspName OBJECT-TYPE
    SYNTAX  OCTET STRING(SIZE(1..20))
    MAX-ACCESS not-accessible
    STATUS current
    DESCRIPTION
     "Identifying value for MPLS Lsp-p."
    ::= { mplsLspPEastEntry 1 }

mplsLspPEastInlabel OBJECT-TYPE
    SYNTAX  Integer32(16..1048575)
    MAX-ACCESS read-write
    STATUS current
    DESCRIPTION
     "East incoming label of the Lsp-p."
    ::= { mplsLspPEastEntry 2 }

mplsLspPEastOutlabel OBJECT-TYPE
    SYNTAX  Integer32(16..1048575)
    MAX-ACCESS read-write
    STATUS current
    DESCRIPTION
     "East outgoing label of the Lsp-p."
    ::= { mplsLspPEastEntry 3 }

mplsLspPEastNextHop OBJECT-TYPE
    SYNTAX  IpAddress
    MAX-ACCESS read-write
    STATUS current
    DESCRIPTION
     "East nexthop Address(IPV4) for the Lsp-p."
    ::= { mplsLspPEastEntry 4 }

mplsLspPEastTunnel OBJECT-TYPE
    SYNTAX  OCTET STRING(SIZE(1..20))
    MAX-ACCESS read-write
    STATUS current
    DESCRIPTION
     "East tunnel name."
    ::= { mplsLspPEastEntry 5 }

mplsLspPEastOutIfindex OBJECT-TYPE
    SYNTAX  Integer32(0..65535)
    MAX-ACCESS read-create
    STATUS current
    DESCRIPTION 
    	"Outgoing interface for the Lsp-p. Out-going 
    	 interface , tunnel, and nexthop ip address 
    	 can not be configured at the same time."
    ::= { mplsLspPEastEntry 6 }
    
mplsLspPEastOutMemIfindex OBJECT-TYPE
    SYNTAX  Integer32(0..65535)
    MAX-ACCESS read-create
    STATUS current
    DESCRIPTION 
    	"Member port index, this field is required only when 
    	 out-going interface is vlan interface."
    ::= { mplsLspPEastEntry 7 }
        
mplsLspPEastReplaceExp OBJECT-TYPE
    SYNTAX  INTEGER {enable(1), disable(2)}
    MAX-ACCESS read-create
    STATUS current
    DESCRIPTION 
    	"Replace exp."
    ::= { mplsLspPEastEntry 8 }        
        
mplsLspPEastRowStatus OBJECT-TYPE
    SYNTAX RowStatus
    MAX-ACCESS read-create
    STATUS current
    DESCRIPTION
        "The status of this conceptual row.
         Now only realize CreateAndGo and Destroy and Active."
    ::= { mplsLspPEastEntry 10 }

mplsLspPEastState OBJECT-TYPE
    SYNTAX INTEGER {active(1), inactive(2)}
    MAX-ACCESS read-only
    STATUS current
    DESCRIPTION
       "The state of the mpls lsp-p east. The meanings of the values are:
        active(1)   -  active;
        inactive(2) -  inactive;"  
    ::= { mplsLspPEastEntry 11 }       

mplsLspPEastIngressPkts         OBJECT-TYPE
    SYNTAX          Counter64
    MAX-ACCESS      read-only
    STATUS          current
    DESCRIPTION
        "Ingress packets number of lsp-p east."
    ::= { mplsLspPEastEntry 20 }

mplsLspPEastIngressbytes         OBJECT-TYPE
    SYNTAX          Counter64
    MAX-ACCESS      read-only
    STATUS          current
    DESCRIPTION
        "Ingress bytes number of lsp-p east."
    ::= { mplsLspPEastEntry 21 }

mplsLspPEastEgressPkts         OBJECT-TYPE
    SYNTAX          Counter64
    MAX-ACCESS      read-only
    STATUS          current
    DESCRIPTION
        "Egress packets number of lsp-p east."
    ::= { mplsLspPEastEntry 22 }
    
mplsLspPEastEgressBytes         OBJECT-TYPE
    SYNTAX          Counter64
    MAX-ACCESS      read-only
    STATUS          current
    DESCRIPTION
        "Egress bytes number of lsp-p east."
    ::= { mplsLspPEastEntry 23 }   
     
mplsLspPWestTable OBJECT-TYPE
    SYNTAX  SEQUENCE OF   MplsLspPWestEntry
    MAX-ACCESS not-accessible
    STATUS   current
    DESCRIPTION
     "Table of west configuration of all mpls lsp-p instances."
    ::= { mpls 19 }

mplsLspPWestEntry OBJECT-TYPE
    SYNTAX  MplsLspPWestEntry
    MAX-ACCESS not-accessible
    STATUS current
    DESCRIPTION
     "Entry of mplsLspPWestTable."
    INDEX   { mplsLspPWestLspName}
    ::= { mplsLspPWestTable 1 }

MplsLspPWestEntry   ::=
    SEQUENCE {
        mplsLspPWestLspName 		OCTET STRING,
        mplsLspPWestInlabel		  Integer32,
        mplsLspPWestOutlabel	  Integer32,
        mplsLspPWestNextHop  	  IpAddress, 
        mplsLspPWestTunnel			OCTET STRING,
        mplsLspPWestOutIfindex		Integer32,
        mplsLspPWestOutMemIfindex	Integer32,        
        mplsLspPWestReplaceExp	INTEGER,              
        mplsLspPWestRowStatus		RowStatus,
        mplsLspPWestState				INTEGER,
        mplsLspPWestIngressPkts		Counter64,
        mplsLspPWestIngressbytes	Counter64,
        mplsLspPWestEgressPkts		Counter64,
        mplsLspPWestEgressBytes		Counter64                                   
        }

mplsLspPWestLspName OBJECT-TYPE
    SYNTAX  OCTET STRING(SIZE(1..20))
    MAX-ACCESS not-accessible
    STATUS current
    DESCRIPTION
     "Identifying value for MPLS Lsp-p."
    ::= { mplsLspPWestEntry 1 }

mplsLspPWestInlabel OBJECT-TYPE
    SYNTAX  Integer32(16..1048575)
    MAX-ACCESS read-write
    STATUS current
    DESCRIPTION
     "West incoming label of the Lsp-p."
    ::= { mplsLspPWestEntry 2 }

mplsLspPWestOutlabel OBJECT-TYPE
    SYNTAX  Integer32(16..1048575)
    MAX-ACCESS read-write
    STATUS current
    DESCRIPTION
     "West outgoing label of the Lsp-p."
    ::= { mplsLspPWestEntry 3 }

mplsLspPWestNextHop OBJECT-TYPE
    SYNTAX  IpAddress
    MAX-ACCESS read-write
    STATUS current
    DESCRIPTION
     "West nexthop Address(IPV4) for the Lsp-p."
    ::= { mplsLspPWestEntry 4 }

mplsLspPWestTunnel OBJECT-TYPE
    SYNTAX  OCTET STRING(SIZE(1..20))
    MAX-ACCESS read-write
    STATUS current
    DESCRIPTION
     "West tunnel name."
    ::= { mplsLspPWestEntry 5 }

mplsLspPWestOutIfindex OBJECT-TYPE
    SYNTAX  Integer32(0..65535)
    MAX-ACCESS read-create
    STATUS current
    DESCRIPTION 
    	"Outgoing interface for the Lsp-p. Out-going 
    	 interface , tunnel, and nexthop ip address 
    	 can not be configured at the same time."
    ::= { mplsLspPWestEntry 6 }
    
mplsLspPWestOutMemIfindex OBJECT-TYPE
    SYNTAX  Integer32(0..65535)
    MAX-ACCESS read-create
    STATUS current
    DESCRIPTION 
    	"Member port index, this field is required only when 
    	 out-going interface is vlan interface."
    ::= { mplsLspPWestEntry 7 }

mplsLspPWestReplaceExp OBJECT-TYPE
    SYNTAX  INTEGER {enable(1), disable(2)}
    MAX-ACCESS read-create
    STATUS current
    DESCRIPTION 
    	"Replace exp."
    ::= { mplsLspPWestEntry 8 }  
            
mplsLspPWestRowStatus OBJECT-TYPE
    SYNTAX RowStatus
    MAX-ACCESS read-create
    STATUS current
    DESCRIPTION
        "The status of this conceptual row.
         Now only realize CreateAndGo and Destroy and Active."
    ::= { mplsLspPWestEntry 10 }

mplsLspPWestState OBJECT-TYPE
    SYNTAX INTEGER {active(1), inactive(2)}
    MAX-ACCESS read-only
    STATUS current
    DESCRIPTION
       "The state of the mpls lsp-p west. The meanings of the values are:
        active(1)   -  active;
        inactive(2) -  inactive;"  
    ::= { mplsLspPWestEntry 11 }       

mplsLspPWestIngressPkts         OBJECT-TYPE
    SYNTAX          Counter64
    MAX-ACCESS      read-only
    STATUS          current
    DESCRIPTION
        "Ingress packets number of lsp-p west."
    ::= { mplsLspPWestEntry 20 }

mplsLspPWestIngressbytes         OBJECT-TYPE
    SYNTAX          Counter64
    MAX-ACCESS      read-only
    STATUS          current
    DESCRIPTION
        "Ingress bytes number of lsp-p west."
    ::= { mplsLspPWestEntry 21 }

mplsLspPWestEgressPkts         OBJECT-TYPE
    SYNTAX          Counter64
    MAX-ACCESS      read-only
    STATUS          current
    DESCRIPTION
        "Egress packets number of lsp-p west."
    ::= { mplsLspPWestEntry 22 }
    
mplsLspPWestEgressBytes         OBJECT-TYPE
    SYNTAX          Counter64
    MAX-ACCESS      read-only
    STATUS          current
    DESCRIPTION
        "Egress bytes number of lsp-p west."
    ::= { mplsLspPWestEntry 23 }   
         
mplsTunnelTable OBJECT-TYPE
    SYNTAX  SEQUENCE OF   MplsTunnelEntry
    MAX-ACCESS not-accessible
    STATUS   current
    DESCRIPTION
     "Table of all mpls tunnel instances."
    ::= { mpls 20 }

mplsTunnelEntry OBJECT-TYPE
    SYNTAX  MplsTunnelEntry
    MAX-ACCESS not-accessible
    STATUS current
    DESCRIPTION
     "Entry of mplsTunnelTable."
    INDEX   { mplsTunnelName}
    ::= { mplsTunnelTable 1 }

MplsTunnelEntry   ::=
    SEQUENCE {
        mplsTunnelName           	OCTET STRING,       
        mplsTunnelApsType				 	INTEGER,
        mplsTunnelRowStatus      	RowStatus,
        mplsTunnelPrimaryLspPe	 	OCTET STRING,
        mplsTunnelSecondaryLspPe 	OCTET STRING,
        mplsTunnelDescription  	  OCTET STRING,        
        mplsTunnelSelectedLspPe	 	OCTET STRING,
        mplsTunnelG8131Mode							INTEGER,
        mplsTunnelG8131WTRTimer					Integer32,
        mplsTunnelG8131HoldOffTimer			Integer32,
        mplsTunnelG8131Action						INTEGER,
        mplsTunnelG8131WorkingLSP				OCTET STRING,
        mplsTunnelG8131ProtectionLSP		OCTET STRING,
        mplsTunnelG8131ActivePath				INTEGER,
        mplsTunnelG8131WTRTimeLeft			Integer32,
        mplsTunnelG8131HoldOffTimeLeft	Integer32,
        mplsTunnelG8131DFOPState				INTEGER,
        mplsTunnelG8131CurrentState			INTEGER,
        mplsTunnelG8131LastState				INTEGER,
        mplsTunnelG8131CurrentEvent			INTEGER,
        mplsTunnelG8131FarEndLastEvent	INTEGER,
        mplsTunnelG8131RequestSignal		INTEGER
        }

mplsTunnelName OBJECT-TYPE
    SYNTAX  OCTET STRING(SIZE(1..20))
    MAX-ACCESS not-accessible
    STATUS current
    DESCRIPTION 
    	"Identifying value for mpls tunnel."
    ::= { mplsTunnelEntry 1 }

mplsTunnelApsType OBJECT-TYPE
    SYNTAX  INTEGER { aps(1), non-aps(2) }
    MAX-ACCESS read-create
    STATUS current
    DESCRIPTION 
    	"APS type for the tunnel."
    ::= { mplsTunnelEntry 2 }
    
mplsTunnelRowStatus OBJECT-TYPE
    SYNTAX RowStatus
    MAX-ACCESS read-create
    STATUS current
    DESCRIPTION
        "The status of this conceptual row.
         Now only realize CreateAndGo and Destroy and Active."
    ::= { mplsTunnelEntry 10 }

mplsTunnelPrimaryLspPe OBJECT-TYPE
    SYNTAX  OCTET STRING(SIZE(0..20))
    MAX-ACCESS read-write
    STATUS current
    DESCRIPTION
     "Primary lsp-pe name of the mpls tunnel."
    ::= { mplsTunnelEntry 11 }

mplsTunnelSecondaryLspPe OBJECT-TYPE
    SYNTAX  OCTET STRING(SIZE(0..20))
    MAX-ACCESS read-write
    STATUS current
    DESCRIPTION
     "Secondary lsp-pe name of the mpls tunnel."
    ::= { mplsTunnelEntry 12 }

mplsTunnelDescription OBJECT-TYPE
    SYNTAX  OCTET STRING (SIZE(1..20))
    MAX-ACCESS read-write
    STATUS current
    DESCRIPTION 
    	"Characters describing of this MPLS tunnel.
    	 Only less than 20 octets is accepted."
    ::= { mplsTunnelEntry 13 }
    
mplsTunnelSelectedLspPe OBJECT-TYPE
    SYNTAX  OCTET STRING (SIZE(1..20))
    MAX-ACCESS read-only
    STATUS current
    DESCRIPTION 
    	"Selected lsp-pe name of the mpls tunnel."
    ::= { mplsTunnelEntry 25 }    

mplsTunnelG8131Mode OBJECT-TYPE
    SYNTAX  INTEGER { revertive(1), non-revertive(2) }
    MAX-ACCESS read-only
    STATUS current
    DESCRIPTION
    	"G8131 mode for the mpls tunnel."
    ::= { mplsTunnelEntry 30 }

mplsTunnelG8131WTRTimer OBJECT-TYPE
    SYNTAX  Integer32 (0..12)
    MAX-ACCESS read-write
    STATUS current
    DESCRIPTION
    	"G8131 wait-to-restore timer value for the mpls tunnel, in minutes."
    DEFVAL {5}
    ::= { mplsTunnelEntry 31 }

mplsTunnelG8131HoldOffTimer OBJECT-TYPE
    SYNTAX  Integer32 (0..100)
    MAX-ACCESS read-write
    STATUS current
    DESCRIPTION
    	"G8131 hold-off timer value for the mpls tunnel, steps of 100ms."
    DEFVAL {0}
    ::= { mplsTunnelEntry 32 }

mplsTunnelG8131Action OBJECT-TYPE
    SYNTAX  INTEGER { force-switch(1), manual-swtich-to-working(2),
                      manual-switch-to-protection(3), lockout(4), 
                      exercise(5), clear(6) }
    MAX-ACCESS read-write
    STATUS current
    DESCRIPTION
    	"G8131 actions for the mpls tunnel."
    ::= { mplsTunnelEntry 33 }

mplsTunnelG8131WorkingLSP OBJECT-TYPE
    SYNTAX  OCTET STRING (SIZE(0..20))
    MAX-ACCESS read-only
    STATUS current
    DESCRIPTION
    	"G8131 working lsp for the mpls tunnel."
    ::= { mplsTunnelEntry 40 }

mplsTunnelG8131ProtectionLSP OBJECT-TYPE
    SYNTAX  OCTET STRING (SIZE(0..20))
    MAX-ACCESS read-only
    STATUS current
    DESCRIPTION
    	"G8131 protection lsp for the mpls tunnel."
    ::= { mplsTunnelEntry 41 }
    
mplsTunnelG8131ActivePath OBJECT-TYPE
    SYNTAX  INTEGER { none(0), working-lsp(1), protection-lsp(2) }
    MAX-ACCESS read-only
    STATUS current
    DESCRIPTION
    	"G8131 active path for the mpls tunnel."
    ::= { mplsTunnelEntry 42 }    
    
mplsTunnelG8131WTRTimeLeft OBJECT-TYPE
    SYNTAX  Integer32
    MAX-ACCESS read-only
    STATUS current
    DESCRIPTION
    	"Left time of G8131 wait-to-restore timer of the mpls tunnel."
    ::= { mplsTunnelEntry 43 }   
    
mplsTunnelG8131HoldOffTimeLeft OBJECT-TYPE
    SYNTAX  Integer32
    MAX-ACCESS read-only
    STATUS current
    DESCRIPTION
    	"Left time of G8131 hold-off timer of the mpls tunnel."
    ::= { mplsTunnelEntry 44 }           
    
mplsTunnelG8131DFOPState OBJECT-TYPE
    SYNTAX  INTEGER 
    {
        not-in-defect-mode(1),
        b-bit-mismatch-defect(2),
        r-bit-mismatch-defect(3),
        invalid-request-state(4),
        aps-recv-on-working-entity(5),
        aps-pdu-not-recv-after-state-change(6),
        a-bit-mismatch-defect(7),
        d-bit-mismatch-defect(8),
        t-bit-mismatch-defect(9)                        
    }
    MAX-ACCESS read-only
    STATUS current
    DESCRIPTION
    	"G8131 DFOP state of the mpls tunnel."
    ::= { mplsTunnelEntry 45 }  

mplsTunnelG8131CurrentState OBJECT-TYPE
    SYNTAX  INTEGER 
    {
        no-request-working-active(0),
        no-request-protection-avtive(1),
        lockout-of-protection(2),
        forced-switch(3),
        signal-fail-on-working(4),
        signal-fail-on-protection(5),
        signal-degrade-on-working(6),
        signal-degrade-on-protection(7),
        manual-switch-to-protection(8),
        manual-switch-to-working(9),
        wait-to-restore(10),
        do-not-revert(11),
        exercise-on-working(12),
        exercise-on-protection(13),
        reverse-request-on-working(14),
        reverse-request-on-protection(15),
        none(16)
    }
    MAX-ACCESS read-only
    STATUS current
    DESCRIPTION
    	"G8131 current state of the mpls tunnel."
    ::= { mplsTunnelEntry 46 }  
    
mplsTunnelG8131LastState OBJECT-TYPE
    SYNTAX  INTEGER 
    {
        no-request-working-active(0),
        no-request-protection-avtive(1),
        lockout-of-protection(2),
        forced-switch(3),
        signal-fail-on-working(4),
        signal-fail-on-protection(5),
        signal-degrade-on-working(6),
        signal-degrade-on-protection(7),
        manual-switch-to-protection(8),
        manual-switch-to-working(9),
        wait-to-restore(10),
        do-not-revert(11),
        exercise-on-working(12),
        exercise-on-protection(13),
        reverse-request-on-working(14),
        reverse-request-on-protection(15),
        none(16)
    }
    MAX-ACCESS read-only
    STATUS current
    DESCRIPTION
    	"G8131 last state of the mpls tunnel."
    ::= { mplsTunnelEntry 47 }  
    
mplsTunnelG8131CurrentEvent OBJECT-TYPE
    SYNTAX  INTEGER 
    {
        local-lockout(0),
        local-force-switch(1),
        local-signal-fail-on-working(2),
        local-working-recover-from-signal-fail(3),
        local-signal-fail-on-protection(4),
        local-protection-recover-from-signal-fail(5),
        local-signal-degrade-on-working(6),
        local-working-recover-from-signal-degrade(7),
        local-signal-degrade-on-protection(8),
        local-protection-recover-from-signal-degrade(9),
        local-manual-switch-to-protection(10),
        local-manual-switch-to-working(11),
        local-clear(12),
        local-exercise(13),
        local-wtr-timer-expire(14),
        remote-lockout(15),
        remote-signal-fail-on-protection(16),
        remote-force-switch(17),
        remote-signal-fail-on-working(18),
        remote-signal-degrade-on-working(19),
        remote-signal-degrade-on-protection(20),
        remote-manual-switch-to-protection(21),
        remote-manual-switch-to-working(22),
        remote-wait-to-restore(23),
        remote-exercise-on-working(24),
        remote-exercise-on-protection(25),
        remote-reverse-request-on-working(26),
        remote-reverse-request-on-protection(27),
        remote-no-request-null(28),
        remote-no-request-normal(29),
        remote-do-not-revert(30),
        none(31)
    }
    MAX-ACCESS read-only
    STATUS current
    DESCRIPTION
    	"G8131 current event of the mpls tunnel."
    ::= { mplsTunnelEntry 48 }  
    
mplsTunnelG8131FarEndLastEvent OBJECT-TYPE
    SYNTAX  INTEGER 
    {
        local-lockout(0),
        local-force-switch(1),
        local-signal-fail-on-working(2),
        local-working-recover-from-signal-fail(3),
        local-signal-fail-on-protection(4),
        local-protection-recover-from-signal-fail(5),
        local-signal-degrade-on-working(6),
        local-working-recover-from-signal-degrade(7),
        local-signal-degrade-on-protection(8),
        local-protection-recover-from-signal-degrade(9),
        local-manual-switch-to-protection(10),
        local-manual-switch-to-working(11),
        local-clear(12),
        local-exercise(13),
        local-wtr-timer-expire(14),
        remote-lockout(15),
        remote-signal-fail-on-protection(16),
        remote-force-switch(17),
        remote-signal-fail-on-working(18),
        remote-signal-degrade-on-working(19),
        remote-signal-degrade-on-protection(20),
        remote-manual-switch-to-protection(21),
        remote-manual-switch-to-working(22),
        remote-wait-to-restore(23),
        remote-exercise-on-working(24),
        remote-exercise-on-protection(25),
        remote-reverse-request-on-working(26),
        remote-reverse-request-on-protection(27),
        remote-no-request-null(28),
        remote-no-request-normal(29),
        remote-do-not-revert(30),
        none(31)
    }
    MAX-ACCESS read-only
    STATUS current
    DESCRIPTION
    	"G8131 far end last event of the mpls tunnel."
    ::= { mplsTunnelEntry 49 }  
    
mplsTunnelG8131RequestSignal OBJECT-TYPE
    SYNTAX  INTEGER { normal(1), null(2), none(3) }
    MAX-ACCESS read-only
    STATUS current
    DESCRIPTION
    	"G8131 request signal of the mpls tunnel."
    ::= { mplsTunnelEntry 50 }                             

mplsPwSPeTable OBJECT-TYPE
    SYNTAX  SEQUENCE OF   MplsPwSPeEntry
    MAX-ACCESS not-accessible
    STATUS   current
    DESCRIPTION
     "Table of all mpls pw s-pe instances."
    ::= { mpls 23 }

mplsPwSPeEntry OBJECT-TYPE
    SYNTAX  MplsPwSPeEntry
    MAX-ACCESS not-accessible
    STATUS current
    DESCRIPTION
     "Entry of mplsPwSPeTable."
    INDEX   { mplsPwSPeName }
    ::= { mplsPwSPeTable 1 }

MplsPwSPeEntry   ::=
    SEQUENCE {
        mplsPwSPeName 	        OCTET STRING,
        mplsPwSPeRowStatus      RowStatus,
        mplsPwSPeOAMMegId	OCTET STRING,
        mplsPwSPeOAMMegIdIcc    Integer32,
        mplsPwSPeOAMMipState	INTEGER,
        mplsPwSPeOAMMegLevel    Integer32,
        mplsPwSPeDescription	  OCTET STRING,
        mplsPwSpeStats          INTEGER               
}

mplsPwSPeName OBJECT-TYPE
    SYNTAX  OCTET STRING(SIZE(1..20))
    MAX-ACCESS not-accessible
    STATUS current
    DESCRIPTION
     "Identifying value for MPLS pw s-pe."
    ::= { mplsPwSPeEntry 1 }

mplsPwSPeRowStatus OBJECT-TYPE
    SYNTAX RowStatus
    MAX-ACCESS read-create
    STATUS current
    DESCRIPTION
        "The status of this conceptual row.
         Now only realize CreateAndGo and Destroy and Active."
    ::= { mplsPwSPeEntry 10 }
      
mplsPwSPeOAMMegId OBJECT-TYPE
    SYNTAX OCTET STRING (SIZE (1..12))
    MAX-ACCESS read-write
    STATUS current
    DESCRIPTION
      "MEG ID of the pw spe."  
    ::= { mplsPwSPeEntry 11 }	   

mplsPwSPeOAMMegIdIcc OBJECT-TYPE
    SYNTAX Integer32 (1..6)
    MAX-ACCESS read-write
    STATUS current
    DESCRIPTION
      "ICC length of MEG ID."
    DEFVAL { 6 }
    ::= { mplsPwSPeEntry 12 }
    
mplsPwSPeOAMMipState OBJECT-TYPE
    SYNTAX INTEGER {enable(1), disable(2)}
    MAX-ACCESS read-write
    STATUS current
    DESCRIPTION
       "MIP state of the pw spe."
    DEFVAL { disable }       
    ::= { mplsPwSPeEntry 13 }    

mplsPwSPeOAMMegLevel OBJECT-TYPE
    SYNTAX Integer32 (0..7)
    MAX-ACCESS read-write
    STATUS current
    DESCRIPTION
      "OAM level."
    DEFVAL { 7 }
    ::= { mplsPwSPeEntry 14 }

mplsPwSPeDescription OBJECT-TYPE
    SYNTAX  OCTET STRING (SIZE(1..20))
    MAX-ACCESS read-write
    STATUS current
    DESCRIPTION 
    	"Characters describing of this S-PE type PW.
    	 Only less than 20 octets is accepted."
    ::= { mplsPwSPeEntry 15 }

mplsPwSpeStats OBJECT-TYPE
    SYNTAX  INTEGER {enable(1),disable(2)}
    MAX-ACCESS read-write
    STATUS current
    DESCRIPTION 
       "Set statistics for mpls pw s-pe. The meanings of the values are:
        enable(1)  -  enable statistics;
        disable(2) -  disable statistics;"  
    DEFVAL { 2 }
    ::= { mplsPwSPeEntry 16 }  
        
mplsPwSPeEastTable OBJECT-TYPE
    SYNTAX  SEQUENCE OF   MplsPwSPeEastEntry
    MAX-ACCESS not-accessible
    STATUS   current
    DESCRIPTION
     "Table of east configuration of all mpls pw s-pe instances."
    ::= { mpls 24 }

mplsPwSPeEastEntry OBJECT-TYPE
    SYNTAX  MplsPwSPeEastEntry
    MAX-ACCESS not-accessible
    STATUS current
    DESCRIPTION
     "Entry of mplsPwSPeEastTable."
    INDEX   { mplsPwSPeEastPwName}
    ::= { mplsPwSPeEastTable 1 }

MplsPwSPeEastEntry   ::=
    SEQUENCE {
        mplsPwSPeEastPwName   OCTET STRING,
        mplsPwSPeEastInlabel  Integer32,
        mplsPwSPeEastOutlabel   Integer32,
        mplsPwSPeEastTunnelName OCTET STRING, 
        mplsPwSPeEastCtrlWord 	INTEGER, 
        mplsPwSPeEastRowStatus	RowStatus,
        mplsPwSPeEastState			INTEGER,
        mplsPwSPeEastIngressPkts		Counter64,
        mplsPwSPeEastIngressbytes		Counter64,
        mplsPwSPeEastEgressPkts			Counter64,
        mplsPwSPeEastEgressBytes		Counter64        
        }

mplsPwSPeEastPwName OBJECT-TYPE
    SYNTAX  OCTET STRING(SIZE(1..20))
    MAX-ACCESS not-accessible
    STATUS current
    DESCRIPTION
     "Identifying value for MPLS pw s-pe."
    ::= { mplsPwSPeEastEntry 1 }

mplsPwSPeEastInlabel OBJECT-TYPE
    SYNTAX  Integer32(16..1048575)
    MAX-ACCESS read-write
    STATUS current
    DESCRIPTION
     "East incoming label of the MPLS pw s-pe."
    ::= { mplsPwSPeEastEntry 2 }

mplsPwSPeEastOutlabel OBJECT-TYPE
    SYNTAX  Integer32(16..1048575)
    MAX-ACCESS read-write
    STATUS current
    DESCRIPTION
     "East outgoing label of the MPLS pw s-pe."
    ::= { mplsPwSPeEastEntry 3 }

mplsPwSPeEastTunnelName OBJECT-TYPE
    SYNTAX  OCTET STRING(SIZE(0..20))
    MAX-ACCESS read-write
    STATUS current
    DESCRIPTION
     "MPLS tunnel name for the MPLS pw s-pe."
    ::= { mplsPwSPeEastEntry 4 }
    
mplsPwSPeEastCtrlWord  OBJECT-TYPE
    SYNTAX INTEGER {control-word(1), no-control-word(2)}
    MAX-ACCESS read-only
    STATUS current
    DESCRIPTION
       "The state of the mpls pw spe east control-word."  
    ::= { mplsPwSPeEastEntry 5 }  

mplsPwSPeEastRowStatus OBJECT-TYPE
    SYNTAX RowStatus
    MAX-ACCESS read-create
    STATUS current
    DESCRIPTION
        "The status of this conceptual row.
         Now only realize CreateAndGo and Destroy and Active."
    ::= { mplsPwSPeEastEntry 10 }

mplsPwSPeEastState OBJECT-TYPE
    SYNTAX INTEGER {up(1), down(2)}
    MAX-ACCESS read-only
    STATUS current
    DESCRIPTION
       "The state of the mpls pw spe east. The meanings of the values are:
        up(1)   -  the state is up;
        down(2) -  the state is down;"  
    ::= { mplsPwSPeEastEntry 11 }   

mplsPwSPeEastIngressPkts         OBJECT-TYPE
    SYNTAX          Counter64
    MAX-ACCESS      read-only
    STATUS          current
    DESCRIPTION
        "Ingress packets number of pw s-pe east."
    ::= { mplsPwSPeEastEntry 20 }

mplsPwSPeEastIngressbytes         OBJECT-TYPE
    SYNTAX          Counter64
    MAX-ACCESS      read-only
    STATUS          current
    DESCRIPTION
        "Ingress bytes number of pw s-pe east."
    ::= { mplsPwSPeEastEntry 21 }

mplsPwSPeEastEgressPkts         OBJECT-TYPE
    SYNTAX          Counter64
    MAX-ACCESS      read-only
    STATUS          current
    DESCRIPTION
        "Egress packets number of pw s-pe east."
    ::= { mplsPwSPeEastEntry 22 }
    
mplsPwSPeEastEgressBytes         OBJECT-TYPE
    SYNTAX          Counter64
    MAX-ACCESS      read-only
    STATUS          current
    DESCRIPTION
        "Egress bytes number of pw s-pe east."
    ::= { mplsPwSPeEastEntry 23 } 
      
mplsPwSPeWestTable OBJECT-TYPE
    SYNTAX  SEQUENCE OF   MplsPwSPeWestEntry
    MAX-ACCESS not-accessible
    STATUS   current
    DESCRIPTION
     "Table of west configuration of all mpls pw s-pe instances."
    ::= { mpls 25 }

mplsPwSPeWestEntry OBJECT-TYPE
    SYNTAX  MplsPwSPeWestEntry
    MAX-ACCESS not-accessible
    STATUS current
    DESCRIPTION
     "Entry of mplsPwSPeWestTable."
    INDEX   { mplsPwSPeWestPwName}
    ::= { mplsPwSPeWestTable 1 }

MplsPwSPeWestEntry   ::=
    SEQUENCE {
        mplsPwSPeWestPwName   OCTET STRING,
        mplsPwSPeWestInlabel  Integer32,
        mplsPwSPeWestOutlabel   Integer32,
        mplsPwSPeWestTunnelName OCTET STRING,
        mplsPwSPeWestCtrlWord		INTEGER,  
        mplsPwSPeWestRowStatus	RowStatus,
        mplsPwSPeWestState			INTEGER,
        mplsPwSPeWestIngressPkts		Counter64,
        mplsPwSPeWestIngressbytes		Counter64,
        mplsPwSPeWestEgressPkts			Counter64,
        mplsPwSPeWestEgressBytes		Counter64               
        }

mplsPwSPeWestPwName OBJECT-TYPE
    SYNTAX  OCTET STRING(SIZE(1..20))
    MAX-ACCESS not-accessible
    STATUS current
    DESCRIPTION
     "Identifying value for MPLS pw s-pe."
    ::= { mplsPwSPeWestEntry 1 }

mplsPwSPeWestInlabel OBJECT-TYPE
    SYNTAX  Integer32(16..1048575)
    MAX-ACCESS read-write
    STATUS current
    DESCRIPTION
     "West incoming label of the MPLS pw s-pe."
    ::= { mplsPwSPeWestEntry 2 }

mplsPwSPeWestOutlabel OBJECT-TYPE
    SYNTAX  Integer32(16..1048575)
    MAX-ACCESS read-write
    STATUS current
    DESCRIPTION
     "West outgoing label of the MPLS pw s-pe."
    ::= { mplsPwSPeWestEntry 3 }

mplsPwSPeWestTunnelName OBJECT-TYPE
    SYNTAX  OCTET STRING(SIZE(0..20))
    MAX-ACCESS read-write
    STATUS current
    DESCRIPTION
     "MPLS tunnel name for the MPLS pw s-pe."
    ::= { mplsPwSPeWestEntry 4 }

mplsPwSPeWestCtrlWord  OBJECT-TYPE
    SYNTAX INTEGER {control-word(1), no-control-word(2)}
    MAX-ACCESS read-only
    STATUS current
    DESCRIPTION
       "The state of the mpls pw spe west control-word."  
    ::= { mplsPwSPeWestEntry 5 } 

mplsPwSPeWestRowStatus OBJECT-TYPE
    SYNTAX RowStatus
    MAX-ACCESS read-create
    STATUS current
    DESCRIPTION
        "The status of this conceptual row.
         Now only realize CreateAndGo and Destroy and Active."
    ::= { mplsPwSPeWestEntry 10 }

mplsPwSPeWestState OBJECT-TYPE
    SYNTAX INTEGER {up(1), down(2)}
    MAX-ACCESS read-only
    STATUS current
    DESCRIPTION
       "The state of the mpls pw spe west. The meanings of the values are:
        up(1)   -  the state is up;
        down(2) -  the state is down;"  
    ::= { mplsPwSPeWestEntry 11 }   

mplsPwSPeWestIngressPkts         OBJECT-TYPE
    SYNTAX          Counter64
    MAX-ACCESS      read-only
    STATUS          current
    DESCRIPTION
        "Ingress packets number of pw s-pe west."
    ::= { mplsPwSPeWestEntry 20 }

mplsPwSPeWestIngressbytes         OBJECT-TYPE
    SYNTAX          Counter64
    MAX-ACCESS      read-only
    STATUS          current
    DESCRIPTION
        "Ingress bytes number of pw s-pe west."
    ::= { mplsPwSPeWestEntry 21 }

mplsPwSPeWestEgressPkts         OBJECT-TYPE
    SYNTAX          Counter64
    MAX-ACCESS      read-only
    STATUS          current
    DESCRIPTION
        "Egress packets number of pw s-pe west."
    ::= { mplsPwSPeWestEntry 22 }
    
mplsPwSPeWestEgressBytes         OBJECT-TYPE
    SYNTAX          Counter64
    MAX-ACCESS      read-only
    STATUS          current
    DESCRIPTION
        "Egress bytes number of pw s-pe west."
    ::= { mplsPwSPeWestEntry 23 } 
          
mplsVplsStaticFdbTable OBJECT-TYPE
    SYNTAX  SEQUENCE OF MplsVplsStaticFdbEntry
    MAX-ACCESS not-accessible
    STATUS   current
    DESCRIPTION
     "Vpls static fdb table."
    ::= { mpls 26 }

mplsVplsStaticFdbEntry OBJECT-TYPE
    SYNTAX  MplsVplsStaticFdbEntry
    MAX-ACCESS not-accessible
    STATUS current
    DESCRIPTION
     "VPLS static fdb entries."
    INDEX   { mplsVplsStaticFdbVplsId, mplsVplsStaticFdbMacAddr}
    ::= { mplsVplsStaticFdbTable 1 }

MplsVplsStaticFdbEntry   ::=
    SEQUENCE {
        mplsVplsStaticFdbVplsId    	Integer32,
        mplsVplsStaticFdbMacAddr 		MacAddress,
        mplsVplsStaticFdbType   		INTEGER,
        mplsVplsStaticFdbIfName 		OCTET STRING,
        mplsVplsStaticFdbPeerIp 		IpAddress,
        mplsVplsStaticFdbTPPeerName OCTET STRING,
        mplsVplsStaticFdbRowStatus	RowStatus
        }

mplsVplsStaticFdbVplsId OBJECT-TYPE
    SYNTAX  Integer32 (1..2147483647)
    MAX-ACCESS not-accessible
    STATUS current
    DESCRIPTION
     "Identifying value for VPLS."
    ::= { mplsVplsStaticFdbEntry 1 }

mplsVplsStaticFdbMacAddr OBJECT-TYPE
    SYNTAX  MacAddress
    MAX-ACCESS not-accessible
    STATUS current
    DESCRIPTION
     "Mac address of the fdb entry."
    ::= { mplsVplsStaticFdbEntry 2 }

mplsVplsStaticFdbType OBJECT-TYPE
    SYNTAX INTEGER {forward(1),discard(2)}
    MAX-ACCESS read-write
    STATUS current
    DESCRIPTION
        "Set static fdb type. When mplsVplsStaticFdbType is set to discard,
        mplsVplsStaticFdbIfName and mplsVplsStaticFdbPeerIp are invalid.
        The meanings of the values are:
        forward(1) -  Forwarding entry;
        discard(2) -  Discard entry;"
    DEFVAL { discard }
    ::= { mplsVplsStaticFdbEntry 3 }

mplsVplsStaticFdbIfName OBJECT-TYPE
    SYNTAX  OCTET STRING(SIZE(0..16))
    MAX-ACCESS read-write
    STATUS current
    DESCRIPTION
     "Out-going interface of the VPLS fdb entry."
    ::= { mplsVplsStaticFdbEntry 4 }

mplsVplsStaticFdbPeerIp OBJECT-TYPE
    SYNTAX  IpAddress
    MAX-ACCESS read-write
    STATUS current
    DESCRIPTION
     "Out-going peer IPV4 address of the VPLS fdb entry."
    ::= { mplsVplsStaticFdbEntry 5 }
    
mplsVplsStaticFdbTPPeerName OBJECT-TYPE
    SYNTAX  OCTET STRING(SIZE(1..20))
    MAX-ACCESS read-write
    STATUS current
    DESCRIPTION 
    	"Out-going tp-peer of the VPLS fdb entry."
    ::= { mplsVplsStaticFdbEntry 6 }    
    
mplsVplsStaticFdbRowStatus OBJECT-TYPE
    SYNTAX  RowStatus
    MAX-ACCESS read-create
    STATUS current
    DESCRIPTION
     "The status of this conceptual row.
     Now only realize CreateAndGo and Destroy and Active."
    ::= { mplsVplsStaticFdbEntry 10 }

mplsStaticFtnTable OBJECT-TYPE
    SYNTAX  SEQUENCE OF MplsStaticFtnEntry
    MAX-ACCESS not-accessible
    STATUS   current
    DESCRIPTION
     "MPLS static ftn table."
    ::= { mpls 27 }

mplsStaticFtnEntry OBJECT-TYPE
    SYNTAX  MplsStaticFtnEntry
    MAX-ACCESS not-accessible
    STATUS current
    DESCRIPTION
     "MPLS static ftn entries."
    INDEX   { mplsStaticFtnFecPrefix, mplsStaticFtnFecPrefixLen, mplsStaticFtnNexthop }
    ::= { mplsStaticFtnTable 1 }

MplsStaticFtnEntry   ::=
    SEQUENCE {
        mplsStaticFtnFecPrefix     IpAddress,
        mplsStaticFtnFecPrefixLen  Integer32,
        mplsStaticFtnNexthop        IpAddress,
        mplsStaticFtnOutlabel       Integer32,
        mplsStaticFtnRowStatus    RowStatus
        }

mplsStaticFtnFecPrefix OBJECT-TYPE
    SYNTAX  IpAddress
    MAX-ACCESS not-accessible
    STATUS current
    DESCRIPTION
     "FEC prefix."
    ::= { mplsStaticFtnEntry 1 }

mplsStaticFtnFecPrefixLen OBJECT-TYPE
    SYNTAX  Integer32
    MAX-ACCESS not-accessible
    STATUS current
    DESCRIPTION
     "FEC prefix length."
    ::= { mplsStaticFtnEntry 2 }

mplsStaticFtnNexthop OBJECT-TYPE
    SYNTAX  IpAddress
    MAX-ACCESS not-accessible
    STATUS current
    DESCRIPTION
     "Nexthop IPV4 address of the FEC."
    ::= { mplsStaticFtnEntry 3 }

mplsStaticFtnOutlabel OBJECT-TYPE
    SYNTAX Integer32
    MAX-ACCESS read-write
    STATUS current
    DESCRIPTION
        "Out-going label for the FEC"
    ::= { mplsStaticFtnEntry 4 }

mplsStaticFtnRowStatus OBJECT-TYPE
    SYNTAX  RowStatus
    MAX-ACCESS read-create
    STATUS current
    DESCRIPTION
     "The status of this conceptual row.
     Now only realize CreateAndGo and Destroy and Active."
    ::= { mplsStaticFtnEntry 10 }

mplsFtnDatabaseTable OBJECT-TYPE
    SYNTAX  SEQUENCE OF MplsFtnDatabaseEntry
    MAX-ACCESS not-accessible
    STATUS   current
    DESCRIPTION
     "MPLS ftn database table."
    ::= { mpls 28 }

mplsFtnDatabaseEntry OBJECT-TYPE
    SYNTAX  MplsFtnDatabaseEntry
    MAX-ACCESS not-accessible
    STATUS current
    DESCRIPTION
     "MPLS ftn database entries."
    INDEX   { mplsFtnDatabaseIndex }
    ::= { mplsFtnDatabaseTable 1 }

MplsFtnDatabaseEntry   ::=
    SEQUENCE {
        mplsFtnDatabaseIndex     Integer32,
        mplsFtnDatabaseFecPrefix     IpAddress,
        mplsFtnDatabaseFecPrefixLen  Integer32,
        mplsFtnDatabaseOutlabel       Integer32,
        mplsFtnDatabaseNexthop        IpAddress,
        mplsFtnDatabaseOutInterface  OCTET STRING,
        mplsFtnDatabaseState     INTEGER
        }

mplsFtnDatabaseIndex OBJECT-TYPE
    SYNTAX  Integer32
    MAX-ACCESS not-accessible
    STATUS current
    DESCRIPTION
     "FEC prefix."
    ::= { mplsFtnDatabaseEntry 1 }

mplsFtnDatabaseFecPrefix OBJECT-TYPE
    SYNTAX  IpAddress
    MAX-ACCESS read-only
    STATUS current
    DESCRIPTION
     "FEC prefix."
    ::= { mplsFtnDatabaseEntry 2 }

mplsFtnDatabaseFecPrefixLen OBJECT-TYPE
    SYNTAX  Integer32
    MAX-ACCESS read-only
    STATUS current
    DESCRIPTION
     "FEC prefix length."
    ::= { mplsFtnDatabaseEntry 3 }

mplsFtnDatabaseOutlabel OBJECT-TYPE
    SYNTAX Integer32
    MAX-ACCESS read-only
    STATUS current
    DESCRIPTION
        "Out-going label for the FEC"
    ::= { mplsFtnDatabaseEntry 4 }

mplsFtnDatabaseNexthop OBJECT-TYPE
    SYNTAX  IpAddress
    MAX-ACCESS read-only
    STATUS current
    DESCRIPTION
     "Nexthop IPV4 address of the FEC."
    ::= { mplsFtnDatabaseEntry 5 }

mplsFtnDatabaseOutInterface OBJECT-TYPE
    SYNTAX  OCTET STRING
    MAX-ACCESS read-only
    STATUS current
    DESCRIPTION
     "Out-going interface for the FEC."
    ::= { mplsFtnDatabaseEntry 6 }

mplsFtnDatabaseState OBJECT-TYPE
    SYNTAX INTEGER {active(1),inactive(2)}
    MAX-ACCESS read-only
    STATUS current
    DESCRIPTION
        "The state of the FTN entry.The meanings of the values are:
        active(1)   -  the entry is active;
        inactive(2) -  the entry is inactive;"
    ::= { mplsFtnDatabaseEntry 7 }

mplsStaticIlmTable OBJECT-TYPE
    SYNTAX  SEQUENCE OF MplsStaticIlmEntry
    MAX-ACCESS not-accessible
    STATUS   current
    DESCRIPTION
     "MPLS static ilm table."
    ::= { mpls 29 }

mplsStaticIlmEntry OBJECT-TYPE
    SYNTAX  MplsStaticIlmEntry
    MAX-ACCESS not-accessible
    STATUS current
    DESCRIPTION
     "MPLS static ilm entries."
    INDEX   { mplsStaticIlmInlabel }
    ::= { mplsStaticIlmTable 1 }

MplsStaticIlmEntry   ::=
    SEQUENCE {
        mplsStaticIlmInlabel        Integer32,
        mplsStaticIlmOpcode     INTEGER,
        mplsStaticIlmNexthop        IpAddress,
        mplsStaticIlmOutlabel       Integer32,
        mplsStaticIlmRowStatus    RowStatus
        }

mplsStaticIlmInlabel OBJECT-TYPE
    SYNTAX Integer32 (16..1048575)
    MAX-ACCESS not-accessible
    STATUS current
    DESCRIPTION
      "Incoming label."
    ::= { mplsStaticIlmEntry 1 }

mplsStaticIlmOpcode OBJECT-TYPE
    SYNTAX  INTEGER {swap(1), pop(2)}
    MAX-ACCESS read-write
    STATUS current
    DESCRIPTION
     "The opcode of the ilm entry.The meanings of the values are:
        swap(1) -  swap incoming label;
        pop(2)  -  pop incoming label."  
    ::= { mplsStaticIlmEntry 2 }

mplsStaticIlmNexthop OBJECT-TYPE
    SYNTAX  IpAddress
    MAX-ACCESS read-write
    STATUS current
    DESCRIPTION
     "Nexthop IPV4 address of the ILM."
    ::= { mplsStaticIlmEntry 3 }

mplsStaticIlmOutlabel OBJECT-TYPE
    SYNTAX Integer32 (0|3|16..1048575)
    MAX-ACCESS read-write
    STATUS current
    DESCRIPTION
      "Out-going label for the ILM."
    ::= { mplsStaticIlmEntry 4 }

mplsStaticIlmRowStatus OBJECT-TYPE
    SYNTAX  RowStatus
    MAX-ACCESS read-create
    STATUS current
    DESCRIPTION
     "The status of this conceptual row.
     Now only realize CreateAndGo and Destroy and Active."
    ::= { mplsStaticIlmEntry 10 }

mplsIlmDatabaseTable OBJECT-TYPE
    SYNTAX  SEQUENCE OF MplsIlmDatabaseEntry
    MAX-ACCESS not-accessible
    STATUS   current
    DESCRIPTION
     "MPLS ilm database table."
    ::= { mpls 30 }

mplsIlmDatabaseEntry OBJECT-TYPE
    SYNTAX  MplsIlmDatabaseEntry
    MAX-ACCESS not-accessible
    STATUS current
    DESCRIPTION
     "MPLS ilm database entries."
    INDEX   { mplsIlmDatabaseIndex }
    ::= { mplsIlmDatabaseTable 1 }

MplsIlmDatabaseEntry   ::=
    SEQUENCE {
        mplsIlmDatabaseIndex     Integer32,
        mplsIlmDatabaseFecPrefix     IpAddress,
        mplsIlmDatabaseFecPrefixLen  Integer32,
        mplsIlmDatabaseInlabel        Integer32,
        mplsIlmDatabaseOutlabel       Integer32,
        mplsIlmDatabaseNexthop        IpAddress,
        mplsIlmDatabaseOutInterface  OCTET STRING,
        mplsIlmDatabaseState		INTEGER,
        mplsIlmDatabaseNexthopMac     MacAddress                               
        }

mplsIlmDatabaseIndex OBJECT-TYPE
    SYNTAX Integer32
    MAX-ACCESS not-accessible
    STATUS current
    DESCRIPTION
      "Index of the ILM entry."
    ::= { mplsIlmDatabaseEntry 1 }

mplsIlmDatabaseFecPrefix OBJECT-TYPE
    SYNTAX  IpAddress
    MAX-ACCESS read-only
    STATUS current
    DESCRIPTION
     "FEC prefix."
    ::= { mplsIlmDatabaseEntry 2 }

mplsIlmDatabaseFecPrefixLen OBJECT-TYPE
    SYNTAX  Integer32
    MAX-ACCESS read-only
    STATUS current
    DESCRIPTION
     "FEC prefix length."
    ::= { mplsIlmDatabaseEntry 3 }

mplsIlmDatabaseInlabel OBJECT-TYPE
    SYNTAX Integer32
    MAX-ACCESS read-only
    STATUS current
    DESCRIPTION
      "Incoming label for the FEC."
    ::= { mplsIlmDatabaseEntry 4 }

mplsIlmDatabaseOutlabel OBJECT-TYPE
    SYNTAX Integer32
    MAX-ACCESS read-only
    STATUS current
    DESCRIPTION
      "Out-going label for the FEC."
    ::= { mplsIlmDatabaseEntry 5 }

mplsIlmDatabaseNexthop OBJECT-TYPE
    SYNTAX  IpAddress
    MAX-ACCESS read-only
    STATUS current
    DESCRIPTION
     "Nexthop IPV4 address of the FEC."
    ::= { mplsIlmDatabaseEntry 6 }

mplsIlmDatabaseOutInterface OBJECT-TYPE
    SYNTAX  OCTET STRING
    MAX-ACCESS read-only
    STATUS current
    DESCRIPTION
     "Out-going interface for the ilm entry."
    ::= { mplsIlmDatabaseEntry 7 }

mplsIlmDatabaseState OBJECT-TYPE
    SYNTAX INTEGER {active(1),inactive(2)}
    MAX-ACCESS read-only
    STATUS current
    DESCRIPTION
        "The state of the ILM entry.The meanings of the values are:
        active(1)   -  the entry is active;
        inactive(2) -  the entry is inactive;"
    ::= { mplsIlmDatabaseEntry 8 }

mplsIlmDatabaseNexthopMac OBJECT-TYPE
    SYNTAX  MacAddress
    MAX-ACCESS read-only
    STATUS current
    DESCRIPTION 
    	"Nexthop mac address of the FEC."
    ::= { mplsIlmDatabaseEntry 11 }    
    
mplsPwTpeTable OBJECT-TYPE
    SYNTAX  SEQUENCE OF   MplsPwTpeEntry
    MAX-ACCESS not-accessible
    STATUS   current
    DESCRIPTION 
    	"Table of all mpls pw-tpe instances."
    ::= { mpls 31 }
    
mplsPwTpeEntry OBJECT-TYPE
    SYNTAX  MplsPwTpeEntry
    MAX-ACCESS not-accessible
    STATUS current
    DESCRIPTION 
    	"Entry of mplsPwTpeTable."
    INDEX   { mplsPwTpeName}
    ::= { mplsPwTpeTable 1 }

MplsPwTpeEntry   ::=
    SEQUENCE {
        mplsPwTpeName 		  					OCTET STRING,
        mplsPwTpeRowStatus  					RowStatus,
        mplsPwTpeDescription	        OCTET STRING,        
        mplsPwTpeOAMMegLevel          Integer32,        
        mplsPwTpeOAMMegId							OCTET STRING,
        mplsPwTpeOAMMegIdIcc          Integer32,
        mplsPwTpeOAMMepId							Integer32,
        mplsPwTpeOAMMepInterval				INTEGER,
        mplsPwTpeOAMMepExp						Integer32,
        mplsPwTpeOAMRMepId						Integer32,        
        mplsPwTpeOAMCCState						INTEGER,                
        mplsPwTpeOAMEventCacheSize		Integer32,
        mplsPwTpeOAM1dmCacheSize			Integer32,          
        mplsPwTpeOAMAisClientSupress	INTEGER,
        mplsPwTpeOAMLck								INTEGER,
        mplsPwTpeOAMEvtLOC   INTEGER,
        mplsPwTpeOAMEvtUMP   INTEGER,
        mplsPwTpeOAMEvtUIN   INTEGER,
        mplsPwTpeOAMEvtUMG   INTEGER,
        mplsPwTpeOAMEvtULV   INTEGER,
        mplsPwTpeOAMEvtW1ST  INTEGER,
        mplsPwTpeOAMEvtRDIR  INTEGER,
        mplsPwTpeOAMEvtRDIT  INTEGER,
        mplsPwTpeOAMEvtAISR  INTEGER,
        mplsPwTpeOAMEvtAIST  INTEGER,
        mplsPwTpeOAMEvtAISD  INTEGER,
        mplsPwTpeOAMEvtLCKR  INTEGER,
        mplsPwTpeOAMEvtLCKT  INTEGER,
        mplsPwTpeOAMEvtLCKD  INTEGER,
        mplsPwTpeOAMEvtCRC   INTEGER,        
        mplsPwTpeOAMState    INTEGER,
        mplsPwTpeIngressPkts             Counter64,
        mplsPwTpeIngressBytes            Counter64,
        mplsPwTpeEgressPkts              Counter64,
        mplsPwTpeEgressBytes             Counter64,
        mplsPwTpeStats      					   INTEGER,
        mplsPwTpeBandwidth   					   Integer32,        
        mplsPwTpeOAMLmDualExp            Integer32,
        mplsPwTpeOAMLmDualStatInterval   Integer32,
        mplsPwTpeOAMLmDualCacheSize      Integer32,
        mplsPwTpeOAMLmSingleExp          Integer32,
        mplsPwTpeOAMLmSingleInterval     INTEGER,
        mplsPwTpeOAMLmSingleCacheSize    Integer32,                
        mplsPwTpeOAMLmEnableState        INTEGER,
        mplsPwTpeOAMLmLocalLossThreshold     Integer32, 
        mplsPwTpeOAMLmRemoteLossThreshold    Integer32,
        mplsPwTpeOAMLmSingleRxCount          Integer32,
        mplsPwTpeOAMLmSingleTxCount          Integer32,	
        mplsPwTpeOAMLmSingleSuccessRate      Integer32,	
        mplsPwTpeOAMLmSingleStartTime        OCTET STRING,
        mplsPwTpeOAMLmSingleEndTime          OCTET STRING		
        }

mplsPwTpeName OBJECT-TYPE
    SYNTAX  OCTET STRING(SIZE(1..20))
    MAX-ACCESS not-accessible
    STATUS current
    DESCRIPTION 
    	"Identifying value for MPLS Lsp-pe."
    ::= { mplsPwTpeEntry 1 }

mplsPwTpeRowStatus OBJECT-TYPE
    SYNTAX RowStatus
    MAX-ACCESS read-create
    STATUS current
    DESCRIPTION
        "The status of this conceptual row.
         Now only realize CreateAndGo and Destroy and Active."
    ::= { mplsPwTpeEntry 10 }     

mplsPwTpeDescription OBJECT-TYPE
    SYNTAX  OCTET STRING (SIZE(1..20))
    MAX-ACCESS read-write
    STATUS current
    DESCRIPTION 
    	"Characters describing of this T-PE type PW.
    	 Only less than 20 octets is accepted."
    ::= { mplsPwTpeEntry 11 }

mplsPwTpeOAMMegLevel OBJECT-TYPE
    SYNTAX Integer32 (0..7)
    MAX-ACCESS read-write
    STATUS current
    DESCRIPTION
      "OAM level."
    DEFVAL { 7 }
    ::= { mplsPwTpeEntry 20 }	
        
mplsPwTpeOAMMegId OBJECT-TYPE
    SYNTAX OCTET STRING (SIZE (1..12))
    MAX-ACCESS read-write
    STATUS current
    DESCRIPTION
      "MEG ID of the lsp-pe."  
    ::= { mplsPwTpeEntry 21 }	   

mplsPwTpeOAMMegIdIcc OBJECT-TYPE
    SYNTAX Integer32 (1..6)
    MAX-ACCESS read-write
    STATUS current
    DESCRIPTION
      "ICC length of MEG ID."
    DEFVAL { 6 }
    ::= { mplsPwTpeEntry 22 }	

mplsPwTpeOAMMepId OBJECT-TYPE
    SYNTAX Integer32 (1..8191)
    MAX-ACCESS read-write
    STATUS current
    DESCRIPTION
      "MEP ID."  
    ::= { mplsPwTpeEntry 23 }	    
    
mplsPwTpeOAMMepInterval OBJECT-TYPE
    SYNTAX INTEGER 
    {
        three-point-three-ms(1), 
        ten-ms(2),
        one-hundred-ms(3),
        one-sec(4),
        ten-sec(5),
        one-min(6),
        ten-min(7)
    }
    MAX-ACCESS read-write
    STATUS current
    DESCRIPTION
      "MEP Interval."  
    ::= { mplsPwTpeEntry 24 }

mplsPwTpeOAMMepExp OBJECT-TYPE
    SYNTAX Integer32 (0..7)
    MAX-ACCESS read-write
    STATUS current
    DESCRIPTION
      "EXP value, default is 7."
    DEFVAL { 7 }  
    ::= { mplsPwTpeEntry 25 }	 

mplsPwTpeOAMRMepId OBJECT-TYPE
    SYNTAX Integer32 (1..8191)
    MAX-ACCESS read-write
    STATUS current
    DESCRIPTION
      "Remote MEP ID."  
    ::= { mplsPwTpeEntry 26 }	      

mplsPwTpeOAMCCState OBJECT-TYPE
    SYNTAX INTEGER {enable(1), disable(2)}
    MAX-ACCESS read-write
    STATUS current
    DESCRIPTION
      "CC state."
    DEFVAL { disable }  
    ::= { mplsPwTpeEntry 27 }	      
    
mplsPwTpeOAMEventCacheSize OBJECT-TYPE
    SYNTAX Integer32 (8..256)
    MAX-ACCESS read-write
    STATUS current
    DESCRIPTION
      "Event entry cache size."  
    DEFVAL { 8 }        
    ::= { mplsPwTpeEntry 28 }	          
         
mplsPwTpeOAM1dmCacheSize OBJECT-TYPE
    SYNTAX Integer32 (8..256)
    MAX-ACCESS read-write
    STATUS current
    DESCRIPTION
      "1dm entry cache size."  
    DEFVAL { 8 }        
    ::= { mplsPwTpeEntry 29 }	      
    
mplsPwTpeOAMAisClientSupress OBJECT-TYPE
    SYNTAX INTEGER {enable(1), disable(2)}
    MAX-ACCESS read-write
    STATUS current
    DESCRIPTION
      "AIS client supress state."    
    DEFVAL { disable }  
    ::= { mplsPwTpeEntry 30 }	    

mplsPwTpeOAMLck OBJECT-TYPE
    SYNTAX INTEGER {enable(1), disable(2)}
    MAX-ACCESS read-write
    STATUS current
    DESCRIPTION
      "Enable pw-tpe lock."    
    DEFVAL { disable }  
    ::= { mplsPwTpeEntry 31 }	    

mplsPwTpeOAMEvtLOC OBJECT-TYPE
    SYNTAX INTEGER {enable(1), disable(2)}
    MAX-ACCESS read-only
    STATUS current
    DESCRIPTION
      "Loc state."    
    DEFVAL { disable }  
    ::= { mplsPwTpeEntry 32 }

mplsPwTpeOAMEvtUMP OBJECT-TYPE
    SYNTAX INTEGER {enable(1), disable(2)}
    MAX-ACCESS read-only
    STATUS current
    DESCRIPTION
      "Unexp RMEPID state."    
    DEFVAL { disable }  
    ::= { mplsPwTpeEntry 33 }

mplsPwTpeOAMEvtUIN OBJECT-TYPE
    SYNTAX INTEGER {enable(1), disable(2)}
    MAX-ACCESS read-only
    STATUS current
    DESCRIPTION
      "Unexp interval state."    
    DEFVAL { disable }  
    ::= { mplsPwTpeEntry 34 }

mplsPwTpeOAMEvtUMG OBJECT-TYPE
    SYNTAX INTEGER {enable(1), disable(2)}
    MAX-ACCESS read-only
    STATUS current
    DESCRIPTION
      "Unexp MEGID state."    
    DEFVAL { disable }  
    ::= { mplsPwTpeEntry 35 }

mplsPwTpeOAMEvtULV OBJECT-TYPE
    SYNTAX INTEGER {enable(1), disable(2)}
    MAX-ACCESS read-only
    STATUS current
    DESCRIPTION
      "Unexp Level state."    
    DEFVAL { disable } 
    ::= { mplsPwTpeEntry 36 }

mplsPwTpeOAMEvtW1ST OBJECT-TYPE
    SYNTAX INTEGER {enable(1), disable(2)}
    MAX-ACCESS read-only
    STATUS current
    DESCRIPTION
      "Wait 1st CCM state."    
    DEFVAL { disable } 
    ::= { mplsPwTpeEntry 37 }

mplsPwTpeOAMEvtRDIR OBJECT-TYPE
    SYNTAX INTEGER {enable(1), disable(2)}
    MAX-ACCESS read-only
    STATUS current
    DESCRIPTION
      "RDI RX state."    
    DEFVAL { disable } 
    ::= { mplsPwTpeEntry 38 }

mplsPwTpeOAMEvtRDIT OBJECT-TYPE
    SYNTAX INTEGER {enable(1), disable(2)}
    MAX-ACCESS read-only
    STATUS current
    DESCRIPTION
      "RDI TX state."    
    DEFVAL { disable } 
    ::= { mplsPwTpeEntry 39 }

mplsPwTpeOAMEvtAISR OBJECT-TYPE
    SYNTAX INTEGER {enable(1), disable(2)}
    MAX-ACCESS read-only
    STATUS current
    DESCRIPTION
      "AIS RX state."    
    DEFVAL { disable } 
    ::= { mplsPwTpeEntry 40 }

mplsPwTpeOAMEvtAIST OBJECT-TYPE
    SYNTAX INTEGER {enable(1), disable(2)}
    MAX-ACCESS read-only
    STATUS current
    DESCRIPTION
      "AIS RX state."    
    DEFVAL { disable } 
    ::= { mplsPwTpeEntry 41 }

mplsPwTpeOAMEvtAISD OBJECT-TYPE
    SYNTAX INTEGER {enable(1), disable(2)}
    MAX-ACCESS read-only
    STATUS current
    DESCRIPTION
      "AIS RX state."    
    DEFVAL { disable } 
    ::= { mplsPwTpeEntry 42 }

mplsPwTpeOAMEvtLCKR OBJECT-TYPE
    SYNTAX INTEGER {enable(1), disable(2)}
    MAX-ACCESS read-only
    STATUS current
    DESCRIPTION
      "LCK RX state."    
    DEFVAL { disable } 
    ::= { mplsPwTpeEntry 43 }

mplsPwTpeOAMEvtLCKT OBJECT-TYPE
    SYNTAX INTEGER {enable(1), disable(2)}
    MAX-ACCESS read-only
    STATUS current
    DESCRIPTION
      "LCK RX state."    
    DEFVAL { disable } 
    ::= { mplsPwTpeEntry 44 }

mplsPwTpeOAMEvtLCKD OBJECT-TYPE
    SYNTAX INTEGER {enable(1), disable(2)}
    MAX-ACCESS read-only
    STATUS current
    DESCRIPTION
      "LCK RX state."    
    DEFVAL { disable } 
    ::= { mplsPwTpeEntry 45 }   

mplsPwTpeOAMEvtCRC OBJECT-TYPE
    SYNTAX INTEGER {enable(1), disable(2)}
    MAX-ACCESS read-only
    STATUS current
    DESCRIPTION
      "CRC RX state."    
    DEFVAL { disable } 
    ::= { mplsPwTpeEntry 46 }  
    
mplsPwTpeOAMState OBJECT-TYPE
    SYNTAX INTEGER {init(0), fail(1), ok(2)}
    MAX-ACCESS read-only
    STATUS current
    DESCRIPTION
      "oam-y1731 Rmep state." 
    ::= { mplsPwTpeEntry 50 } 
    
mplsPwTpeIngressPkts             OBJECT-TYPE
    SYNTAX          Counter64
    MAX-ACCESS      read-only
    STATUS          current
    DESCRIPTION
        "Ingress packtes number of mpls pw-tpe."
    ::= { mplsPwTpeEntry 51 }
    
mplsPwTpeIngressBytes             OBJECT-TYPE
    SYNTAX          Counter64
    MAX-ACCESS      read-only
    STATUS          current
    DESCRIPTION
        "Ingress bytes number of mpls pw-tpe."
    ::= { mplsPwTpeEntry 52 }

mplsPwTpeEgressPkts                 OBJECT-TYPE
    SYNTAX          Counter64
    MAX-ACCESS      read-only
    STATUS          current
    DESCRIPTION
        "Egress packtes number of mpls pw-tpe."
    ::= { mplsPwTpeEntry 53 }
    
mplsPwTpeEgressBytes             OBJECT-TYPE
    SYNTAX          Counter64
    MAX-ACCESS      read-only
    STATUS          current
    DESCRIPTION
        "Egress bytes number of mpls pw-tpe."
    ::= { mplsPwTpeEntry 54 }    

mplsPwTpeStats OBJECT-TYPE
    SYNTAX INTEGER {enable(1), disable(2)}
    MAX-ACCESS read-write
    STATUS current
    DESCRIPTION
      "Pw-tpe statistics."    
    DEFVAL { disable }  
    ::= { mplsPwTpeEntry 55 }	 

mplsPwTpeBandwidth OBJECT-TYPE
    SYNTAX Integer32 (-1..1000000)
    MAX-ACCESS read-write
    STATUS current
    DESCRIPTION
      "pw-tpe bandwidth in kbps. -1 means no limitation"
    ::= { mplsPwTpeEntry 56 }
       
mplsPwTpeOAMLmDualExp OBJECT-TYPE
    SYNTAX Integer32 (0..9)
    MAX-ACCESS read-write
    STATUS current
    DESCRIPTION
      "Configure dual-ended loss measurment packets with specified exp will be counted.
      <0-7> specified exp; 8 means Packets with different exp will be counted separately;
      9 means All packets with different exp will be counted together."
    ::= { mplsPwTpeEntry 61 }
    
mplsPwTpeOAMLmDualStatInterval OBJECT-TYPE
    SYNTAX Integer32 (1..10)
    MAX-ACCESS read-write
    STATUS current
    DESCRIPTION
      "Configure dual-ended loss measurment interval value."
    DEFVAL { 1 } 
    ::= { mplsPwTpeEntry 62 }

mplsPwTpeOAMLmDualCacheSize    OBJECT-TYPE
    SYNTAX Integer32 (1..512)
    MAX-ACCESS read-write
    STATUS current
    DESCRIPTION
      "Configure dual-ended loss measurment cache size."
    DEFVAL { 128 } 
    ::= { mplsPwTpeEntry 63 }

mplsPwTpeOAMLmSingleExp OBJECT-TYPE
    SYNTAX Integer32 (0..9)
    MAX-ACCESS read-write
    STATUS current
    DESCRIPTION
      "Configure single-ended loss measurment packets with specified exp will be counted.
      <0-7> specified exp; 8 means Packets with different exp will be counted separately;
      9 means All packets with different exp will be counted together."
    ::= { mplsPwTpeEntry 66 }

mplsPwTpeOAMLmSingleInterval OBJECT-TYPE
    SYNTAX INTEGER         
    {    
        one-hundred-ms(1),
        one-sec(2),
        ten-sec(3)
    }
    MAX-ACCESS read-write
    STATUS current
    DESCRIPTION
      "Config Interval."
    ::= { mplsPwTpeEntry 67 }	

mplsPwTpeOAMLmSingleCacheSize    OBJECT-TYPE
    SYNTAX Integer32 (1..512)
    MAX-ACCESS read-write
    STATUS current
    DESCRIPTION
      "Configure single-ended loss measurment cache size."
    DEFVAL { 128 } 
    ::= { mplsPwTpeEntry 68 }
        
mplsPwTpeOAMLmEnableState OBJECT-TYPE
    SYNTAX INTEGER {enable-dual(1), enable-single(2), disable(3)}
    MAX-ACCESS read-write
    STATUS current
    DESCRIPTION
      "Enable or disable oam-y1731 loss measurment."    
    DEFVAL { disable } 
    ::= { mplsPwTpeEntry 70 }     

mplsPwTpeOAMLmLocalLossThreshold    OBJECT-TYPE
    SYNTAX Integer32 (0..100)
    MAX-ACCESS read-write
    STATUS current
    DESCRIPTION
      "Local packet loss percentage, 0 means threshold not enabled."
    DEFVAL { 0 } 
    ::= { mplsPwTpeEntry 71 }    

mplsPwTpeOAMLmRemoteLossThreshold    OBJECT-TYPE
    SYNTAX Integer32 (0..100)
    MAX-ACCESS read-write
    STATUS current
    DESCRIPTION
      "Local packet loss percentage, 0 means threshold not enabled."
    DEFVAL { 0 } 
    ::= { mplsPwTpeEntry 72 }
	
mplsPwTpeOAMLmSingleRxCount    OBJECT-TYPE
    SYNTAX Integer32 (0..255)
    MAX-ACCESS read-only
    STATUS current
    DESCRIPTION
      "LMM single-ended packet Rx count."
    ::= { mplsPwTpeEntry 73 }
	
mplsPwTpeOAMLmSingleTxCount    OBJECT-TYPE
   SYNTAX Integer32 (0..255)
    MAX-ACCESS read-only
    STATUS current
    DESCRIPTION
      "LMM single-ended packet Tx count."
    ::= { mplsPwTpeEntry 74 }
	
mplsPwTpeOAMLmSingleSuccessRate    OBJECT-TYPE
    SYNTAX Integer32 (0..100)
    MAX-ACCESS read-only
    STATUS current
    DESCRIPTION
      "LMM single-ended success rate."
    ::= { mplsPwTpeEntry 75 }
	
mplsPwTpeOAMLmSingleStartTime OBJECT-TYPE
    SYNTAX  OCTET STRING(SIZE(1..50))
    MAX-ACCESS read-only
    STATUS current
    DESCRIPTION
    	"LMM proactive single-ended start time."
    ::= { mplsPwTpeEntry 76 }
	
mplsPwTpeOAMLmSingleEndTime OBJECT-TYPE
    SYNTAX  OCTET STRING(SIZE(1..50))
    MAX-ACCESS read-only
    STATUS current
    DESCRIPTION
    	"LMM proactive single-ended end time."
    ::= { mplsPwTpeEntry 77 }
  
mplsPwTpeConfTable OBJECT-TYPE
    SYNTAX  SEQUENCE OF   MplsPwTpeConfEntry
    MAX-ACCESS not-accessible
    STATUS   current
    DESCRIPTION 
    	"Table of configuration of all mpls pw-tpe instances."
    ::= { mpls 32 }
    
mplsPwTpeConfEntry OBJECT-TYPE
    SYNTAX  MplsPwTpeConfEntry
    MAX-ACCESS not-accessible
    STATUS current
    DESCRIPTION 
    	"Entry of mplsPwTpeConfTable."
    INDEX   { mplsPwTpeName}
    ::= { mplsPwTpeConfTable 1 }

MplsPwTpeConfEntry   ::=
    SEQUENCE {
        mplsPwTpeConfInlabel		  Integer32,
        mplsPwTpeConfOutlabel	  	Integer32,
        mplsPwTpeConfPwMode	  		INTEGER,
        mplsPwTpeConfTunnel				OCTET STRING, 
        mplsPwTpeConfRowStatus		RowStatus                
        }

mplsPwTpeConfInlabel OBJECT-TYPE
    SYNTAX  Integer32(16..1048575)
    MAX-ACCESS read-create
    STATUS current
    DESCRIPTION 
    	"Incoming label of the t-pe."
    ::= { mplsPwTpeConfEntry 1 }

mplsPwTpeConfOutlabel OBJECT-TYPE
    SYNTAX  Integer32(16..1048575)
    MAX-ACCESS read-create
    STATUS current
    DESCRIPTION 
    	"Outgoing label of the t-pe."
    ::= { mplsPwTpeConfEntry 2 }

mplsPwTpeConfPwMode OBJECT-TYPE
    SYNTAX  INTEGER { raw(1), tagged(2) }
    MAX-ACCESS read-create
    STATUS current
    DESCRIPTION 
    	"Pw mode of the t-pe."
    DEFVAL { raw }
    ::= { mplsPwTpeConfEntry 3 }

mplsPwTpeConfTunnel OBJECT-TYPE
    SYNTAX  OCTET STRING(SIZE(1..20)) 
    MAX-ACCESS read-create
    STATUS current
    DESCRIPTION 
    	"Tunnel name."
    ::= { mplsPwTpeConfEntry 4 }
    
mplsPwTpeConfRowStatus OBJECT-TYPE
    SYNTAX RowStatus
    MAX-ACCESS read-create
    STATUS current
    DESCRIPTION
        "The status of this conceptual row.
         Now only realize CreateAndGo and Destroy and Active."
    ::= { mplsPwTpeConfEntry 10 }
    
mplsTPVpwsTable OBJECT-TYPE
    SYNTAX  SEQUENCE OF MplsTPVpwsEntry
    MAX-ACCESS not-accessible
    STATUS   current
    DESCRIPTION 
    	"Specify an MPLS Layer-2 Virtual Circuit."
    ::= { mpls 33 }

mplsTPVpwsEntry OBJECT-TYPE
    SYNTAX  MplsTPVpwsEntry
    MAX-ACCESS not-accessible
    STATUS current
    DESCRIPTION 
    	"Entry of mplsTPVpwsTable."
    INDEX   { mplsTPVpwsVcId}
    ::= { mplsTPVpwsTable 1 }

MplsTPVpwsEntry   ::=
    SEQUENCE {
        mplsTPVpwsVcId         				Integer32,
        mplsTPVpwsVcName 		    			OCTET STRING,
        mplsTPVpwsApsType   	  			INTEGER,
		mplsTPVpwsVlanOperation   	  			INTEGER,
        mplsTPVpwsRowStatus		  			RowStatus,
        mplsTPVpwsPrimaryPw     			OCTET STRING,
        mplsTPVpwsSecondaryPw    			OCTET STRING,
        mplsTPVpwsSelectedPw    			OCTET STRING,                 
        mplsTPVpwsDescription	        OCTET STRING,
        mplsTPAcVpwsIngressPkts       Counter64,
        mplsTPAcVpwsIngressbytes      Counter64,
        mplsTPAcVpwsEgressPkts        Counter64,
        mplsTPAcVpwsEgressBytes       Counter64,
        mplsTPVpwsG8131Mode							INTEGER,
        mplsTPVpwsG8131WTRTimer					Integer32,
        mplsTPVpwsG8131HoldOffTimer			Integer32,
        mplsTPVpwsG8131Action						INTEGER,
        mplsTPVpwsG8131WorkingPw				OCTET STRING,
        mplsTPVpwsG8131ProtectionPw		OCTET STRING,
        mplsTPVpwsG8131ActivePath				INTEGER,
        mplsTPVpwsG8131WTRTimeLeft			Integer32,
        mplsTPVpwsG8131HoldOffTimeLeft	Integer32,
        mplsTPVpwsG8131DFOPState				INTEGER,
        mplsTPVpwsG8131CurrentState			INTEGER,
        mplsTPVpwsG8131LastState				INTEGER,
        mplsTPVpwsG8131CurrentEvent			INTEGER,
        mplsTPVpwsG8131FarEndLastEvent	INTEGER,
        mplsTPVpwsG8131RequestSignal		INTEGER,
        mplsTPVpwsOAMCsfInterval				Integer32,    
        mplsTPVpwsOAMCSFRxDown               INTEGER, 
        mplsTPVpwsOAMCSFRxRelay              INTEGER, 
        mplsTPVpwsOAMCSFRxRelayMdName           OCTET STRING,
        mplsTPVpwsOAMCSFRxRelayMaVid           Integer32,
        mplsTPVpwsOAMCSFRxRelayMepId           Integer32 
        }

mplsTPVpwsVcId OBJECT-TYPE
    SYNTAX  Integer32(1..424967295)
    MAX-ACCESS not-accessible
    STATUS current
    DESCRIPTION 
    	"Identifying value for MPLS Layer-2 Virtual Circuit."
    ::= { mplsTPVpwsEntry 1 }

mplsTPVpwsVcName OBJECT-TYPE
    SYNTAX  OCTET STRING(SIZE(1..20))
    MAX-ACCESS read-create
    STATUS current
    DESCRIPTION 
    	"Identifying string for mpls-tp vpws.
    	Only 20 octets is accepted.."
    ::= { mplsTPVpwsEntry 2 }

mplsTPVpwsApsType OBJECT-TYPE
    SYNTAX  INTEGER { aps(1), non-aps(2) }
    MAX-ACCESS read-create
    STATUS current
    DESCRIPTION 
       "Set aps type for mpls-tp vpws."  
    DEFVAL { 2 }
    ::= { mplsTPVpwsEntry 3 }   
	
mplsTPVpwsVlanOperation OBJECT-TYPE
    SYNTAX  INTEGER { ac-vlan-operation(1), no-ac-vlan-operation(2) }
    MAX-ACCESS read-create
    STATUS current
    DESCRIPTION 
       "Set enable ac vlan operation for mpls-tp vpws."  
    DEFVAL { 2 }
    ::= { mplsTPVpwsEntry 4 }   
    
mplsTPVpwsRowStatus OBJECT-TYPE
    SYNTAX RowStatus
    MAX-ACCESS read-create
    STATUS current
    DESCRIPTION
        "The status of this conceptual row.
         Now only realize CreateAndGo and Destroy and Active."
    ::= { mplsTPVpwsEntry 10 }
    
mplsTPVpwsPrimaryPw OBJECT-TYPE
    SYNTAX  OCTET STRING(SIZE(0..20))
    MAX-ACCESS read-write
    STATUS current
    DESCRIPTION 
    	"Primary pw tpe name of the mpls-tp vpws."
    ::= { mplsTPVpwsEntry 11 }
    
mplsTPVpwsSecondaryPw OBJECT-TYPE
    SYNTAX  OCTET STRING(SIZE(0..20))
    MAX-ACCESS read-write
    STATUS current
    DESCRIPTION 
    	"Secondary pw tpe name of the mpls-tp vpws.
    	 Can not set secondary pw for non-aps type."
    ::= { mplsTPVpwsEntry 12 }

mplsTPVpwsSelectedPw OBJECT-TYPE
    SYNTAX  OCTET STRING(SIZE(0..20))
    MAX-ACCESS read-write
    STATUS current
    DESCRIPTION 
    	"Secondary pw tpe name of the mpls-tp vpws.
    	 Can not set secondary pw for non-aps type."
    ::= { mplsTPVpwsEntry 13 }

-- mplsTPVpwsIngressPkts         OBJECT-TYPE
--     SYNTAX          Counter64
--     MAX-ACCESS      read-only
--     STATUS          current
--     DESCRIPTION
--         "Ingress packets number of mpls vpws."
--     ::= { mplsTPVpwsEntry 14 }
-- 
-- mplsTPVpwsIngressbytes         OBJECT-TYPE
--     SYNTAX          Counter64
--     MAX-ACCESS      read-only
--     STATUS          current
--     DESCRIPTION
--         "Ingress bytes number of mpls vpws."
--     ::= { mplsTPVpwsEntry 15 }
-- 
-- mplsTPVpwsEgressPkts         OBJECT-TYPE
--     SYNTAX          Counter64
--     MAX-ACCESS      read-only
--     STATUS          current
--     DESCRIPTION
--         "Egress packets number of mpls vpws."
--     ::= { mplsTPVpwsEntry 16 }
--     
-- mplsTPVpwsEgressBytes         OBJECT-TYPE
--     SYNTAX          Counter64
--     MAX-ACCESS      read-only
--     STATUS          current
--     DESCRIPTION
--         "Egress bytes number of mpls vpws."
--     ::= { mplsTPVpwsEntry 17 }    

mplsTPVpwsDescription OBJECT-TYPE
    SYNTAX  OCTET STRING (SIZE(1..20))
    MAX-ACCESS read-write
    STATUS current
    DESCRIPTION 
    	"Characters describing of this instance of MPLS based VPWS.
    	 Only less than 20 octets is accepted."
    ::= { mplsTPVpwsEntry 18 } 

-- mplsTPVpwsStats OBJECT-TYPE
--     SYNTAX  INTEGER {enable(1),disable(2)}
--     MAX-ACCESS read-write
--     STATUS current
--     DESCRIPTION 
--        "Set statistics for mpls-tp vpws. The meanings of the values are:
--         enable(1)  -  enable statistics;
--         disable(2) -  disable statistics;"  
--     DEFVAL { 2 }
--     ::= { mplsTPVpwsEntry 19 }  

mplsTPAcVpwsIngressPkts         OBJECT-TYPE
    SYNTAX          Counter64
    MAX-ACCESS      read-only
    STATUS          current
    DESCRIPTION
        "Ingress packets number of mpls ac vpws."
    ::= { mplsTPVpwsEntry 21 }

mplsTPAcVpwsIngressbytes         OBJECT-TYPE
    SYNTAX          Counter64
    MAX-ACCESS      read-only
    STATUS          current
    DESCRIPTION
        "Ingress bytes number of mpls ac vpws."
    ::= { mplsTPVpwsEntry 22 }

mplsTPAcVpwsEgressPkts         OBJECT-TYPE
    SYNTAX          Counter64
    MAX-ACCESS      read-only
    STATUS          current
    DESCRIPTION
        "Egress packets number of mpls ac vpws."
    ::= { mplsTPVpwsEntry 23 }
    
mplsTPAcVpwsEgressBytes         OBJECT-TYPE
    SYNTAX          Counter64
    MAX-ACCESS      read-only
    STATUS          current
    DESCRIPTION
        "Egress bytes number of mpls ac vpws."
    ::= { mplsTPVpwsEntry 24 } 
                    
mplsTPVpwsG8131Mode OBJECT-TYPE
    SYNTAX  INTEGER { revertive(1), non-revertive(2) }
    MAX-ACCESS read-only
    STATUS current
    DESCRIPTION
    	"G8131 mode for the mpls tp vpws."
    ::= { mplsTPVpwsEntry 30 }

mplsTPVpwsG8131WTRTimer OBJECT-TYPE
    SYNTAX  Integer32(0..12)
    MAX-ACCESS read-write
    STATUS current
    DESCRIPTION
    	"G8131 wait-to-restore timer value for the mpls tp vpws, in minutes."
    DEFVAL {5}
    ::= { mplsTPVpwsEntry 31 }

mplsTPVpwsG8131HoldOffTimer OBJECT-TYPE
    SYNTAX  Integer32(0..100)
    MAX-ACCESS read-write
    STATUS current
    DESCRIPTION
    	"G8131 hold-off timer value for the mpls tp vpws, steps of 100ms."
    DEFVAL {0}
    ::= { mplsTPVpwsEntry 32 }

mplsTPVpwsG8131Action OBJECT-TYPE
    SYNTAX  INTEGER { force-switch(1), manual-swtich-to-working(2),
                      manual-switch-to-protection(3), lockout(4), 
                      exercise(5), clear(6) }
    MAX-ACCESS read-write
    STATUS current
    DESCRIPTION
    	"G8131 actions for the mpls tp vpws."
    ::= { mplsTPVpwsEntry 33 }

mplsTPVpwsG8131WorkingPw OBJECT-TYPE
    SYNTAX  OCTET STRING(SIZE(0..20))
    MAX-ACCESS read-only
    STATUS current
    DESCRIPTION
    	"G8131 working pw for the mpls tp vpws."
    ::= { mplsTPVpwsEntry 40 }

mplsTPVpwsG8131ProtectionPw OBJECT-TYPE
    SYNTAX  OCTET STRING(SIZE(0..20))
    MAX-ACCESS read-only
    STATUS current
    DESCRIPTION
    	"G8131 protection pw for the mpls tp vpws."
    ::= { mplsTPVpwsEntry 41 }
    
mplsTPVpwsG8131ActivePath OBJECT-TYPE
    SYNTAX  INTEGER { none(0), working-lsp(1), protection-lsp(2) }
    MAX-ACCESS read-only
    STATUS current
    DESCRIPTION
    	"G8131 active path for the mpls tp vpws."
    ::= { mplsTPVpwsEntry 42 }    
    
mplsTPVpwsG8131WTRTimeLeft OBJECT-TYPE
    SYNTAX  Integer32
    MAX-ACCESS read-only
    STATUS current
    DESCRIPTION
    	"Left time of G8131 wait-to-restore timer of the mpls tp vpws."
    ::= { mplsTPVpwsEntry 43 }   
    
mplsTPVpwsG8131HoldOffTimeLeft OBJECT-TYPE
    SYNTAX  Integer32
    MAX-ACCESS read-only
    STATUS current
    DESCRIPTION
    	"Left time of G8131 hold-off timer of the mpls tp vpws."
    ::= { mplsTPVpwsEntry 44 }           
    
mplsTPVpwsG8131DFOPState OBJECT-TYPE
    SYNTAX  INTEGER 
    {
        not-in-defect-mode(1),
        b-bit-mismatch-defect(2),
        r-bit-mismatch-defect(3),
        invalid-request-state(4),
        aps-recv-on-working-entity(5),
        aps-pdu-not-recv-after-state-change(6),
        a-bit-mismatch-defect(7),
        d-bit-mismatch-defect(8),
        t-bit-mismatch-defect(9)         
    }
    MAX-ACCESS read-only
    STATUS current
    DESCRIPTION
    	"G8131 DFOP state of the mpls tp vpws."
    ::= { mplsTPVpwsEntry 45 }  

mplsTPVpwsG8131CurrentState OBJECT-TYPE
    SYNTAX  INTEGER 
    {
        no-request-working-active(0),
        no-request-protection-avtive(1),
        lockout-of-protection(2),
        forced-switch(3),
        signal-fail-on-working(4),
        signal-fail-on-protection(5),
        signal-degrade-on-working(6),
        signal-degrade-on-protection(7),
        manual-switch-to-protection(8),
        manual-switch-to-working(9),
        wait-to-restore(10),
        do-not-revert(11),
        exercise-on-working(12),
        exercise-on-protection(13),
        reverse-request-on-working(14),
        reverse-request-on-protection(15),
        none(16)
    }
    MAX-ACCESS read-only
    STATUS current
    DESCRIPTION
    	"G8131 current state of the mpls tp vpws."
    ::= { mplsTPVpwsEntry 46 }  
    
mplsTPVpwsG8131LastState OBJECT-TYPE
    SYNTAX  INTEGER 
    {
        no-request-working-active(0),
        no-request-protection-avtive(1),
        lockout-of-protection(2),
        forced-switch(3),
        signal-fail-on-working(4),
        signal-fail-on-protection(5),
        signal-degrade-on-working(6),
        signal-degrade-on-protection(7),
        manual-switch-to-protection(8),
        manual-switch-to-working(9),
        wait-to-restore(10),
        do-not-revert(11),
        exercise-on-working(12),
        exercise-on-protection(13),
        reverse-request-on-working(14),
        reverse-request-on-protection(15),
        none(16)   
    }
    MAX-ACCESS read-only
    STATUS current
    DESCRIPTION
    	"G8131 last state of the mpls tp vpws."
    ::= { mplsTPVpwsEntry 47 }  
    
mplsTPVpwsG8131CurrentEvent OBJECT-TYPE
    SYNTAX  INTEGER 
    {
        local-lockout(0),
        local-force-switch(1),
        local-signal-fail-on-working(2),
        local-working-recover-from-signal-fail(3),
        local-signal-fail-on-protection(4),
        local-protection-recover-from-signal-fail(5),
        local-signal-degrade-on-working(6),
        local-working-recover-from-signal-degrade(7),
        local-signal-degrade-on-protection(8),
        local-protection-recover-from-signal-degrade(9),
        local-manual-switch-to-protection(10),
        local-manual-switch-to-working(11),
        local-clear(12),
        local-exercise(13),
        local-wtr-timer-expire(14),
        remote-lockout(15),
        remote-signal-fail-on-protection(16),
        remote-force-switch(17),
        remote-signal-fail-on-working(18),
        remote-signal-degrade-on-working(19),
        remote-signal-degrade-on-protection(20),
        remote-manual-switch-to-protection(21),
        remote-manual-switch-to-working(22),
        remote-wait-to-restore(23),
        remote-exercise-on-working(24),
        remote-exercise-on-protection(25),
        remote-reverse-request-on-working(26),
        remote-reverse-request-on-protection(27),
        remote-no-request-null(28),
        remote-no-request-normal(29),
        remote-do-not-revert(30),
        none(31)
    }
    MAX-ACCESS read-only
    STATUS current
    DESCRIPTION
    	"G8131 current event of the mpls tp vpws."
    ::= { mplsTPVpwsEntry 48 }  
    
mplsTPVpwsG8131FarEndLastEvent OBJECT-TYPE
    SYNTAX  INTEGER 
    {
        local-lockout(0),
        local-force-switch(1),
        local-signal-fail-on-working(2),
        local-working-recover-from-signal-fail(3),
        local-signal-fail-on-protection(4),
        local-protection-recover-from-signal-fail(5),
        local-signal-degrade-on-working(6),
        local-working-recover-from-signal-degrade(7),
        local-signal-degrade-on-protection(8),
        local-protection-recover-from-signal-degrade(9),
        local-manual-switch-to-protection(10),
        local-manual-switch-to-working(11),
        local-clear(12),
        local-exercise(13),
        local-wtr-timer-expire(14),
        remote-lockout(15),
        remote-signal-fail-on-protection(16),
        remote-force-switch(17),
        remote-signal-fail-on-working(18),
        remote-signal-degrade-on-working(19),
        remote-signal-degrade-on-protection(20),
        remote-manual-switch-to-protection(21),
        remote-manual-switch-to-working(22),
        remote-wait-to-restore(23),
        remote-exercise-on-working(24),
        remote-exercise-on-protection(25),
        remote-reverse-request-on-working(26),
        remote-reverse-request-on-protection(27),
        remote-no-request-null(28),
        remote-no-request-normal(29),
        remote-do-not-revert(30),
        none(31)  
    }
    MAX-ACCESS read-only
    STATUS current
    DESCRIPTION
    	"G8131 far end last event of the mpls tp vpws."
    ::= { mplsTPVpwsEntry 49 }  
    
mplsTPVpwsG8131RequestSignal OBJECT-TYPE
    SYNTAX  INTEGER { normal(1), null(2), none(3) }
    MAX-ACCESS read-only
    STATUS current
    DESCRIPTION
    	"G8131 request signal of the mpls tp vpws."
    ::= { mplsTPVpwsEntry 50 }         

mplsTPVpwsOAMCsfInterval OBJECT-TYPE
    SYNTAX Integer32 (0|1|60)
    MAX-ACCESS read-write
    STATUS current
    DESCRIPTION
      "Interval of CSF PDU.
      0:no oam-y1731 csf server enable."  
    ::= { mplsTPVpwsEntry 60 }  
     
mplsTPVpwsOAMCSFRxDown OBJECT-TYPE
    SYNTAX INTEGER (0|1)
    MAX-ACCESS read-write
    STATUS current
    DESCRIPTION
      "Action of Receiving CSF PDU AC Down.
      0:no oam-y1731 csf rx-aciton down.
      1:oam-y1731 csf rx-action down enable."  
    ::= { mplsTPVpwsEntry 61 } 
    
mplsTPVpwsOAMCSFRxRelay OBJECT-TYPE
    SYNTAX INTEGER (0|1)
    MAX-ACCESS read-write
    STATUS current
    DESCRIPTION
      "Action of Receiving CSF PDU AC relay to Eth-csf.
      0:no oam-y1731 csf rx-aciton relay.
      1:oam-y1731 csf rx-action relay enable."  
    ::= { mplsTPVpwsEntry 62 } 
    
mplsTPVpwsOAMCSFRxRelayMdName OBJECT-TYPE
    SYNTAX  OCTET STRING (SIZE(1..44))
    MAX-ACCESS read-write
    STATUS current
    DESCRIPTION
      "MD Name for rx-action relay."  
    ::= { mplsTPVpwsEntry 63 }   
    
mplsTPVpwsOAMCSFRxRelayMaVid OBJECT-TYPE
    SYNTAX Integer32 (1..4094)
    MAX-ACCESS read-write
    STATUS current
    DESCRIPTION
      "MA Vlan Id for rx-action relay."  
    ::= { mplsTPVpwsEntry 64 }
     
mplsTPVpwsOAMCSFRxRelayMepId OBJECT-TYPE
    SYNTAX Integer32 (1..8191)
    MAX-ACCESS read-write
    STATUS current
    DESCRIPTION
      "Mep Id for rx-action relay."  
    ::= { mplsTPVpwsEntry 65 } 
                
mplsVplsTPPeerTable OBJECT-TYPE
    SYNTAX  SEQUENCE OF MplsVplsTPPeerEntry
    MAX-ACCESS not-accessible
    STATUS   current
    DESCRIPTION 
    	"Peers to VPLS domains."
    ::= { mpls 34 }

mplsVplsTPPeerEntry OBJECT-TYPE
    SYNTAX  MplsVplsTPPeerEntry
    MAX-ACCESS not-accessible
    STATUS current
    DESCRIPTION 
    	"Entry of mplsVplsTPPeerTable."
    INDEX   { mplsVplsTPPeerVplsId, mplsVplsTPPeerName}
    ::= { mplsVplsTPPeerTable 1 }

MplsVplsTPPeerEntry   ::=
    SEQUENCE {
        mplsVplsTPPeerVplsId        		Unsigned32,
        mplsVplsTPPeerName 		    			OCTET STRING,
        mplsVplsTPPeerApsType	    			INTEGER,        
        mplsVplsTPPeerPEType	    			INTEGER,         
        mplsVplsTPPeerRowStatus		  		RowStatus,
        mplsVplsTPPeerPrimaryPw		 			OCTET STRING,
        mplsVplsTPPeerSecondaryPw   		OCTET STRING,
        mplsVplsTPPeerSelectedPw    				OCTET STRING,             
        mplsVplsTPPeerDescription	        OCTET STRING,
        mplsVplsTPPeerG8131Mode						INTEGER,
        mplsVplsTPPeerG8131WTRTimer					Integer32,
        mplsVplsTPPeerG8131HoldOffTimer			Integer32,
        mplsVplsTPPeerG8131Action						INTEGER,
        mplsVplsTPPeerG8131WorkingPw				OCTET STRING,
        mplsVplsTPPeerG8131ProtectionPw		OCTET STRING,
        mplsVplsTPPeerG8131ActivePath				INTEGER,
        mplsVplsTPPeerG8131WTRTimeLeft			Integer32,
        mplsVplsTPPeerG8131HoldOffTimeLeft	Integer32,
        mplsVplsTPPeerG8131DFOPState				INTEGER,
        mplsVplsTPPeerG8131CurrentState			INTEGER,
        mplsVplsTPPeerG8131LastState				INTEGER,
        mplsVplsTPPeerG8131CurrentEvent			INTEGER,
        mplsVplsTPPeerG8131FarEndLastEvent	INTEGER,
        mplsVplsTPPeerG8131RequestSignal		INTEGER               
        }

mplsVplsTPPeerVplsId OBJECT-TYPE
    SYNTAX  Unsigned32(1..4294967295)
    MAX-ACCESS not-accessible
    STATUS current
    DESCRIPTION 
    	"Identifying value for VPLS."
    ::= { mplsVplsTPPeerEntry 1 }
        
mplsVplsTPPeerName OBJECT-TYPE
    SYNTAX  OCTET STRING(SIZE(1..20)) 
    MAX-ACCESS not-accessible
    STATUS current
    DESCRIPTION 
    	"Name of the peer node to be added."
    ::= { mplsVplsTPPeerEntry 2 }
    
mplsVplsTPPeerApsType OBJECT-TYPE
    SYNTAX INTEGER { aps(1), non-aps(2) }
    MAX-ACCESS read-create
    STATUS current
    DESCRIPTION
        "APS type of the vpls tp-peer."
    DEFVAL { non-aps }
    ::= { mplsVplsTPPeerEntry 3 }	  

mplsVplsTPPeerPEType OBJECT-TYPE
    SYNTAX  INTEGER {spe(1),upe(2)}
    MAX-ACCESS read-create
    STATUS current
    DESCRIPTION 
       "Set PW type for mpls vpls tp-peer. The meanings of the values are:
        spe(1)  -  Superstarum PE;
        upe(2)  -  Underlayer PE;"  
    DEFVAL { 1 }
    ::= { mplsVplsTPPeerEntry 4 }
        
mplsVplsTPPeerRowStatus OBJECT-TYPE
    SYNTAX  RowStatus
    MAX-ACCESS read-create
    STATUS current
    DESCRIPTION 
    	"The status of this conceptual row.Now only realize CreateAndGo 
            and Destroy and Active."
    ::= { mplsVplsTPPeerEntry 10 }

mplsVplsTPPeerPrimaryPw OBJECT-TYPE
    SYNTAX  OCTET STRING(SIZE(0..20)) 
    MAX-ACCESS read-write
    STATUS current
    DESCRIPTION 
    	"Primary pw of the vpls tp-peer."
    ::= { mplsVplsTPPeerEntry 11 }
    
mplsVplsTPPeerSecondaryPw OBJECT-TYPE
    SYNTAX  OCTET STRING(SIZE(0..20)) 
    MAX-ACCESS read-write
    STATUS current
    DESCRIPTION 
    	"Secondary pw of the vpls tp-peer."
    ::= { mplsVplsTPPeerEntry 12 }
    
mplsVplsTPPeerSelectedPw OBJECT-TYPE
    SYNTAX  OCTET STRING(SIZE(0..20))
    MAX-ACCESS read-write
    STATUS current
    DESCRIPTION 
    	"Secondary pw tpe name of the vpls tp-peer.
    	 Can not set secondary pw for non-aps type."
    ::= { mplsVplsTPPeerEntry 13 }

-- mplsVplsTPPeerIngressPkts         OBJECT-TYPE
--     SYNTAX          Counter64
--     MAX-ACCESS      read-only
--     STATUS          current
--     DESCRIPTION
--         "Ingress packets number of mpls vpls peer."
--     ::= { mplsVplsTPPeerEntry 14 }
-- 
-- mplsVplsTPPeerIngressbytes         OBJECT-TYPE
--     SYNTAX          Counter64
--     MAX-ACCESS      read-only
--     STATUS          current
--     DESCRIPTION
--         "Ingress bytes number of mpls vpls peer."
--     ::= { mplsVplsTPPeerEntry 15 }
-- 
-- mplsVplsTPPeerEgressPkts         OBJECT-TYPE
--     SYNTAX          Counter64
--     MAX-ACCESS      read-only
--     STATUS          current
--     DESCRIPTION
--         "Egress packets number of mpls vpls peer."
--     ::= { mplsVplsTPPeerEntry 16 }
--     
-- mplsVplsTPPeerEgressBytes         OBJECT-TYPE
--     SYNTAX          Counter64
--     MAX-ACCESS      read-only
--     STATUS          current
--     DESCRIPTION
--         "Egress bytes number of mpls vpls peer."
--     ::= { mplsVplsTPPeerEntry 17 }     
   
mplsVplsTPPeerDescription OBJECT-TYPE
    SYNTAX  OCTET STRING (SIZE(1..20))
    MAX-ACCESS read-write
    STATUS current
    DESCRIPTION 
    	"Characters describing of this VPLS peer.
    	 Only less than 20 octets is accepted."
    ::= { mplsVplsTPPeerEntry 18 }  

-- mplsVplsTPPeerStats OBJECT-TYPE
--     SYNTAX  INTEGER {enable(1),disable(2)}
--     MAX-ACCESS read-write
--     STATUS current
--     DESCRIPTION 
--        "Set statistics for mpls vpls tp-peer. The meanings of the values are:
--         enable(1)  -  enable statistics;
--         disable(2) -  disable statistics;"  
--     DEFVAL { 2 }
--     ::= { mplsVplsTPPeerEntry 19 }  
                	                    
mplsVplsTPPeerG8131Mode OBJECT-TYPE
    SYNTAX  INTEGER { revertive(1), non-revertive(2) }
    MAX-ACCESS read-only
    STATUS current
    DESCRIPTION
    	"G8131 mode for the vpls tp-peer."
    ::= { mplsVplsTPPeerEntry 30 }

mplsVplsTPPeerG8131WTRTimer OBJECT-TYPE
    SYNTAX  Integer32(0..12)
    MAX-ACCESS read-write
    STATUS current
    DESCRIPTION
    	"G8131 wait-to-restore timer value for the vpls tp-peer, in minutes."
    DEFVAL {5}
    ::= { mplsVplsTPPeerEntry 31 }

mplsVplsTPPeerG8131HoldOffTimer OBJECT-TYPE
    SYNTAX  Integer32(0..100)
    MAX-ACCESS read-write
    STATUS current
    DESCRIPTION
    	"G8131 hold-off timer value for the vpls tp-peer, steps of 100ms."
    DEFVAL {0}
    ::= { mplsVplsTPPeerEntry 32 }

mplsVplsTPPeerG8131Action OBJECT-TYPE
    SYNTAX  INTEGER { force-switch(1), manual-swtich-to-working(2),
                      manual-switch-to-protection(3), lockout(4), 
                      exercise(5), clear(6) }
    MAX-ACCESS read-write
    STATUS current
    DESCRIPTION
    	"G8131 actions for the vpls tp-peer."
    ::= { mplsVplsTPPeerEntry 33 }

mplsVplsTPPeerG8131WorkingPw OBJECT-TYPE
    SYNTAX  OCTET STRING(SIZE(0..20))
    MAX-ACCESS read-only
    STATUS current
    DESCRIPTION
    	"G8131 working pw for the vpls tp-peer."
    ::= { mplsVplsTPPeerEntry 40 }

mplsVplsTPPeerG8131ProtectionPw OBJECT-TYPE
    SYNTAX  OCTET STRING(SIZE(0..20))
    MAX-ACCESS read-only
    STATUS current
    DESCRIPTION
    	"G8131 protection pw for the vpls tp-peer."
    ::= { mplsVplsTPPeerEntry 41 }
    
mplsVplsTPPeerG8131ActivePath OBJECT-TYPE
    SYNTAX  INTEGER { none(0), working-lsp(1), protection-lsp(2) }
    MAX-ACCESS read-only
    STATUS current
    DESCRIPTION
    	"G8131 active path for the vpls tp-peer."
    ::= { mplsVplsTPPeerEntry 42 }    
    
mplsVplsTPPeerG8131WTRTimeLeft OBJECT-TYPE
    SYNTAX  Integer32
    MAX-ACCESS read-only
    STATUS current
    DESCRIPTION
    	"Left time of G8131 wait-to-restore timer of the vpls tp-peer."
    ::= { mplsVplsTPPeerEntry 43 }   
    
mplsVplsTPPeerG8131HoldOffTimeLeft OBJECT-TYPE
    SYNTAX  Integer32
    MAX-ACCESS read-only
    STATUS current
    DESCRIPTION
    	"Left time of G8131 hold-off timer of the vpls tp-peer."
    ::= { mplsVplsTPPeerEntry 44 }           
    
mplsVplsTPPeerG8131DFOPState OBJECT-TYPE
    SYNTAX  INTEGER 
    {
        not-in-defect-mode(1),
        b-bit-mismatch-defect(2),
        r-bit-mismatch-defect(3),
        invalid-request-state(4),
        aps-recv-on-working-entity(5),
        aps-pdu-not-recv-after-state-change(6),
        a-bit-mismatch-defect(7),
        d-bit-mismatch-defect(8),
        t-bit-mismatch-defect(9)         
    }
    MAX-ACCESS read-only
    STATUS current
    DESCRIPTION
    	"G8131 DFOP state of the vpls tp-peer."
    ::= { mplsVplsTPPeerEntry 45 }  

mplsVplsTPPeerG8131CurrentState OBJECT-TYPE
    SYNTAX  INTEGER 
    {
        no-request-working-active(0),
        no-request-protection-avtive(1),
        lockout-of-protection(2),
        forced-switch(3),
        signal-fail-on-working(4),
        signal-fail-on-protection(5),
        signal-degrade-on-working(6),
        signal-degrade-on-protection(7),
        manual-switch-to-protection(8),
        manual-switch-to-working(9),
        wait-to-restore(10),
        do-not-revert(11),
        exercise-on-working(12),
        exercise-on-protection(13),
        reverse-request-on-working(14),
        reverse-request-on-protection(15),
        none(16)
    }
    MAX-ACCESS read-only
    STATUS current
    DESCRIPTION
    	"G8131 current state of the vpls tp-peer."
    ::= { mplsVplsTPPeerEntry 46 }  
    
mplsVplsTPPeerG8131LastState OBJECT-TYPE
    SYNTAX  INTEGER 
    {
        no-request-working-active(0),
        no-request-protection-avtive(1),
        lockout-of-protection(2),
        forced-switch(3),
        signal-fail-on-working(4),
        signal-fail-on-protection(5),
        signal-degrade-on-working(6),
        signal-degrade-on-protection(7),
        manual-switch-to-protection(8),
        manual-switch-to-working(9),
        wait-to-restore(10),
        do-not-revert(11),
        exercise-on-working(12),
        exercise-on-protection(13),
        reverse-request-on-working(14),
        reverse-request-on-protection(15),
        none(16) 
    }
    MAX-ACCESS read-only
    STATUS current
    DESCRIPTION
    	"G8131 last state of the vpls tp-peer."
    ::= { mplsVplsTPPeerEntry 47 }  
    
mplsVplsTPPeerG8131CurrentEvent OBJECT-TYPE
    SYNTAX  INTEGER 
    {
        local-lockout(0),
        local-force-switch(1),
        local-signal-fail-on-working(2),
        local-working-recover-from-signal-fail(3),
        local-signal-fail-on-protection(4),
        local-protection-recover-from-signal-fail(5),
        local-signal-degrade-on-working(6),
        local-working-recover-from-signal-degrade(7),
        local-signal-degrade-on-protection(8),
        local-protection-recover-from-signal-degrade(9),
        local-manual-switch-to-protection(10),
        local-manual-switch-to-working(11),
        local-clear(12),
        local-exercise(13),
        local-wtr-timer-expire(14),
        remote-lockout(15),
        remote-signal-fail-on-protection(16),
        remote-force-switch(17),
        remote-signal-fail-on-working(18),
        remote-signal-degrade-on-working(19),
        remote-signal-degrade-on-protection(20),
        remote-manual-switch-to-protection(21),
        remote-manual-switch-to-working(22),
        remote-wait-to-restore(23),
        remote-exercise-on-working(24),
        remote-exercise-on-protection(25),
        remote-reverse-request-on-working(26),
        remote-reverse-request-on-protection(27),
        remote-no-request-null(28),
        remote-no-request-normal(29),
        remote-do-not-revert(30),
        none(31)
    }
    MAX-ACCESS read-only
    STATUS current
    DESCRIPTION
    	"G8131 current event of the vpls tp-peer."
    ::= { mplsVplsTPPeerEntry 48 }  
    
mplsVplsTPPeerG8131FarEndLastEvent OBJECT-TYPE
    SYNTAX  INTEGER 
    {
        local-lockout(0),
        local-force-switch(1),
        local-signal-fail-on-working(2),
        local-working-recover-from-signal-fail(3),
        local-signal-fail-on-protection(4),
        local-protection-recover-from-signal-fail(5),
        local-signal-degrade-on-working(6),
        local-working-recover-from-signal-degrade(7),
        local-signal-degrade-on-protection(8),
        local-protection-recover-from-signal-degrade(9),
        local-manual-switch-to-protection(10),
        local-manual-switch-to-working(11),
        local-clear(12),
        local-exercise(13),
        local-wtr-timer-expire(14),
        remote-lockout(15),
        remote-signal-fail-on-protection(16),
        remote-force-switch(17),
        remote-signal-fail-on-working(18),
        remote-signal-degrade-on-working(19),
        remote-signal-degrade-on-protection(20),
        remote-manual-switch-to-protection(21),
        remote-manual-switch-to-working(22),
        remote-wait-to-restore(23),
        remote-exercise-on-working(24),
        remote-exercise-on-protection(25),
        remote-reverse-request-on-working(26),
        remote-reverse-request-on-protection(27),
        remote-no-request-null(28),
        remote-no-request-normal(29),
        remote-do-not-revert(30),
        none(31)
    }
    MAX-ACCESS read-only
    STATUS current
    DESCRIPTION
    	"G8131 far end last event of the vpls tp-peer."
    ::= { mplsVplsTPPeerEntry 49 }  
    
mplsVplsTPPeerG8131RequestSignal OBJECT-TYPE
    SYNTAX  INTEGER { normal(1), null(2), none(3) }
    MAX-ACCESS read-only
    STATUS current
    DESCRIPTION
    	"G8131 request signal of the vpls tp-peer."
    ::= { mplsVplsTPPeerEntry 50 }       

-- mplsVplsTPPeerMacWithdrawRxPks      OBJECT-TYPE
--     SYNTAX          Integer32
--     MAX-ACCESS      read-only
--     STATUS          current
--     DESCRIPTION
--         "Rx Mac-withdraw packets number of mpls peer."
--     ::= { mplsVplsTPPeerEntry 51 }    
-- 
-- mplsVplsTPPeerMacWithdrawTxPks      OBJECT-TYPE
--     SYNTAX          Integer32
--     MAX-ACCESS      read-only
--     STATUS          current
--     DESCRIPTION
--         "Tx Mac-withdraw packets number of mpls peer."
--     ::= { mplsVplsTPPeerEntry 52 }  
--     
-- mplsVplsTPPeerMacWithdrawAckRxPks      OBJECT-TYPE
--     SYNTAX          Integer32
--     MAX-ACCESS      read-only
--     STATUS          current
--     DESCRIPTION
--         "Rx Mac-withdraw ACK packets number of mpls peer."
--     ::= { mplsVplsTPPeerEntry 53 }      
-- 
-- mplsVplsTPPeerMacWithdrawAckTxPks      OBJECT-TYPE
--     SYNTAX          Integer32
--     MAX-ACCESS      read-only
--     STATUS          current
--     DESCRIPTION
--         "Tx Mac-withdraw ACK packets number of mpls peer."
--     ::= { mplsVplsTPPeerEntry 54 }  
    
mplsLspPeAisClientTable OBJECT-TYPE
    SYNTAX  SEQUENCE OF   MplsLspPeAisClientEntry
    MAX-ACCESS not-accessible
    STATUS   current
    DESCRIPTION 
    	"Table of all clients bound to ais server(lsp-pe)."
    ::= { mpls 35 }
    
mplsLspPeAisClientEntry OBJECT-TYPE
    SYNTAX  MplsLspPeAisClientEntry
    MAX-ACCESS not-accessible
    STATUS current
    DESCRIPTION 
    	"Entry of mplsLspPeAisClientTable."
    INDEX   { mplsLspPeName, lspPeAisClientBindType, lspPeAisClientBindName }
    ::= { mplsLspPeAisClientTable 1 }

MplsLspPeAisClientEntry   ::=
    SEQUENCE {
        lspPeAisClientBindType		INTEGER,         
        lspPeAisClientBindName		OCTET STRING,        
        lspPeAisClientRowStatus			RowStatus
        }

lspPeAisClientBindType OBJECT-TYPE
    SYNTAX INTEGER { lsp-p(1), pw-spe(2), pw-tpe(3) }
    MAX-ACCESS not-accessible
    STATUS current
    DESCRIPTION
      "Client lsp name for ais server(lsp-pe)."  
    ::= { mplsLspPeAisClientEntry 1 }	    
    
lspPeAisClientBindName OBJECT-TYPE
    SYNTAX OCTET STRING (SIZE (1..20))
    MAX-ACCESS not-accessible
    STATUS current
    DESCRIPTION
      "Client lsp name for ais server(lsp-pe)."  
    ::= { mplsLspPeAisClientEntry 2 }	    
            
lspPeAisClientRowStatus OBJECT-TYPE
    SYNTAX  RowStatus
    MAX-ACCESS read-create
    STATUS current
    DESCRIPTION 
    	"The status of this conceptual row.
    	Now only realize CreateAndGo and Destroy and Active."
    ::= { mplsLspPeAisClientEntry 10 }      

mplsLspPeLckClientTable OBJECT-TYPE
    SYNTAX  SEQUENCE OF   MplsLspPeLckClientEntry
    MAX-ACCESS not-accessible
    STATUS   current
    DESCRIPTION 
    	"Table of all clients bound to ais server(lsp-pe)."
    ::= { mpls 36 }
    
mplsLspPeLckClientEntry OBJECT-TYPE
    SYNTAX  MplsLspPeLckClientEntry
    MAX-ACCESS not-accessible
    STATUS current
    DESCRIPTION 
    	"Entry of mplsLspPeLckClientTable."
    INDEX   { mplsLspPeName, mplsLspPeLckClientBindType, mplsLspPeLckClientBindName }
    ::= { mplsLspPeLckClientTable 1 }

MplsLspPeLckClientEntry   ::=
    SEQUENCE {
        mplsLspPeLckClientBindType		INTEGER,         
        mplsLspPeLckClientBindName		OCTET STRING,        
        mplsLspPeLckClientRowStatus			RowStatus
        }

mplsLspPeLckClientBindType OBJECT-TYPE
    SYNTAX INTEGER { lsp-p(1), pw-spe(2), pw-tpe(3) }
    MAX-ACCESS not-accessible
    STATUS current
    DESCRIPTION
      "Client lsp name for ais server(lsp-pe)."  
    ::= { mplsLspPeLckClientEntry 1 }	    
    
mplsLspPeLckClientBindName OBJECT-TYPE
    SYNTAX OCTET STRING (SIZE (1..20))
    MAX-ACCESS not-accessible
    STATUS current
    DESCRIPTION
      "Client lsp name for ais server(lsp-pe)."  
    ::= { mplsLspPeLckClientEntry 2 }	    
            
mplsLspPeLckClientRowStatus OBJECT-TYPE
    SYNTAX  RowStatus
    MAX-ACCESS read-create
    STATUS current
    DESCRIPTION 
    	"The status of this conceptual row.
    	Now only realize CreateAndGo and Destroy and Active."
    ::= { mplsLspPeLckClientEntry 10 }  

mplsTpOAMSdReason OBJECT IDENTIFIER    ::= { mpls 44 }    

sdReasonAisRx OBJECT-TYPE
    SYNTAX INTEGER {enable(1), disable(2)}
    MAX-ACCESS read-write
    STATUS current
    DESCRIPTION
       "Ais rx."
    DEFVAL { disable }
    ::= { mplsTpOAMSdReason 1 }   

sdReasonAisDefect OBJECT-TYPE
    SYNTAX INTEGER {enable(1), disable(2)}
    MAX-ACCESS read-write
    STATUS current
    DESCRIPTION
       "Ais defect."
    DEFVAL { enable }       
    ::= { mplsTpOAMSdReason 2 }   

sdReasonCRC OBJECT-TYPE
    SYNTAX INTEGER {enable(1), disable(2)}
    MAX-ACCESS read-write
    STATUS current
    DESCRIPTION
       "CRC defect."
    DEFVAL { enable }       
    ::= { mplsTpOAMSdReason 3 }  
        
mplsDCNManagementIp OBJECT-TYPE
    SYNTAX IpAddress
    MAX-ACCESS read-write
    STATUS current
    DESCRIPTION
       "Managemenet ip address for MPLS DCN."
    ::= { mpls 45 }   
    
mplsTrustTopMostExp OBJECT-TYPE
    SYNTAX INTEGER { enable(1), disable(2) }
    MAX-ACCESS read-write
    STATUS current
    DESCRIPTION
       "The state of mpls trust topmost-exp."
    ::= { mpls 46 }   
    
mplsTpChannelType OBJECT-TYPE
    SYNTAX OCTET STRING (SIZE(1..4))
    MAX-ACCESS read-write
    STATUS current
    DESCRIPTION
       "The channel type of mpls-tp oam-y1731."
    ::= { mpls 47 }   
        
mplsTpNodeId OBJECT-TYPE
    SYNTAX IpAddress
    MAX-ACCESS read-write
    STATUS current
    DESCRIPTION
       "The node id of the switch."
    ::= { mpls 48 }   
    
mplsTpOAMSfReason OBJECT IDENTIFIER    ::= { mpls 49 }    

sfReasonAisDefect OBJECT-TYPE
    SYNTAX INTEGER {enable(1), disable(2)}
    MAX-ACCESS read-write
    STATUS current
    DESCRIPTION
       "Ais defect."
    DEFVAL { disable }
    ::= { mplsTpOAMSfReason 1 }   

sfReasonLoc OBJECT-TYPE
    SYNTAX INTEGER {enable(1), disable(2)}
    MAX-ACCESS read-write
    STATUS current
    DESCRIPTION
       "Loc."
    DEFVAL { enable }       
    ::= { mplsTpOAMSfReason 2 }   

sfReasonRdiRx OBJECT-TYPE
    SYNTAX INTEGER {enable(1), disable(2)}
    MAX-ACCESS read-write
    STATUS current
    DESCRIPTION
       "Recv Rdi."
    DEFVAL { disable }       
    ::= { mplsTpOAMSfReason 3 }
    
sfReasonAisRx OBJECT-TYPE
    SYNTAX INTEGER {enable(1), disable(2)}
    MAX-ACCESS read-write
    STATUS current
    DESCRIPTION
       "Recv Ais."
    DEFVAL { disable }       
    ::= { mplsTpOAMSfReason 4 } 
    
sfReasonCsfDefect OBJECT-TYPE
    SYNTAX INTEGER {enable(1), disable(2)}
    MAX-ACCESS read-write
    STATUS current
    DESCRIPTION
       "Cfs Defect."
    DEFVAL { disable }       
    ::= { mplsTpOAMSfReason 5 }        
    
    
mplsTpOAMRdiReason OBJECT IDENTIFIER    ::= { mpls 50 }    

rdiReasonLoc OBJECT-TYPE
    SYNTAX INTEGER {enable(1), disable(2)}
    MAX-ACCESS read-write
    STATUS current
    DESCRIPTION
       "LOC defect."
    DEFVAL { enable }
    ::= { mplsTpOAMRdiReason 1 }   

rdiReasonCCError OBJECT-TYPE
    SYNTAX INTEGER {enable(1), disable(2)}
    MAX-ACCESS read-write
    STATUS current
    DESCRIPTION
       "CC error defects: include RMEP not found, CC Interval mismatch."
    DEFVAL { enable }       
    ::= { mplsTpOAMRdiReason 2 }   

rdiReasonCCMisMerge OBJECT-TYPE
    SYNTAX INTEGER {enable(1), disable(2)}
    MAX-ACCESS read-write
    STATUS current
    DESCRIPTION
       "CC mismerge defects: include MEGID mismatch, Low CC level."
    DEFVAL { enable }       
    ::= { mplsTpOAMRdiReason 3 }   
        
mplsTpOAMAisReason OBJECT IDENTIFIER    ::= { mpls 51 }

aisReasonLoc OBJECT-TYPE
    SYNTAX INTEGER {enable(1), disable(2)}
    MAX-ACCESS read-write
    STATUS current
    DESCRIPTION
       "LOC defect."
    DEFVAL { enable }
    ::= { mplsTpOAMAisReason 1 }   

aisReasonUnExpRMepID OBJECT-TYPE
    SYNTAX INTEGER {enable(1), disable(2)}
    MAX-ACCESS read-write
    STATUS current
    DESCRIPTION
       "Unexpected RMEPID."
    DEFVAL { disable }       
    ::= { mplsTpOAMAisReason 2 }   

aisReasonUnExpInterval OBJECT-TYPE
    SYNTAX INTEGER {enable(1), disable(2)}
    MAX-ACCESS read-write
    STATUS current
    DESCRIPTION
       "Unexpected CC Interval."
    DEFVAL { disable }       
    ::= { mplsTpOAMAisReason 3 }   

aisReasonUnExpMegId OBJECT-TYPE
    SYNTAX INTEGER {enable(1), disable(2)}
    MAX-ACCESS read-write
    STATUS current
    DESCRIPTION
       "Unexpected MEGID."
    DEFVAL { disable }       
    ::= { mplsTpOAMAisReason 4 }   
    
aisReasonUnExpMegLevel OBJECT-TYPE
    SYNTAX INTEGER {enable(1), disable(2)}
    MAX-ACCESS read-write
    STATUS current
    DESCRIPTION
       "Unexpected CC Level."
    DEFVAL { disable }       
    ::= { mplsTpOAMAisReason 5 }     
          
aisReasonAisDefect OBJECT-TYPE
    SYNTAX INTEGER {enable(1), disable(2)}
    MAX-ACCESS read-write
    STATUS current
    DESCRIPTION
       "AIS defect."
    DEFVAL { enable }       
    ::= { mplsTpOAMAisReason 6 }     

aisReasonLockRx OBJECT-TYPE
    SYNTAX INTEGER {enable(1), disable(2)}
    MAX-ACCESS read-write
    STATUS current
    DESCRIPTION
       "Lock Rx."
    DEFVAL { enable }       
    ::= { mplsTpOAMAisReason 7 }     
          
mplsTpOAMEventRuleTable OBJECT-TYPE
    SYNTAX  SEQUENCE OF MplsTpOAMEventRuleEntry
    MAX-ACCESS not-accessible
    STATUS   current
    DESCRIPTION 
    	"MPLS-TP OAM event rule table."
    ::= { mpls 52 }

mplsTpOAMEventRuleEntry OBJECT-TYPE
    SYNTAX  MplsTpOAMEventRuleEntry
    MAX-ACCESS not-accessible
    STATUS current
    DESCRIPTION 
    	"MPLS-Tp event rule entries."
    INDEX   { mplsTpOAMEventId }
    ::= { mplsTpOAMEventRuleTable 1 }

MplsTpOAMEventRuleEntry   ::=
    SEQUENCE {
        mplsTpOAMEventRuleId        INTEGER,      
        mplsTpOAMEventLog					  INTEGER,
        mplsTpOAMEventTrap          INTEGER,       
        mplsTpOAMEventCache         INTEGER
        }

mplsTpOAMEventRuleId OBJECT-TYPE
    SYNTAX INTEGER
    {
        loc(1),
        unExpRMepID(2),
        unExpInterval(3),
        unExpMegId(4),
        unExpMegLevel(5),
        rdiRx(6),
        rdiTx(7),
        waitFirstCC(8),
        aisRx(9),
        aisTx(10),
        aisDefect(11),        
        eventCacheFull(12),
        oneDmCacheFull(13),
        lockRx(14),
        lockTx(15),
        lockDefect(16),
        crcDefect(17)
    }
    MAX-ACCESS not-accessible
    STATUS current
    DESCRIPTION
      "MPLS-tp OAM event id."  
    ::= { mplsTpOAMEventRuleEntry 1 }	

mplsTpOAMEventLog OBJECT-TYPE
    SYNTAX INTEGER {enable(1), disable(2)}
    MAX-ACCESS read-write
    STATUS current
    DESCRIPTION
      "State of MPLS-tp event log."    
    ::= { mplsTpOAMEventRuleEntry 2 }	

mplsTpOAMEventTrap OBJECT-TYPE
    SYNTAX INTEGER {enable(1), disable(2)}
    MAX-ACCESS read-write
    STATUS current
    DESCRIPTION
      "State of MPLS-tp event trap."        
    ::= { mplsTpOAMEventRuleEntry 3 }	

mplsTpOAMEventCache OBJECT-TYPE
    SYNTAX INTEGER {enable(1), disable(2)}
    MAX-ACCESS read-write
    STATUS current
    DESCRIPTION
      "State of MPLS-tp event cache."     
    ::= { mplsTpOAMEventRuleEntry 4 }	        

mplsTpSectionTable OBJECT-TYPE
    SYNTAX  SEQUENCE OF   MplsTpSectionEntry
    MAX-ACCESS not-accessible
    STATUS   current
    DESCRIPTION 
    	"Table of all mpls-tp section instances."
    ::= { mpls 53 }
    
mplsTpSectionEntry OBJECT-TYPE
    SYNTAX  MplsTpSectionEntry
    MAX-ACCESS not-accessible
    STATUS current
    DESCRIPTION 
    	"Entry of mplsTpSectionTable."
    INDEX   { sectionName }
    ::= { mplsTpSectionTable 1 }

MplsTpSectionEntry   ::=
    SEQUENCE {
        sectionName                OCTET STRING,       
        sectionRowStatus      	   RowStatus,
        sectionPeer		             IpAddress,
        sectionOutIfindex 				 Integer32,
        sectionOutMemIfindex			 Integer32,
        sectionDescription	       OCTET STRING,
        sectionMegLevel            Integer32,        
        sectionMegId		           OCTET STRING,
        sectionMegIdIcc            Integer32,
        sectionMepId		           Integer32,
        sectionMepInterval	       INTEGER,
        sectionMepExp     	       Integer32,                
        sectionRMepId		           Integer32,        
        sectionCCState		         INTEGER,                
        sectionEventCacheSize	     Integer32,
        section1dmCacheSize	       Integer32,
        sectionAisInterval	       Integer32,          
        sectionLck							   INTEGER,        
        sectionLckInterval         Integer32,
        sectionState               INTEGER,
        sectionEvtLOC              INTEGER,
        sectionEvtUMP              INTEGER,
        sectionEvtUIN              INTEGER,
        sectionEvtUMG              INTEGER,
        sectionEvtULV              INTEGER,
        sectionEvtW1ST             INTEGER,
        sectionEvtRDIR             INTEGER,
        sectionEvtRDIT             INTEGER,
        sectionEvtAISR             INTEGER,
        sectionEvtAIST             INTEGER,
        sectionEvtAISD             INTEGER,
        sectionEvtLCKR             INTEGER,
        sectionEvtLCKT             INTEGER,
        sectionEvtLCKD             INTEGER,
        sectionEvtCRC              INTEGER,        
        sectionLckTxEnable         INTEGER,
        sectionOAMState            INTEGER,
        sectionLmDualExp           Integer32,
        sectionLmDualStatInterval  Integer32,
        sectionLmDualCacheSize     Integer32,
        sectionLmSingleExp         Integer32,
        sectionLmSingleInterval    INTEGER,
        sectionLmSingleCacheSize   Integer32,            
        sectionLmEnableState       INTEGER,
        sectionLmLocalLossThreshold    Integer32,
        sectionLmRemoteLossThreshold   Integer32,
        sectionLmSingleRxCount	       Integer32,
        sectionLmSingleTxCount	       Integer32,
        sectionLmSingleSuccessRate     Integer32,
        sectionLmSingleStartTime	   OCTET STRING,
        sectionLmSingleEndTime	       OCTET STRING		
        }
        
sectionName OBJECT-TYPE
    SYNTAX OCTET STRING (SIZE (1..12))
    MAX-ACCESS not-accessible
    STATUS current
    DESCRIPTION
      "MPLS-TP section name."  
    ::= { mplsTpSectionEntry 1 }	    
      
sectionRowStatus OBJECT-TYPE
    SYNTAX  RowStatus
    MAX-ACCESS read-create
    STATUS current
    DESCRIPTION 
    	"The status of this conceptual row.
    	Now only realize CreateAndGo and Destroy and Active."
    ::= { mplsTpSectionEntry 10 }        
    
sectionPeer OBJECT-TYPE
    SYNTAX IpAddress
    MAX-ACCESS read-write
    STATUS current
    DESCRIPTION
      "The peer IP address of the section."  
    ::= { mplsTpSectionEntry 11 }	        

sectionOutIfindex OBJECT-TYPE
    SYNTAX Integer32(0..65535)
    MAX-ACCESS read-write
    STATUS current
    DESCRIPTION
      "The out-going interface of the section in non-ip env."  
    ::= { mplsTpSectionEntry 12 }	    

sectionOutMemIfindex OBJECT-TYPE
    SYNTAX Integer32(0..65535)
    MAX-ACCESS read-write
    STATUS current
    DESCRIPTION
      "The member out-going interface of the section in non-ip env."  
    ::= { mplsTpSectionEntry 13 }	  
        
sectionDescription OBJECT-TYPE
    SYNTAX  OCTET STRING (SIZE(1..20))
    MAX-ACCESS read-write
    STATUS current
    DESCRIPTION 
    	"Characters describing of this mpls-tp section.
    	 Only less than 20 octets is accepted."
    ::= { mplsTpSectionEntry 14 }       
  
sectionMegLevel OBJECT-TYPE
    SYNTAX Integer32 (0..7)
    MAX-ACCESS read-write
    STATUS current
    DESCRIPTION
      "OAM level."
    DEFVAL { 7 }
    ::= { mplsTpSectionEntry 19 }	 
            
sectionMegId OBJECT-TYPE
    SYNTAX OCTET STRING (SIZE (1..12))
    MAX-ACCESS read-write
    STATUS current
    DESCRIPTION
      "MEG ID of the service."  
    ::= { mplsTpSectionEntry 20 }	         

sectionMegIdIcc OBJECT-TYPE
    SYNTAX Integer32 (1..6)
    MAX-ACCESS read-write
    STATUS current
    DESCRIPTION
      "ICC length of MEG ID."
    DEFVAL { 6 }
    ::= { mplsTpSectionEntry 21 }	  

sectionMepId OBJECT-TYPE
    SYNTAX Integer32 (1..8191)
    MAX-ACCESS read-write
    STATUS current
    DESCRIPTION
      "MEP ID."  
    ::= { mplsTpSectionEntry 22 }	    
    
sectionMepInterval OBJECT-TYPE
    SYNTAX INTEGER 
    {
        three-point-three-ms(1), 
        ten-ms(2),
        one-hundred-ms(3),
        one-sec(4),
        ten-sec(5),
        one-min(6),
        ten-min(7)
    }
    MAX-ACCESS read-write
    STATUS current
    DESCRIPTION
      "MEP Interval."  
    ::= { mplsTpSectionEntry 23 }	 

sectionMepExp OBJECT-TYPE
    SYNTAX Integer32 (0..7)
    MAX-ACCESS read-write
    STATUS current
    DESCRIPTION
      "EXP value, default is 7." 
    DEFVAL { 7 } 
    ::= { mplsTpSectionEntry 24 }	

sectionRMepId OBJECT-TYPE
    SYNTAX Integer32 (1..8191)
    MAX-ACCESS read-write
    STATUS current
    DESCRIPTION
      "Remote MEP ID."  
    ::= { mplsTpSectionEntry 25 }	      

sectionCCState OBJECT-TYPE
    SYNTAX INTEGER {enable(1), disable(2)}
    MAX-ACCESS read-write
    STATUS current
    DESCRIPTION
      "CC state."
    DEFVAL { disable }  
    ::= { mplsTpSectionEntry 26 }	      
    
sectionEventCacheSize OBJECT-TYPE
    SYNTAX Integer32 (8..256)
    MAX-ACCESS read-write
    STATUS current
    DESCRIPTION
      "Event entry cache size."  
    DEFVAL { 8 }        
    ::= { mplsTpSectionEntry 27 }	          
         
section1dmCacheSize OBJECT-TYPE
    SYNTAX Integer32 (8..256)
    MAX-ACCESS read-write
    STATUS current
    DESCRIPTION
      "1dm entry cache size."  
    DEFVAL { 8 }        
    ::= { mplsTpSectionEntry 28 }	 
    
sectionAisInterval OBJECT-TYPE
    SYNTAX Integer32 (0|1|60)
    MAX-ACCESS read-write
    STATUS current
    DESCRIPTION
      "Interval of AIS PDU.
      0:no oam-y1731 ais server enable."  
    ::= { mplsTpSectionEntry 29 }        

sectionLck OBJECT-TYPE
    SYNTAX INTEGER {enable(1), disable(2)}
    MAX-ACCESS read-write
    STATUS current
    DESCRIPTION
      "Lck state."    
    DEFVAL { disable }  
    ::= { mplsTpSectionEntry 31 }	 
    
sectionLckInterval OBJECT-TYPE
    SYNTAX Integer32 (0|1|60)
    MAX-ACCESS read-write
    STATUS current
    DESCRIPTION
      "Mpls-tp section lock interval.
      0:no oam-y1731 lck server enable."    
    DEFVAL { 0 }  
    ::= { mplsTpSectionEntry 32 }	                    

sectionState OBJECT-TYPE
    SYNTAX INTEGER {init(0), fail(1), ok(2)}
    MAX-ACCESS read-only
    STATUS current
    DESCRIPTION
      "MPLS-TP section status"  
    ::= { mplsTpSectionEntry 33 }
    
sectionEvtLOC OBJECT-TYPE
    SYNTAX INTEGER {enable(1), disable(2)}
    MAX-ACCESS read-only
    STATUS current
    DESCRIPTION
      "Loc state."    
    DEFVAL { disable }  
    ::= { mplsTpSectionEntry 34 }

sectionEvtUMP OBJECT-TYPE
    SYNTAX INTEGER {enable(1), disable(2)}
    MAX-ACCESS read-only
    STATUS current
    DESCRIPTION
      "Unexp RMEPID state."    
    DEFVAL { disable }  
    ::= { mplsTpSectionEntry 35 }

sectionEvtUIN OBJECT-TYPE
    SYNTAX INTEGER {enable(1), disable(2)}
    MAX-ACCESS read-only
    STATUS current
    DESCRIPTION
      "Unexp interval state."    
    DEFVAL { disable }  
    ::= { mplsTpSectionEntry 36 }

sectionEvtUMG OBJECT-TYPE
    SYNTAX INTEGER {enable(1), disable(2)}
    MAX-ACCESS read-only
    STATUS current
    DESCRIPTION
      "Unexp MEGID state."    
    DEFVAL { disable }  
    ::= { mplsTpSectionEntry 37 }

sectionEvtULV OBJECT-TYPE
    SYNTAX INTEGER {enable(1), disable(2)}
    MAX-ACCESS read-only
    STATUS current
    DESCRIPTION
      "Unexp Level state."    
    DEFVAL { disable } 
    ::= { mplsTpSectionEntry 38 }

sectionEvtW1ST OBJECT-TYPE
    SYNTAX INTEGER {enable(1), disable(2)}
    MAX-ACCESS read-only
    STATUS current
    DESCRIPTION
      "Wait 1st CCM state."    
    DEFVAL { disable } 
    ::= { mplsTpSectionEntry 39 }

sectionEvtRDIR OBJECT-TYPE
    SYNTAX INTEGER {enable(1), disable(2)}
    MAX-ACCESS read-only
    STATUS current
    DESCRIPTION
      "RDI RX state."    
    DEFVAL { disable } 
    ::= { mplsTpSectionEntry 40 }

sectionEvtRDIT OBJECT-TYPE
    SYNTAX INTEGER {enable(1), disable(2)}
    MAX-ACCESS read-only
    STATUS current
    DESCRIPTION
      "RDI TX state."    
    DEFVAL { disable } 
    ::= { mplsTpSectionEntry 41 }

sectionEvtAISR OBJECT-TYPE
    SYNTAX INTEGER {enable(1), disable(2)}
    MAX-ACCESS read-only
    STATUS current
    DESCRIPTION
      "AIS RX state."    
    DEFVAL { disable } 
    ::= { mplsTpSectionEntry 42 }

sectionEvtAIST OBJECT-TYPE
    SYNTAX INTEGER {enable(1), disable(2)}
    MAX-ACCESS read-only
    STATUS current
    DESCRIPTION
      "AIS RX state."    
    DEFVAL { disable } 
    ::= { mplsTpSectionEntry 43 }

sectionEvtAISD OBJECT-TYPE
    SYNTAX INTEGER {enable(1), disable(2)}
    MAX-ACCESS read-only
    STATUS current
    DESCRIPTION
      "AIS RX state."    
    DEFVAL { disable } 
    ::= { mplsTpSectionEntry 44 }

sectionEvtLCKR OBJECT-TYPE
    SYNTAX INTEGER {enable(1), disable(2)}
    MAX-ACCESS read-only
    STATUS current
    DESCRIPTION
      "LCK RX state."    
    DEFVAL { disable } 
    ::= { mplsTpSectionEntry 45 }

sectionEvtLCKT OBJECT-TYPE
    SYNTAX INTEGER {enable(1), disable(2)}
    MAX-ACCESS read-only
    STATUS current
    DESCRIPTION
      "LCK RX state."    
    DEFVAL { disable } 
    ::= { mplsTpSectionEntry 46 }

sectionEvtLCKD OBJECT-TYPE
    SYNTAX INTEGER {enable(1), disable(2)}
    MAX-ACCESS read-only
    STATUS current
    DESCRIPTION
      "LCK RX state."    
    DEFVAL { disable } 
    ::= { mplsTpSectionEntry 47 }            

sectionLckTxEnable OBJECT-TYPE
    SYNTAX INTEGER {enable(1), disable(2)}
    MAX-ACCESS read-only
    STATUS current
    DESCRIPTION
      "oam-y1731 lck server enable."    
    DEFVAL { 2 }  
    ::= { mplsTpSectionEntry 48 }		

sectionEvtCRC OBJECT-TYPE
    SYNTAX INTEGER {enable(1), disable(2)}
    MAX-ACCESS read-only
    STATUS current
    DESCRIPTION
      "CRC RX state."    
    DEFVAL { disable } 
    ::= { mplsTpSectionEntry 49 }  
    
sectionOAMState OBJECT-TYPE
    SYNTAX INTEGER {init(0), fail(1), ok(2)}
    MAX-ACCESS read-only
    STATUS current
    DESCRIPTION
      "oam-y1731 Rmep state."   
    ::= { mplsTpSectionEntry 50 }

sectionLmDualExp OBJECT-TYPE
    SYNTAX Integer32 (0..9)
    MAX-ACCESS read-write
    STATUS current
    DESCRIPTION
      "Configure dual-ended loss measurment packets with specified exp will be counted.
      <0-7> specified exp; 8 means Packets with different exp will be counted separately;
      9 means All packets with different exp will be counted together."
    ::= { mplsTpSectionEntry 61 }
    
sectionLmDualStatInterval OBJECT-TYPE
    SYNTAX Integer32 (1..10)
    MAX-ACCESS read-write
    STATUS current
    DESCRIPTION
      "Configure dual-ended loss measurment interval value."
    DEFVAL { 1 } 
    ::= { mplsTpSectionEntry 62 }

sectionLmDualCacheSize    OBJECT-TYPE
    SYNTAX Integer32 (1..512)
    MAX-ACCESS read-write
    STATUS current
    DESCRIPTION
      "Configure dual-ended loss measurment cache size."
    DEFVAL { 128 } 
    ::= { mplsTpSectionEntry 63 }

sectionLmSingleExp OBJECT-TYPE
    SYNTAX Integer32 (0..9)
    MAX-ACCESS read-write
    STATUS current
    DESCRIPTION
      "Configure single-ended loss measurment packets with specified exp will be counted.
      <0-7> specified exp; 8 means Packets with different exp will be counted separately;
      9 means All packets with different exp will be counted together."
    ::= { mplsTpSectionEntry 66 }

sectionLmSingleInterval OBJECT-TYPE
    SYNTAX INTEGER         
    {    
        one-hundred-ms(1),
        one-sec(2),
        ten-sec(3)
    }
    MAX-ACCESS read-write
    STATUS current
    DESCRIPTION
      "Config Interval."
    ::= { mplsTpSectionEntry 67 }	

sectionLmSingleCacheSize    OBJECT-TYPE
    SYNTAX Integer32 (1..512)
    MAX-ACCESS read-write
    STATUS current
    DESCRIPTION
      "Configure single-ended loss measurment cache size."
    DEFVAL { 128 } 
    ::= { mplsTpSectionEntry 68 }
    
sectionLmEnableState OBJECT-TYPE
    SYNTAX INTEGER {enable-dual(1), enable-single(2), disable(3)}
    MAX-ACCESS read-write
    STATUS current
    DESCRIPTION
      "Enable or disable oam-y1731 loss measurment."    
    DEFVAL { disable } 
    ::= { mplsTpSectionEntry 70 }    

sectionLmLocalLossThreshold    OBJECT-TYPE
    SYNTAX Integer32 (0..100)
    MAX-ACCESS read-write
    STATUS current
    DESCRIPTION
      "Local packet loss percentage, 0 means threshold not enabled."
    DEFVAL { 0 } 
    ::= { mplsTpSectionEntry 71 }    

sectionLmRemoteLossThreshold    OBJECT-TYPE
    SYNTAX Integer32 (0..100)
    MAX-ACCESS read-write
    STATUS current
    DESCRIPTION
      "Local packet loss percentage, 0 means threshold not enabled."
    DEFVAL { 0 } 
    ::= { mplsTpSectionEntry 72 }

sectionLmSingleRxCount    OBJECT-TYPE
    SYNTAX Integer32 (0..255)
    MAX-ACCESS read-only
    STATUS current
    DESCRIPTION
      "LMM single-ended packet Rx count."
    ::= { mplsTpSectionEntry 73 } 

sectionLmSingleTxCount    OBJECT-TYPE
    SYNTAX Integer32 (0..255)
    MAX-ACCESS read-only
    STATUS current
    DESCRIPTION
      "LMM single-ended packet Tx count."
    ::= { mplsTpSectionEntry 74 } 

sectionLmSingleSuccessRate    OBJECT-TYPE
    SYNTAX Integer32 (0..100)
    MAX-ACCESS read-only
    STATUS current
    DESCRIPTION
      "LMM single-ended success rate."
    ::= { mplsTpSectionEntry 75 } 

sectionLmSingleStartTime OBJECT-TYPE
    SYNTAX  OCTET STRING(SIZE(1..50))
    MAX-ACCESS read-only
    STATUS current
    DESCRIPTION
    	"LMM proactive single-ended start time."
    ::= { mplsTpSectionEntry 76 }
	
sectionLmSingleEndTime OBJECT-TYPE
    SYNTAX  OCTET STRING(SIZE(1..50))
    MAX-ACCESS read-only
    STATUS current
    DESCRIPTION
    	"LMM proactive single-ended end time."
    ::= { mplsTpSectionEntry 77 }
	
mplsTpSectionAisClientTable OBJECT-TYPE
    SYNTAX  SEQUENCE OF   MplsTpSectionAisClientEntry
    MAX-ACCESS not-accessible
    STATUS   current
    DESCRIPTION 
    	"Table of all clients bound to mpls-tp section ais server."
    ::= { mpls 54 }
    
mplsTpSectionAisClientEntry OBJECT-TYPE
    SYNTAX  MplsTpSectionAisClientEntry
    MAX-ACCESS not-accessible
    STATUS current
    DESCRIPTION 
    	"Entry of mplsTpSectionAisClientTable."
    INDEX   { sectionName, sectionAisClientBindType, sectionAisClientBindName }
    ::= { mplsTpSectionAisClientTable 1 }

MplsTpSectionAisClientEntry   ::=
    SEQUENCE {
        sectionAisClientBindType    INTEGER,
        sectionAisClientBindName		OCTET STRING,        
        sectionAisClientRowStatus			RowStatus
        }
        
sectionAisClientBindType OBJECT-TYPE
    SYNTAX INTEGER {lsp-p(1),lsp-pe(2)}
    MAX-ACCESS not-accessible
    STATUS current
    DESCRIPTION
      "Client type for ais server(lsp-pe)."  
    ::= { mplsTpSectionAisClientEntry 1 }	           
    
sectionAisClientBindName OBJECT-TYPE
    SYNTAX OCTET STRING (SIZE (1..20))
    MAX-ACCESS not-accessible
    STATUS current
    DESCRIPTION
      "Client lsp name for MPLS-TP section ais server."  
    ::= { mplsTpSectionAisClientEntry 2 }	    
            
sectionAisClientRowStatus OBJECT-TYPE
    SYNTAX  RowStatus
    MAX-ACCESS read-create
    STATUS current
    DESCRIPTION 
    	"The status of this conceptual row.
    	Now only realize CreateAndGo and Destroy and Active."
    ::= { mplsTpSectionAisClientEntry 10 }        

mplsTpSectionLckClientTable OBJECT-TYPE
    SYNTAX  SEQUENCE OF   MplsTpSectionLckClientEntry
    MAX-ACCESS not-accessible
    STATUS   current
    DESCRIPTION 
    	"Table of all clients bound to mpls-tp section lck server."
    ::= { mpls 55 }
    
mplsTpSectionLckClientEntry OBJECT-TYPE
    SYNTAX  MplsTpSectionLckClientEntry
    MAX-ACCESS not-accessible
    STATUS current
    DESCRIPTION 
    	"Entry of mplsTpSectionLckClientTable."
    INDEX   { sectionName, sectionLckClientBindType, sectionLckClientBindName }
    ::= { mplsTpSectionLckClientTable 1 }

MplsTpSectionLckClientEntry   ::=
    SEQUENCE {
        sectionLckClientBindType    INTEGER,
        sectionLckClientBindName		OCTET STRING,        
        sectionLckClientRowStatus			RowStatus
        }
        
sectionLckClientBindType OBJECT-TYPE
    SYNTAX INTEGER {lsp-p(1),lsp-pe(2)}
    MAX-ACCESS not-accessible
    STATUS current
    DESCRIPTION
      "Client type for lck server(section)."  
    ::= { mplsTpSectionLckClientEntry 1 }	           
    
sectionLckClientBindName OBJECT-TYPE
    SYNTAX OCTET STRING (SIZE (1..20))
    MAX-ACCESS not-accessible
    STATUS current
    DESCRIPTION
      "Client lsp name for MPLS-TP section lck server."  
    ::= { mplsTpSectionLckClientEntry 2 }	    
            
sectionLckClientRowStatus OBJECT-TYPE
    SYNTAX  RowStatus
    MAX-ACCESS read-create
    STATUS current
    DESCRIPTION 
    	"The status of this conceptual row.
    	Now only realize CreateAndGo and Destroy and Active."
    ::= { mplsTpSectionLckClientEntry 10 }        
        
mplsTpOAMClearCache OBJECT-TYPE
    SYNTAX INTEGER { event-cache(1), onedm-cache(2), statistics-cache(3) }
    MAX-ACCESS read-write
    STATUS current
    DESCRIPTION
       "Clear MPLS-TP OAM cache ."
    ::= { mpls 56 } 

mplsTpOAMLoopbackDiscoveryTable OBJECT-TYPE
    SYNTAX  SEQUENCE OF   MplsTpOAMLoopbackDiscoveryEntry
    MAX-ACCESS not-accessible
    STATUS   current
    DESCRIPTION 
    	"Table of mpls-tp discovery loopback."
    ::= { mpls 60 }
    
mplsTpOAMLoopbackDiscoveryEntry OBJECT-TYPE
    SYNTAX  MplsTpOAMLoopbackDiscoveryEntry
    MAX-ACCESS not-accessible
    STATUS current
    DESCRIPTION 
    	"Entry of mplsTpOAMLoopbackDiscoveryTable."
    INDEX   { oamDiscoveryIndex }
    ::= { mplsTpOAMLoopbackDiscoveryTable 1 }

MplsTpOAMLoopbackDiscoveryEntry   ::=
    SEQUENCE {
        oamDiscoveryIndex						Integer32,
        oamDiscoveryServiceType			INTEGER,
        oamDiscoveryServiceName			OCTET STRING,
        oamDiscoveryStartTTL				Integer32,
        oamDiscoveryEndTTL					Integer32,
        oamDiscoveryMepIdTlv				INTEGER,
        oamDiscoveryDataTlv					Integer32,
        oamDiscoveryTimeout					Integer32,
        oamDiscoveryExp							Integer32, 
        oamDiscoveryTstTlv					Integer32,
        oamDiscoveryTstPattern			Integer32,       
        oamDiscoveryRowstatus				RowStatus,
        oamDiscoveryOperState				INTEGER,
        oamDiscoveryTimeSpent				Integer32,
        oamDiscoverySuccessRate			Integer32
        }
        
oamDiscoveryIndex OBJECT-TYPE
    SYNTAX Integer32 (1)
    MAX-ACCESS not-accessible
    STATUS current
    DESCRIPTION
      "Index of oam discovery loopback request.Must be 1."  
    ::= { mplsTpOAMLoopbackDiscoveryEntry 1 }	           
    
oamDiscoveryServiceType OBJECT-TYPE
    SYNTAX INTEGER { section(1), lsp-pe(2), pw-tpe(3) }
    MAX-ACCESS read-write
    STATUS current
    DESCRIPTION
      "Service type of the request."  
    ::= { mplsTpOAMLoopbackDiscoveryEntry 2 }	    
            
oamDiscoveryServiceName OBJECT-TYPE
    SYNTAX OCTET STRING (SIZE (1..20))
    MAX-ACCESS read-write
    STATUS current
    DESCRIPTION
      "Service name of the request."  
    ::= { mplsTpOAMLoopbackDiscoveryEntry 3 }	                
            
oamDiscoveryStartTTL OBJECT-TYPE
    SYNTAX Integer32 (1..255)
    MAX-ACCESS read-write
    STATUS current
    DESCRIPTION
      "TTL number to start."  
    ::= { mplsTpOAMLoopbackDiscoveryEntry 5 }	        
    
oamDiscoveryEndTTL OBJECT-TYPE
    SYNTAX Integer32 (1..255)
    MAX-ACCESS read-write
    STATUS current
    DESCRIPTION
      "TTL number to end."  
    ::= { mplsTpOAMLoopbackDiscoveryEntry 6 }	            

oamDiscoveryMepIdTlv OBJECT-TYPE
    SYNTAX INTEGER {request(1), no-request(2)}
    MAX-ACCESS read-write
    STATUS current
    DESCRIPTION
      "Whether to request the mepid tlv for the request."  
    DEFVAL { no-request }      
    ::= { mplsTpOAMLoopbackDiscoveryEntry 7 }	        
    
oamDiscoveryDataTlv OBJECT-TYPE
    SYNTAX Integer32 (0..1500)
    MAX-ACCESS read-write
    STATUS current
    DESCRIPTION
      "TTL number to end."  
    DEFVAL { 0 }      
    ::= { mplsTpOAMLoopbackDiscoveryEntry 8 }	  

oamDiscoveryTimeout OBJECT-TYPE
    SYNTAX Integer32 (1..255)
    MAX-ACCESS read-write
    STATUS current
    DESCRIPTION
      "TTL number to end."  
    DEFVAL { 5 }
    ::= { mplsTpOAMLoopbackDiscoveryEntry 9 }	  

oamDiscoveryExp OBJECT-TYPE
    SYNTAX Integer32 (0..7)
    MAX-ACCESS read-write
    STATUS current
    DESCRIPTION
      "MPLS exp."  
    DEFVAL { 7 }
    ::= { mplsTpOAMLoopbackDiscoveryEntry 10 }	  
    
oamDiscoveryTstTlv OBJECT-TYPE
    SYNTAX Integer32 (2..1500)
    MAX-ACCESS read-write
    STATUS current
    DESCRIPTION
      "Send with test TLV."       
    ::= { mplsTpOAMLoopbackDiscoveryEntry 11 }	   

oamDiscoveryTstPattern OBJECT-TYPE
    SYNTAX Integer32 (0..3)
    MAX-ACCESS read-write
    STATUS current
    DESCRIPTION
      "Configure test pattern.
      0  Null signal without CRC-32.
      1  Null signal with CRC-32.
      2  PRBS without CRC-32.
      3  PRBS with CRC-32."       
    ::= { mplsTpOAMLoopbackDiscoveryEntry 12 }	      

    
oamDiscoveryRowstatus OBJECT-TYPE
    SYNTAX  RowStatus
    MAX-ACCESS read-create
    STATUS current
    DESCRIPTION 
    	"The status of this conceptual row.
    	Now only realize CreateAndGo and Destroy and Active."
    ::= { mplsTpOAMLoopbackDiscoveryEntry 15 }         

oamDiscoveryOperState OBJECT-TYPE
    SYNTAX INTEGER { done(1), in-progress(2) }
    MAX-ACCESS read-only
    STATUS current
    DESCRIPTION
      "The operation status."  
    ::= { mplsTpOAMLoopbackDiscoveryEntry 16 }	      
    
oamDiscoveryTimeSpent OBJECT-TYPE
    SYNTAX Integer32
    MAX-ACCESS read-only
    STATUS current
    DESCRIPTION
      "The time spent of the request, in ms."  
    ::= { mplsTpOAMLoopbackDiscoveryEntry 17 }	    

oamDiscoverySuccessRate OBJECT-TYPE
    SYNTAX Integer32
    MAX-ACCESS read-only
    STATUS current
    DESCRIPTION
      "The success rate of the request."  
    ::= { mplsTpOAMLoopbackDiscoveryEntry 18 }	    

mplsTpOAMDiscoveryResultTable OBJECT-TYPE
    SYNTAX  SEQUENCE OF   MplsTpOAMDiscoveryResultEntry
    MAX-ACCESS not-accessible
    STATUS   current
    DESCRIPTION 
    	"Table of mpls-tp discovery result."
    ::= { mpls 61 }
    
mplsTpOAMDiscoveryResultEntry OBJECT-TYPE
    SYNTAX  MplsTpOAMDiscoveryResultEntry
    MAX-ACCESS not-accessible
    STATUS current
    DESCRIPTION 
    	"Entry of mplsTpOAMDiscoveryResultTable."
    INDEX   { oamDiscoveryResultTTL }
    ::= { mplsTpOAMDiscoveryResultTable 1 }

MplsTpOAMDiscoveryResultEntry   ::=
    SEQUENCE {
        oamDiscoveryResultTTL						Integer32,
        oamDiscoveryResultReplyType			INTEGER,
        oamDiscoveryResultMepId    			Integer32,
        oamDiscoveryResultICC						OCTET STRING,
        oamDiscoveryResultNodeId				IpAddress,
        oamDiscoveryResultIfNum					Integer32
        }
        
oamDiscoveryResultTTL OBJECT-TYPE
    SYNTAX Integer32
    MAX-ACCESS not-accessible
    STATUS current
    DESCRIPTION
      "Index of oam discovery loopback state. TTL number"  
    ::= { mplsTpOAMDiscoveryResultEntry 1 }	           
    
oamDiscoveryResultReplyType OBJECT-TYPE
    SYNTAX INTEGER { mip(1), mep(2) }
    MAX-ACCESS read-only
    STATUS current
    DESCRIPTION
      "Service type of the request."  
    ::= { mplsTpOAMDiscoveryResultEntry 2 }	    
            
oamDiscoveryResultMepId OBJECT-TYPE
    SYNTAX Integer32
    MAX-ACCESS read-only
    STATUS current
    DESCRIPTION
      "Service name of the request."  
    ::= { mplsTpOAMDiscoveryResultEntry 3 }	                
            
oamDiscoveryResultICC OBJECT-TYPE
    SYNTAX OCTET STRING
    MAX-ACCESS read-only
    STATUS current
    DESCRIPTION
      "ICC."  
    ::= { mplsTpOAMDiscoveryResultEntry 4 }	  
    
oamDiscoveryResultNodeId OBJECT-TYPE
    SYNTAX IpAddress
    MAX-ACCESS read-only
    STATUS current
    DESCRIPTION
      "MIP node id"  
    ::= { mplsTpOAMDiscoveryResultEntry 5 }	        

oamDiscoveryResultIfNum OBJECT-TYPE
    SYNTAX Integer32
    MAX-ACCESS read-only
    STATUS current
    DESCRIPTION
      "Interface number."  
    ::= { mplsTpOAMDiscoveryResultEntry 6 }	    
        
mplsTpOAMLoopbackRmepTable OBJECT-TYPE
    SYNTAX  SEQUENCE OF   MplsTpOAMLoopbackRmepEntry
    MAX-ACCESS not-accessible
    STATUS   current
    DESCRIPTION 
    	"Table of mpls-tp discovery rmep."
    ::= { mpls 62 }
    
mplsTpOAMLoopbackRmepEntry OBJECT-TYPE
    SYNTAX  MplsTpOAMLoopbackRmepEntry
    MAX-ACCESS not-accessible
    STATUS current
    DESCRIPTION 
    	"Entry of mplsTpOAMLoopbackRmepTable."
    INDEX   { oamRmepIndex }
    ::= { mplsTpOAMLoopbackRmepTable 1 }

MplsTpOAMLoopbackRmepEntry   ::=
    SEQUENCE {
        oamRmepIndex						Integer32,
        oamRmepServiceType			INTEGER,
        oamRmepServiceName			OCTET STRING,
        oamRmepId							Integer32,
        oamRmepMepIdTlv				INTEGER,
        oamRmepDataTlv					Integer32,
        oamRmepTimeout					Integer32,
        oamRmepRepeat					Integer32,
        oamRmepExp							Integer32,        
        oamRmepRowstatus				RowStatus,
        oamRmepOperState				INTEGER,
        oamRmepTimeSpent				Integer32,
        oamRmepSuccessRate			Integer32
        }
        
oamRmepIndex OBJECT-TYPE
    SYNTAX Integer32 (1)
    MAX-ACCESS not-accessible
    STATUS current
    DESCRIPTION
      "Index of oam rmep loopback request.Must be 1."  
    ::= { mplsTpOAMLoopbackRmepEntry 1 }	           
    
oamRmepServiceType OBJECT-TYPE
    SYNTAX INTEGER { section(1), lsp-pe(2), pw-tpe(3)}
    MAX-ACCESS read-write
    STATUS current
    DESCRIPTION
      "Service type of the request."  
    ::= { mplsTpOAMLoopbackRmepEntry 2 }	    
            
oamRmepServiceName OBJECT-TYPE
    SYNTAX OCTET STRING (SIZE (1..20))
    MAX-ACCESS read-write
    STATUS current
    DESCRIPTION
      "Service name of the request."  
    ::= { mplsTpOAMLoopbackRmepEntry 3 }	                
            
oamRmepId OBJECT-TYPE
    SYNTAX Integer32 (1..8191)
    MAX-ACCESS read-write
    STATUS current
    DESCRIPTION
      "Rmep id of the request."  
    ::= { mplsTpOAMLoopbackRmepEntry 5 }	                

oamRmepMepIdTlv OBJECT-TYPE
    SYNTAX INTEGER {request(1), no-request(2)}
    MAX-ACCESS read-write
    STATUS current
    DESCRIPTION
      "Whether to request the mepid tlv for the request."  
    DEFVAL { no-request }      
    ::= { mplsTpOAMLoopbackRmepEntry 6 }	        
    
oamRmepDataTlv OBJECT-TYPE
    SYNTAX Integer32 (0..9000)
    MAX-ACCESS read-write
    STATUS current
    DESCRIPTION
      "TTL number to end."  
    DEFVAL { 0 }      
    ::= { mplsTpOAMLoopbackRmepEntry 7 }	  

oamRmepTimeout OBJECT-TYPE
    SYNTAX Integer32 (1..255)
    MAX-ACCESS read-write
    STATUS current
    DESCRIPTION
      "TTL number to end."  
    DEFVAL { 5 }
    ::= { mplsTpOAMLoopbackRmepEntry 8 }	  

oamRmepRepeat OBJECT-TYPE
    SYNTAX Integer32 (1..255)
    MAX-ACCESS read-write
    STATUS current
    DESCRIPTION
      "Repeat count."  
    DEFVAL { 1 }
    ::= { mplsTpOAMLoopbackRmepEntry 9 }	  

oamRmepExp OBJECT-TYPE
    SYNTAX Integer32 (0..7)
    MAX-ACCESS read-write
    STATUS current
    DESCRIPTION
      "MPLS exp."  
    DEFVAL { 7 }
    ::= { mplsTpOAMLoopbackRmepEntry 10 }	 
        
oamRmepRowstatus OBJECT-TYPE
    SYNTAX  RowStatus
    MAX-ACCESS read-create
    STATUS current
    DESCRIPTION 
    	"The status of this conceptual row.
    	Now only realize CreateAndGo and Destroy and Active."
    ::= { mplsTpOAMLoopbackRmepEntry 15 }         

oamRmepOperState OBJECT-TYPE
    SYNTAX INTEGER { done(1), in-progress(2) }
    MAX-ACCESS read-only
    STATUS current
    DESCRIPTION
      "The operation status."  
    ::= { mplsTpOAMLoopbackRmepEntry 16 }	      
    
oamRmepTimeSpent OBJECT-TYPE
    SYNTAX Integer32
    MAX-ACCESS read-only
    STATUS current
    DESCRIPTION
      "The time spent of the request, in ms."  
    ::= { mplsTpOAMLoopbackRmepEntry 17 }	    

oamRmepSuccessRate OBJECT-TYPE
    SYNTAX Integer32
    MAX-ACCESS read-only
    STATUS current
    DESCRIPTION
      "The success rate of the request."  
    ::= { mplsTpOAMLoopbackRmepEntry 18 }	 

mplsTpOAMLoopbackMipTable OBJECT-TYPE
    SYNTAX  SEQUENCE OF   MplsTpOAMLoopbackMipEntry
    MAX-ACCESS not-accessible
    STATUS   current
    DESCRIPTION 
    	"Table of mpls-tp discovery mip."
    ::= { mpls 64 }
    
mplsTpOAMLoopbackMipEntry OBJECT-TYPE
    SYNTAX  MplsTpOAMLoopbackMipEntry
    MAX-ACCESS not-accessible
    STATUS current
    DESCRIPTION 
    	"Entry of mplsTpOAMLoopbackMipTable."
    INDEX   { oamMipIndex }
    ::= { mplsTpOAMLoopbackMipTable 1 }

MplsTpOAMLoopbackMipEntry   ::=
    SEQUENCE {
        oamMipIndex						Integer32,
        oamMipServiceType			INTEGER,
        oamMipServiceName			OCTET STRING,
        oamMipTTL							Integer32,
        oamMipNodeId					IpAddress,
        oamMipMepIdTlv				INTEGER,
        oamMipDataTlv					Integer32,
        oamMipTimeout					Integer32,          
        oamMipRepeat					Integer32,
        oamMipExp             Integer32,
        oamMipRowstatus				RowStatus,
        oamMipOperState				INTEGER,
        oamMipTimeSpent				Integer32,
        oamMipSuccessRate			Integer32
        }	
    
oamMipIndex OBJECT-TYPE
    SYNTAX Integer32 (1)
    MAX-ACCESS not-accessible
    STATUS current
    DESCRIPTION
      "Index of oam mip loopback request.Must be 1."  
    ::= { mplsTpOAMLoopbackMipEntry 1 }	           
    
oamMipServiceType OBJECT-TYPE
    SYNTAX INTEGER { lsp-pe(2), pw-tpe(3) }
    MAX-ACCESS read-write
    STATUS current
    DESCRIPTION
      "Service type of the request."  
    ::= { mplsTpOAMLoopbackMipEntry 2 }	    
            
oamMipServiceName OBJECT-TYPE
    SYNTAX OCTET STRING (SIZE (1..20))
    MAX-ACCESS read-write
    STATUS current
    DESCRIPTION
      "Service name of the request."  
    ::= { mplsTpOAMLoopbackMipEntry 3 }	                
            
oamMipTTL OBJECT-TYPE
    SYNTAX Integer32 (1..255)
    MAX-ACCESS read-write
    STATUS current
    DESCRIPTION
      "TTL to the target mip."  
    ::= { mplsTpOAMLoopbackMipEntry 5 }
        
oamMipNodeId OBJECT-TYPE
    SYNTAX IpAddress
    MAX-ACCESS read-write
    STATUS current
    DESCRIPTION
      "Mip node id."  
    ::= { mplsTpOAMLoopbackMipEntry 6 }	                

oamMipMepIdTlv OBJECT-TYPE
    SYNTAX INTEGER {request(1), no-request(2)}
    MAX-ACCESS read-write
    STATUS current
    DESCRIPTION
      "Whether to request the mepid tlv for the request."  
    DEFVAL { no-request }      
    ::= { mplsTpOAMLoopbackMipEntry 7 }	        
    
oamMipDataTlv OBJECT-TYPE
    SYNTAX Integer32 (0..9000)
    MAX-ACCESS read-write
    STATUS current
    DESCRIPTION
      "TTL number to end."  
    DEFVAL { 0 }      
    ::= { mplsTpOAMLoopbackMipEntry 8 }	  

oamMipTimeout OBJECT-TYPE
    SYNTAX Integer32 (1..255)
    MAX-ACCESS read-write
    STATUS current
    DESCRIPTION
      "TTL number to end."  
    DEFVAL { 5 }
    ::= { mplsTpOAMLoopbackMipEntry 9 }	  

oamMipRepeat OBJECT-TYPE
    SYNTAX Integer32 (1..255)
    MAX-ACCESS read-write
    STATUS current
    DESCRIPTION
      "Repeat count."  
    DEFVAL { 1 }
    ::= { mplsTpOAMLoopbackMipEntry 10 }	  

oamMipExp OBJECT-TYPE
    SYNTAX Integer32 (0..7)
    MAX-ACCESS read-write
    STATUS current
    DESCRIPTION
      "MPLS exp."  
    DEFVAL { 7 }
    ::= { mplsTpOAMLoopbackMipEntry 11 }
    
oamMipRowstatus OBJECT-TYPE
    SYNTAX  RowStatus
    MAX-ACCESS read-create
    STATUS current
    DESCRIPTION 
    	"The status of this conceptual row.
    	Now only realize CreateAndGo and Destroy and Active."
    ::= { mplsTpOAMLoopbackMipEntry 15 }         

oamMipOperState OBJECT-TYPE
    SYNTAX INTEGER { done(1), in-progress(2) }
    MAX-ACCESS read-only
    STATUS current
    DESCRIPTION
      "The operation status."  
    ::= { mplsTpOAMLoopbackMipEntry 16 }	      
    
oamMipTimeSpent OBJECT-TYPE
    SYNTAX Integer32
    MAX-ACCESS read-only
    STATUS current
    DESCRIPTION
      "The time spent of the request, in ms."  
    ::= { mplsTpOAMLoopbackMipEntry 17 }	    

oamMipSuccessRate OBJECT-TYPE
    SYNTAX Integer32
    MAX-ACCESS read-only
    STATUS current
    DESCRIPTION
      "The success rate of the request."  
    ::= { mplsTpOAMLoopbackMipEntry 18 }	 

mplsTpOAM1dmRequestTable OBJECT-TYPE
    SYNTAX  SEQUENCE OF   MplsTpOAM1dmRequestEntry
    MAX-ACCESS not-accessible
    STATUS   current
    DESCRIPTION 
    	"Table of mpls-tp 1dm request."
    ::= { mpls 65 }
    
mplsTpOAM1dmRequestEntry OBJECT-TYPE
    SYNTAX  MplsTpOAM1dmRequestEntry
    MAX-ACCESS not-accessible
    STATUS current
    DESCRIPTION 
    	"Entry of mplsTpOAM1dmRequestTable."
    INDEX   { oam1dmReqIndex }
    ::= { mplsTpOAM1dmRequestTable 1 }

MplsTpOAM1dmRequestEntry   ::=
    SEQUENCE {
        oam1dmReqIndex						Integer32,
        oam1dmReqServiceType			INTEGER,
        oam1dmReqServiceName			OCTET STRING,
        oam1dmReqRepeat					Integer32,        
        oam1dmReqExp							Integer32,
        oam1dmReqInterval					INTEGER,
        oam1dmReqRowstatus				RowStatus,
        oam1dmReqOperState				INTEGER
        }
        
oam1dmReqIndex OBJECT-TYPE
    SYNTAX Integer32 (1)
    MAX-ACCESS not-accessible
    STATUS current
    DESCRIPTION
      "Index of oam 1dm request.Must be 1."  
    ::= { mplsTpOAM1dmRequestEntry 1 }	           
    
oam1dmReqServiceType OBJECT-TYPE
    SYNTAX INTEGER { section(1), lsp-pe(2), pw-tpe(3) }
    MAX-ACCESS read-write
    STATUS current
    DESCRIPTION
      "Service type of the request."  
    ::= { mplsTpOAM1dmRequestEntry 2 }	    
            
oam1dmReqServiceName OBJECT-TYPE
    SYNTAX OCTET STRING (SIZE (1..20))
    MAX-ACCESS read-write
    STATUS current
    DESCRIPTION
      "Service name of the request."  
    ::= { mplsTpOAM1dmRequestEntry 3 }	                
            
oam1dmReqRepeat OBJECT-TYPE
    SYNTAX Integer32 (1..32)
    MAX-ACCESS read-write
    STATUS current
    DESCRIPTION
      "Config Exp."  
    ::= { mplsTpOAM1dmRequestEntry 5 }
    
oam1dmReqExp OBJECT-TYPE
    SYNTAX Integer32 (0..7)
    MAX-ACCESS read-write
    STATUS current
    DESCRIPTION
      "Config Exp."  
    ::= { mplsTpOAM1dmRequestEntry 6 }
        
oam1dmReqInterval OBJECT-TYPE
    SYNTAX INTEGER         
    {    
        one-hundred-ms(1),
        one-sec(2),
        ten-sec(3)
    }
    MAX-ACCESS read-write
    STATUS current
    DESCRIPTION
      "Config Interval."
    DEFVAL { one-sec }  
    ::= { mplsTpOAM1dmRequestEntry 7 }	                
    
oam1dmReqRowstatus OBJECT-TYPE
    SYNTAX  RowStatus
    MAX-ACCESS read-create
    STATUS current
    DESCRIPTION 
    	"The status of this conceptual row.
    	Now only realize CreateAndGo and Destroy and Active."
    ::= { mplsTpOAM1dmRequestEntry 15 }         

oam1dmReqOperState OBJECT-TYPE
    SYNTAX INTEGER { done(1), in-progress(2) }
    MAX-ACCESS read-only
    STATUS current
    DESCRIPTION
      "The operation status."  
    ::= { mplsTpOAM1dmRequestEntry 16 }	   
       
mplsTpOAMDmmRequestTable OBJECT-TYPE
    SYNTAX  SEQUENCE OF   MplsTpOAMDmmRequestEntry
    MAX-ACCESS not-accessible
    STATUS   current
    DESCRIPTION 
    	"Table of mpls-tp dmm request."
    ::= { mpls 67 }
    
mplsTpOAMDmmRequestEntry OBJECT-TYPE
    SYNTAX  MplsTpOAMDmmRequestEntry
    MAX-ACCESS not-accessible
    STATUS current
    DESCRIPTION 
    	"Entry of mplsTpOAMDmmRequestTable."
    INDEX   { oamDmmReqIndex }
    ::= { mplsTpOAMDmmRequestTable 1 }

MplsTpOAMDmmRequestEntry   ::=
    SEQUENCE {
        oamDmmReqIndex						Integer32,
        oamDmmReqServiceType			INTEGER,
        oamDmmReqServiceName			OCTET STRING,
        oamDmmReqRepeat					Integer32,        
        oamDmmReqExp							Integer32,
        oamDmmReqInterval					INTEGER,
        oamDmmReqRowstatus				RowStatus,
        oamDmmReqOperState				INTEGER,
        oamDmmReqSuccessRate			Integer32,
        oamDmmReqAverDelay				Counter64, 
        oamDmmReqAverVar			        Counter64,               
        oamDmmReqMaxDelay				Counter64,
        oamDmmReqMinDelay 				Counter64                        
        }
        
oamDmmReqIndex OBJECT-TYPE
    SYNTAX Integer32 (1)
    MAX-ACCESS not-accessible
    STATUS current
    DESCRIPTION
      "Index of oam dmm request.Must be 1."  
    ::= { mplsTpOAMDmmRequestEntry 1 }	           
    
oamDmmReqServiceType OBJECT-TYPE
    SYNTAX INTEGER { section(1), lsp-pe(2), pw-tpe(3) }
    MAX-ACCESS read-write
    STATUS current
    DESCRIPTION
      "Service type of the request."  
    ::= { mplsTpOAMDmmRequestEntry 2 }	    
            
oamDmmReqServiceName OBJECT-TYPE
    SYNTAX OCTET STRING (SIZE (1..20))
    MAX-ACCESS read-write
    STATUS current
    DESCRIPTION
      "Service name of the request."  
    ::= { mplsTpOAMDmmRequestEntry 3 }	                
            
oamDmmReqRepeat OBJECT-TYPE
    SYNTAX Integer32 (1..32)
    MAX-ACCESS read-write
    STATUS current
    DESCRIPTION
      "Config Exp."  
    ::= { mplsTpOAMDmmRequestEntry 5 }
    
oamDmmReqExp OBJECT-TYPE
    SYNTAX Integer32 (0..7)
    MAX-ACCESS read-write
    STATUS current
    DESCRIPTION
      "Config Exp."  
    ::= { mplsTpOAMDmmRequestEntry 6 }
        
oamDmmReqInterval OBJECT-TYPE
    SYNTAX INTEGER         
    {    
        one-hundred-ms(1),
        one-sec(2),
        ten-sec(3)
    }
    MAX-ACCESS read-write
    STATUS current
    DESCRIPTION
      "Config Interval."
    DEFVAL { one-sec }  
    ::= { mplsTpOAMDmmRequestEntry 7 }	                
    
oamDmmReqRowstatus OBJECT-TYPE
    SYNTAX  RowStatus
    MAX-ACCESS read-create
    STATUS current
    DESCRIPTION 
    	"The status of this conceptual row.
    	Now only realize CreateAndGo and Destroy and Active."
    ::= { mplsTpOAMDmmRequestEntry 15 }         

oamDmmReqOperState OBJECT-TYPE
    SYNTAX INTEGER { done(1), in-progress(2) }
    MAX-ACCESS read-only
    STATUS current
    DESCRIPTION
      "The operation status."  
    ::= { mplsTpOAMDmmRequestEntry 16 }	   

oamDmmReqSuccessRate OBJECT-TYPE
    SYNTAX Integer32 (1..100)
    MAX-ACCESS read-only
    STATUS current
    DESCRIPTION
      "Success-rate of the operation."  
    ::= { mplsTpOAMDmmRequestEntry 17 }	   
    
oamDmmReqAverDelay OBJECT-TYPE
    SYNTAX Counter64
    MAX-ACCESS read-only
    STATUS current
    DESCRIPTION
      "Average delay."  
    ::= { mplsTpOAMDmmRequestEntry 18 }	   
    
oamDmmReqAverVar OBJECT-TYPE
    SYNTAX Counter64
    MAX-ACCESS read-only
    STATUS current
    DESCRIPTION
      "Average variation."  
    ::= { mplsTpOAMDmmRequestEntry 19 }	        
    
oamDmmReqMaxDelay OBJECT-TYPE
    SYNTAX Counter64
    MAX-ACCESS read-only
    STATUS current
    DESCRIPTION
      "Maximum delay."  
    ::= { mplsTpOAMDmmRequestEntry 20 }	   
    
oamDmmReqMinDelay OBJECT-TYPE
    SYNTAX Counter64
    MAX-ACCESS read-only
    STATUS current
    DESCRIPTION
      "Minimum delay."  
    ::= { mplsTpOAMDmmRequestEntry 21 }	     
    
mplsTpOAMDmmResultTable OBJECT-TYPE
    SYNTAX  SEQUENCE OF MplsTpOAMDmmResultEntry
    MAX-ACCESS not-accessible
    STATUS   current
    DESCRIPTION 
    	"MPLS-TP OAM Dmm Result table."
    ::= { mpls 68 }

mplsTpOAMDmmResultEntry OBJECT-TYPE
    SYNTAX  MplsTpOAMDmmResultEntry
    MAX-ACCESS not-accessible
    STATUS current
    DESCRIPTION 
    	"MPLS-TP Dmm Result entries."
    INDEX   { mplsTpOAMDmmResultIndex }
    ::= { mplsTpOAMDmmResultTable 1 }

MplsTpOAMDmmResultEntry   ::=
    SEQUENCE {
        mplsTpOAMDmmResultIndex			    Integer32,      
        mplsTpOAMDmmResultDelay			    Counter64,
        mplsTpOAMDmmResultVariation     Counter64,
        mplsTpOAMDmmResultExp			      Integer32,          
        mplsTpOAMDmmResultTime          OCTET STRING  
        }

mplsTpOAMDmmResultIndex OBJECT-TYPE
    SYNTAX Integer32
    MAX-ACCESS not-accessible
    STATUS current
    DESCRIPTION
      "Index of the entry."  
    ::= { mplsTpOAMDmmResultEntry 1 }	
    
mplsTpOAMDmmResultDelay OBJECT-TYPE
    SYNTAX Counter64
    MAX-ACCESS read-only
    STATUS current
    DESCRIPTION
      "Delay time."    
    ::= { mplsTpOAMDmmResultEntry 2 }	
    
mplsTpOAMDmmResultVariation OBJECT-TYPE
    SYNTAX Counter64
    MAX-ACCESS read-only
    STATUS current
    DESCRIPTION
      "Variation."    
    ::= { mplsTpOAMDmmResultEntry 3 }	    

mplsTpOAMDmmResultExp OBJECT-TYPE
    SYNTAX Integer32
    MAX-ACCESS read-only
    STATUS current
    DESCRIPTION
      "Action type."    
    ::= { mplsTpOAMDmmResultEntry 4 }	    
    
mplsTpOAMDmmResultTime OBJECT-TYPE
    SYNTAX OCTET STRING
    MAX-ACCESS read-only
    STATUS current
    DESCRIPTION
      "Event time."    
    ::= { mplsTpOAMDmmResultEntry 5 }	               

mplsTpOAMResourceTable OBJECT-TYPE
    SYNTAX  SEQUENCE OF MplsTpOAMResourceEntry
    MAX-ACCESS not-accessible
    STATUS   current
    DESCRIPTION 
    	"MPLS-TP OAM resource table."
    ::= { mpls 70 }

mplsTpOAMResourceEntry OBJECT-TYPE
    SYNTAX  MplsTpOAMResourceEntry
    MAX-ACCESS not-accessible
    STATUS current
    DESCRIPTION 
    	"MPLS-Tp resource rule entries."
    INDEX   { mplsTpOAMResourceId }
    ::= { mplsTpOAMResourceTable 1 }

MplsTpOAMResourceEntry   ::=
    SEQUENCE {
        mplsTpOAMResourceId		      INTEGER,      
        mplsTpOAMResourceMax				Integer32,
        mplsTpOAMResourceCurrent    Integer32       
        }

mplsTpOAMResourceId OBJECT-TYPE
    SYNTAX INTEGER
    {
        section(1),
        meg(2),
        local-mep(3),
        remote-mep(4),
        mip(5),
        csf(6)
    }
    MAX-ACCESS not-accessible
    STATUS current
    DESCRIPTION
      "Resource type."  
    ::= { mplsTpOAMResourceEntry 1 }	

mplsTpOAMResourceMax OBJECT-TYPE
    SYNTAX Integer32
    MAX-ACCESS read-only
    STATUS current
    DESCRIPTION
      "Max resource number."    
    ::= { mplsTpOAMResourceEntry 2 }	

mplsTpOAMResourceCurrent OBJECT-TYPE
    SYNTAX Integer32
    MAX-ACCESS read-only
    STATUS current
    DESCRIPTION
      "Current resource number."    
    ::= { mplsTpOAMResourceEntry 3 }	

mplsTpOAMStatisticTable OBJECT-TYPE
    SYNTAX  SEQUENCE OF MplsTpOAMStatisticEntry
    MAX-ACCESS not-accessible
    STATUS   current
    DESCRIPTION 
    	"MPLS-TP OAM Statistic table."
    ::= { mpls 71 }

mplsTpOAMStatisticEntry OBJECT-TYPE
    SYNTAX  MplsTpOAMStatisticEntry
    MAX-ACCESS not-accessible
    STATUS current
    DESCRIPTION 
    	"MPLS-Tp Statistic rule entries."
    INDEX   { mplsTpOAMStatisticPktType }
    ::= { mplsTpOAMStatisticTable 1 }

MplsTpOAMStatisticEntry   ::=
    SEQUENCE {
        mplsTpOAMStatisticPktType   INTEGER,      
        mplsTpOAMStatisticTx				Integer32,
        mplsTpOAMStatisticRx		    Integer32,
        mplsTpOAMStatisticRxErr	    Integer32          
        }

mplsTpOAMStatisticPktType OBJECT-TYPE
    SYNTAX INTEGER
    {
        lbm(1),
        lbr(2),
        ais(3),
        one-dm(4),
        dmm(5),
        dmr(6),
        unexp-cc(7),
        unknown(8),
        lck(9),
        csf(10),
        aps(11)
    }
    MAX-ACCESS not-accessible
    STATUS current
    DESCRIPTION
      "Statistic type."  
    ::= { mplsTpOAMStatisticEntry 1 }	

mplsTpOAMStatisticTx OBJECT-TYPE
    SYNTAX Integer32
    MAX-ACCESS read-only
    STATUS current
    DESCRIPTION
      "TX packet number."    
    ::= { mplsTpOAMStatisticEntry 2 }	

mplsTpOAMStatisticRx OBJECT-TYPE
    SYNTAX Integer32
    MAX-ACCESS read-only
    STATUS current
    DESCRIPTION
      "RX packet number."    
    ::= { mplsTpOAMStatisticEntry 3 }	

mplsTpOAMStatisticRxErr OBJECT-TYPE
    SYNTAX Integer32
    MAX-ACCESS read-only
    STATUS current
    DESCRIPTION
      "RX error packet number."    
    ::= { mplsTpOAMStatisticEntry 4 }	

mplsTpOAMEventTable OBJECT-TYPE
    SYNTAX  SEQUENCE OF MplsTpOAMEventEntry
    MAX-ACCESS not-accessible
    STATUS   current
    DESCRIPTION 
    	"MPLS-TP OAM Event table."
    ::= { mpls 72 }

mplsTpOAMEventEntry OBJECT-TYPE
    SYNTAX  MplsTpOAMEventEntry
    MAX-ACCESS not-accessible
    STATUS current
    DESCRIPTION 
    	"MPLS-TP Event entries."
    INDEX   { mplsTpOAMEventIndex }
    ::= { mplsTpOAMEventTable 1 }

MplsTpOAMEventEntry   ::=
    SEQUENCE {
        mplsTpOAMEventIndex			    Integer32,      
        mplsTpOAMEventService				INTEGER,
        mplsTpOAMEventMegId		    	OCTET STRING,
        mplsTpOAMEventMepId		    	Integer32,        
        mplsTpOAMEventId				    INTEGER,
        mplsTpOAMEventAction		    INTEGER,        
        mplsTpOAMEventTime          OCTET STRING  
        }

mplsTpOAMEventIndex OBJECT-TYPE
    SYNTAX Integer32
    MAX-ACCESS not-accessible
    STATUS current
    DESCRIPTION
      "Event index."  
    ::= { mplsTpOAMEventEntry 1 }	

mplsTpOAMEventService OBJECT-TYPE
    SYNTAX INTEGER
    {
        section(1),
        lsp(2),
        pw-tpe(3)
    }
    MAX-ACCESS read-only
    STATUS current
    DESCRIPTION
      "Service type of the event."    
    ::= { mplsTpOAMEventEntry 2 }	

mplsTpOAMEventMegId OBJECT-TYPE
    SYNTAX OCTET STRING
    MAX-ACCESS read-only
    STATUS current
    DESCRIPTION
      "MEG ID."    
    ::= { mplsTpOAMEventEntry 3 }	

mplsTpOAMEventMepId OBJECT-TYPE
    SYNTAX Integer32
    MAX-ACCESS read-only
    STATUS current
    DESCRIPTION
      "MEP ID."    
    ::= { mplsTpOAMEventEntry 4 }	
    
mplsTpOAMEventId OBJECT-TYPE
    SYNTAX INTEGER
    {
        loc(1),
        unExpRMepId(2),
        unExpInterval(3),
        unExpMegId(4),
        unExpLevel(5),
        rdiRx(6),
        rdiTx(7),
        waitFistCCM(8),
        aisRx(9),
        aisTx(10),
        aisDefect(11),        
        eventFull(12),
        oneDmFull(13),
        lockRx(14),
        lockTx(15),
        lockDefect(16),
        crcDefect(17)        
    }
    MAX-ACCESS read-only
    STATUS current
    DESCRIPTION
      "Event type."    
    ::= { mplsTpOAMEventEntry 5 }	    

mplsTpOAMEventAction OBJECT-TYPE
    SYNTAX INTEGER
    {
        occur(1),
        clear(2)        
    }
    MAX-ACCESS read-only
    STATUS current
    DESCRIPTION
      "Action type."    
    ::= { mplsTpOAMEventEntry 6 }	    
    
mplsTpOAMEventTime OBJECT-TYPE
    SYNTAX OCTET STRING
    MAX-ACCESS read-only
    STATUS current
    DESCRIPTION
      "Event time."    
    ::= { mplsTpOAMEventEntry 7 }	    

mplsTpOAM1dmTable OBJECT-TYPE
    SYNTAX  SEQUENCE OF MplsTpOAM1dmEntry
    MAX-ACCESS not-accessible
    STATUS   current
    DESCRIPTION 
    	"MPLS-TP OAM 1dm table."
    ::= { mpls 73 }

mplsTpOAM1dmEntry OBJECT-TYPE
    SYNTAX  MplsTpOAM1dmEntry
    MAX-ACCESS not-accessible
    STATUS current
    DESCRIPTION 
    	"MPLS-TP 1dm entries."
    INDEX   { mplsTpOAM1dmMegId, mplsTpOAM1dmIndex }
    ::= { mplsTpOAM1dmTable 1 }

MplsTpOAM1dmEntry   ::=
    SEQUENCE {
        mplsTpOAM1dmMegId		    	OCTET STRING,
        mplsTpOAM1dmIndex			    Integer32,      
        mplsTpOAM1dmService				INTEGER,
        mplsTpOAM1dmMepId		    	Integer32,        
        mplsTpOAM1dmDelay			    Counter64,
        mplsTpOAM1dmVariation     Counter64,
        mplsTpOAM1dmExp			      Integer32,          
        mplsTpOAM1dmTime          OCTET STRING  
        }

mplsTpOAM1dmMegId OBJECT-TYPE
    SYNTAX OCTET STRING
    MAX-ACCESS not-accessible
    STATUS current
    DESCRIPTION
      "MEG ID."    
    ::= { mplsTpOAM1dmEntry 1 }	

mplsTpOAM1dmIndex OBJECT-TYPE
    SYNTAX Integer32
    MAX-ACCESS not-accessible
    STATUS current
    DESCRIPTION
      "Index of the entry."  
    ::= { mplsTpOAM1dmEntry 2 }	
        
mplsTpOAM1dmService OBJECT-TYPE
    SYNTAX INTEGER
    {
        section(1),
        lsp(2),
        pw-tpe(3)
    }
    MAX-ACCESS read-only
    STATUS current
    DESCRIPTION
      "Service type of the data."    
    ::= { mplsTpOAM1dmEntry 3 }	

mplsTpOAM1dmMepId OBJECT-TYPE
    SYNTAX Integer32
    MAX-ACCESS read-only
    STATUS current
    DESCRIPTION
      "MEP ID."    
    ::= { mplsTpOAM1dmEntry 4 }	
    
mplsTpOAM1dmDelay OBJECT-TYPE
    SYNTAX Counter64
    MAX-ACCESS read-only
    STATUS current
    DESCRIPTION
      "Delay time."    
    ::= { mplsTpOAM1dmEntry 5 }	
    
mplsTpOAM1dmVariation OBJECT-TYPE
    SYNTAX Counter64
    MAX-ACCESS read-only
    STATUS current
    DESCRIPTION
      "Variation."    
    ::= { mplsTpOAM1dmEntry 6 }	    

mplsTpOAM1dmExp OBJECT-TYPE
    SYNTAX Integer32
    MAX-ACCESS read-only
    STATUS current
    DESCRIPTION
      "Action type."    
    ::= { mplsTpOAM1dmEntry 7 }	    
    
mplsTpOAM1dmTime OBJECT-TYPE
    SYNTAX OCTET STRING
    MAX-ACCESS read-only
    STATUS current
    DESCRIPTION
      "Event time."    
    ::= { mplsTpOAM1dmEntry 8 }	        
    
mplsTpOAM1dmStatisticTable OBJECT-TYPE
    SYNTAX  SEQUENCE OF MplsTpOAM1dmStatisticEntry
    MAX-ACCESS not-accessible
    STATUS   current
    DESCRIPTION 
    	"MPLS-TP OAM 1dm statistic table."
    ::= { mpls 74 }

mplsTpOAM1dmStatisticEntry OBJECT-TYPE
    SYNTAX  MplsTpOAM1dmStatisticEntry
    MAX-ACCESS not-accessible
    STATUS current
    DESCRIPTION 
    	"MPLS-TP 1dm statistic entries."
    INDEX   { mplsTpOAM1dmStatMegId }
    ::= { mplsTpOAM1dmStatisticTable 1 }

MplsTpOAM1dmStatisticEntry   ::=
    SEQUENCE {
        mplsTpOAM1dmStatMegId		    	OCTET STRING,
        mplsTpOAM1dmStatMinDelay    	Counter64,        
        mplsTpOAM1dmStatMaxDelay	    Counter64,
        mplsTpOAM1dmStatAverDelay     Counter64,
        mplsTpOAM1dmStatAverVariation	Counter64
        }

mplsTpOAM1dmStatMegId OBJECT-TYPE
    SYNTAX OCTET STRING (SIZE (1..12))
    MAX-ACCESS not-accessible
    STATUS current
    DESCRIPTION
      "MEG ID."    
    ::= { mplsTpOAM1dmStatisticEntry 1 }	

mplsTpOAM1dmStatMinDelay OBJECT-TYPE
    SYNTAX Counter64
    MAX-ACCESS read-only
    STATUS current
    DESCRIPTION
      "Minimum delay time."    
    ::= { mplsTpOAM1dmStatisticEntry 2 }	 
    
mplsTpOAM1dmStatMaxDelay OBJECT-TYPE
    SYNTAX Counter64
    MAX-ACCESS read-only
    STATUS current
    DESCRIPTION
      "Maximum delay time."    
    ::= { mplsTpOAM1dmStatisticEntry 3 }	 

mplsTpOAM1dmStatAverDelay OBJECT-TYPE
    SYNTAX Counter64
    MAX-ACCESS read-only
    STATUS current
    DESCRIPTION
      "Average delay time."    
    ::= { mplsTpOAM1dmStatisticEntry 4 }	             

mplsTpOAM1dmStatAverVariation OBJECT-TYPE
    SYNTAX Counter64
    MAX-ACCESS read-only
    STATUS current
    DESCRIPTION
      "Average variation."    
    ::= { mplsTpOAM1dmStatisticEntry 5 }	     

mplsTpOAMMPStatisticTable OBJECT-TYPE
    SYNTAX  SEQUENCE OF MplsTpOAMMPStatisticEntry
    MAX-ACCESS not-accessible
    STATUS   current
    DESCRIPTION 
    	"MPLS-TP OAM MEP and MIP Statistic table."
    ::= { mpls 75 }

mplsTpOAMMPStatisticEntry OBJECT-TYPE
    SYNTAX  MplsTpOAMMPStatisticEntry
    MAX-ACCESS not-accessible
    STATUS current
    DESCRIPTION 
    	"MPLS-Tp MP Statistic entries."
    INDEX   { mplsTpOAMMPStatMegId, mplsTpOAMMPStatPktType }
    ::= { mplsTpOAMMPStatisticTable 1 }

MplsTpOAMMPStatisticEntry   ::=
    SEQUENCE {
        mplsTpOAMMPStatMegId				OCTET STRING,
        mplsTpOAMMPStatPktType   		INTEGER,      
        mplsTpOAMMPStatTx						Counter64,
        mplsTpOAMMPStatRx		   		  Counter64,
        mplsTpOAMMPStatRxErr	      Counter64          
        }
        
mplsTpOAMMPStatMegId OBJECT-TYPE
    SYNTAX OCTET STRING (SIZE (1..12))
    MAX-ACCESS not-accessible
    STATUS current
    DESCRIPTION
      "MEG ID."    
    ::= { mplsTpOAMMPStatisticEntry 1 }	
    
mplsTpOAMMPStatPktType OBJECT-TYPE
    SYNTAX INTEGER
    {
        lbm(1),
        lbr(2),
        ais(3),
        one-dm(4),
        dmm(5),
        dmr(6),
        unexp-cc(7),
        unknown(8),
        lck(9),
        csf(10),
        aps(11)        
    }
    MAX-ACCESS not-accessible
    STATUS current
    DESCRIPTION
      "Packet type."  
    ::= { mplsTpOAMMPStatisticEntry 2 }	
    
mplsTpOAMMPStatTx OBJECT-TYPE
    SYNTAX Counter64
    MAX-ACCESS read-only
    STATUS current
    DESCRIPTION
      "Tx packet number."    
    ::= { mplsTpOAMMPStatisticEntry 3 }	 
    
mplsTpOAMMPStatRx OBJECT-TYPE
    SYNTAX Counter64
    MAX-ACCESS read-only
    STATUS current
    DESCRIPTION
      "Rx packet number."    
    ::= { mplsTpOAMMPStatisticEntry 4 }	 
    
mplsTpOAMMPStatRxErr OBJECT-TYPE
    SYNTAX Counter64
    MAX-ACCESS read-only
    STATUS current
    DESCRIPTION
      "Rx error packet number."    
    ::= { mplsTpOAMMPStatisticEntry 5 }	 

mplsTpOAMMepEventDefectTable OBJECT-TYPE
    SYNTAX  SEQUENCE OF MplsTpOAMMepEventDefectEntry
    MAX-ACCESS not-accessible
    STATUS   current
    DESCRIPTION 
    	"MPLS-TP OAM MEP event defect table."
    ::= { mpls 76 }

mplsTpOAMMepEventDefectEntry OBJECT-TYPE
    SYNTAX  MplsTpOAMMepEventDefectEntry
    MAX-ACCESS not-accessible
    STATUS current
    DESCRIPTION 
    	"MPLS-Tp MEP event defect entries."
    INDEX   { mplsTpOAMMepEvtMegId, mplsTpOAMMepEvtId }
    ::= { mplsTpOAMMepEventDefectTable 1 }

MplsTpOAMMepEventDefectEntry   ::=
    SEQUENCE {
        mplsTpOAMMepEvtMegId				OCTET STRING,
        mplsTpOAMMepEvtId   		    INTEGER,      
        mplsTpOAMMepEvtDefect				INTEGER    
        }
        
mplsTpOAMMepEvtMegId OBJECT-TYPE
    SYNTAX OCTET STRING (SIZE (1..12))
    MAX-ACCESS not-accessible
    STATUS current
    DESCRIPTION
      "MEG ID."    
    ::= { mplsTpOAMMepEventDefectEntry 1 }	
    
mplsTpOAMMepEvtId OBJECT-TYPE
    SYNTAX INTEGER
    {
        loc(1),
        unExpRMepId(2),
        unExpInterval(3),
        unExpMegId(4),
        unExpLevel(5),
        rdiRx(6),
        rdiTx(7),
        waitFistCCM(8),
        aisRx(9),
        aisTx(10),
        aisDefect(11),        
        eventFull(12),
        oneDmFull(13),
        lockRx(14),
        lockTx(15),
        lockDefect(16),
        crcDefect(17)        
    }
    MAX-ACCESS not-accessible
    STATUS current
    DESCRIPTION
      "Event type."  
    ::= { mplsTpOAMMepEventDefectEntry 2 }	
    
mplsTpOAMMepEvtDefect OBJECT-TYPE
    SYNTAX INTEGER { yes(1), no(2) }
    MAX-ACCESS read-only
    STATUS current
    DESCRIPTION
      "Event status."    
    ::= { mplsTpOAMMepEventDefectEntry 3 }	 

mplsTPVpwsOAMCsfTable OBJECT-TYPE
    SYNTAX  SEQUENCE OF MplsTPVpwsOAMCsfEntry
    MAX-ACCESS not-accessible
    STATUS   current
    DESCRIPTION 
    	"Display OAM csf status of an MPLS Layer-2 Virtual Circuit."
    ::= { mpls 77 }

mplsTPVpwsOAMCsfEntry OBJECT-TYPE
    SYNTAX  MplsTPVpwsOAMCsfEntry
    MAX-ACCESS not-accessible
    STATUS current
    DESCRIPTION 
    	"Entry of mplsTPVpwsOAMCsfTable."
    INDEX   { mplsTPVpwsOAMCsfVcId}
    ::= { mplsTPVpwsOAMCsfTable 1 }

MplsTPVpwsOAMCsfEntry   ::=
    SEQUENCE {
        mplsTPVpwsOAMCsfVcId         				Integer32,
        mplsTPVpwsOAMCsfSrvState				INTEGER,
        mplsTPVpwsOAMCsfClientState                             INTEGER,
        mplsTPVpwsOAMCsfDCReason                                INTEGER,
        mplsTPVpwsOAMCsfClientInterval                          Integer32,
        mplsTPVpwsOAMCsfACDownEn                                INTEGER,
        mplsTPVpwsOAMCsfACStatus                                INTEGER,
        mplsTPVpwsOAMCsfTxCSFPacket                             INTEGER
        }

mplsTPVpwsOAMCsfVcId OBJECT-TYPE
    SYNTAX  Integer32(1..424967295)
    MAX-ACCESS not-accessible
    STATUS current
    DESCRIPTION 
    	"Identifying value for MPLS Layer-2 Virtual Circuit."
    ::= { mplsTPVpwsOAMCsfEntry 1 }
    
mplsTPVpwsOAMCsfSrvState OBJECT-TYPE
    SYNTAX INTEGER { los(0), fdi(1), rdi(2), ok(3), init(4) }
    MAX-ACCESS read-only
    STATUS current
    DESCRIPTION
      "Csf Local AC state."  
    ::= { mplsTPVpwsOAMCsfEntry 2 }   

mplsTPVpwsOAMCsfClientState OBJECT-TYPE
    SYNTAX INTEGER { los(0), fdi(1), rdi(2), dc(3), init(4) }
    MAX-ACCESS read-only
    STATUS current
    DESCRIPTION
      "Csf Remote AC state."  
    ::= { mplsTPVpwsOAMCsfEntry 3 } 

mplsTPVpwsOAMCsfDCReason OBJECT-TYPE
    SYNTAX INTEGER { init(0), timeout(1), dci(2), invalid(3) }
    MAX-ACCESS read-only
    STATUS current
    DESCRIPTION
      "Csf DC reason."  
    ::= { mplsTPVpwsOAMCsfEntry 4 } 

mplsTPVpwsOAMCsfClientInterval OBJECT-TYPE
    SYNTAX Integer32 (0|1|60)
    MAX-ACCESS read-only
    STATUS current
    DESCRIPTION
      "Interval of CSF client PDU, 0 is invalid."  
    ::= { mplsTPVpwsOAMCsfEntry 5 } 

mplsTPVpwsOAMCsfACDownEn OBJECT-TYPE
    SYNTAX INTEGER { disable(0), down(1)}
    MAX-ACCESS read-only
    STATUS current
    DESCRIPTION
      "When receive csf packet, set AC port down. 1 is set AC port to down."  
    ::= { mplsTPVpwsOAMCsfEntry 6 } 

mplsTPVpwsOAMCsfACStatus OBJECT-TYPE
    SYNTAX INTEGER { up(0), down(1), admin-down(2), errdisable(3), csf-ac-down(4), absent(5) }
    MAX-ACCESS read-only
    STATUS current
    DESCRIPTION
      "The AC interface status."  
    ::= { mplsTPVpwsOAMCsfEntry 7 }

mplsTPVpwsOAMCsfTxCSFPacket OBJECT-TYPE
    SYNTAX INTEGER { yes(1), no(2) }
    MAX-ACCESS read-only
    STATUS current
    DESCRIPTION
      "TX CSF packet status."  
    ::= { mplsTPVpwsOAMCsfEntry 8 }
            
mplsVplsDynamicFdbTable OBJECT-TYPE
    SYNTAX  SEQUENCE OF MplsVplsDynamicFdbEntry
    MAX-ACCESS not-accessible
    STATUS   current
    DESCRIPTION 
    	"Vpls dynamic fdb table."
    ::= { mpls 78 }

mplsVplsDynamicFdbEntry OBJECT-TYPE
    SYNTAX  MplsVplsDynamicFdbEntry
    MAX-ACCESS not-accessible
    STATUS current
    DESCRIPTION 
    	"VPLS dynamic fdb entries."
    INDEX   { mplsVplsDynamicFdbVplsId, mplsVplsDynamicFdbMacAddr}
    ::= { mplsVplsDynamicFdbTable 1 }

MplsVplsDynamicFdbEntry   ::=
    SEQUENCE {
        mplsVplsDynamicFdbVplsId    	Integer32,
        mplsVplsDynamicFdbMacAddr 	MacAddress,
        mplsVplsDynamicFdbIfName 	OCTET STRING,
        mplsVplsDynamicFdbPeerIp 	IpAddress,
        mplsVplsDynamicFdbTPPeerName    OCTET STRING
        }

mplsVplsDynamicFdbVplsId OBJECT-TYPE
    SYNTAX  Integer32 (1..2147483647)
    MAX-ACCESS not-accessible
    STATUS current
    DESCRIPTION 
    	"Identifying value for VPLS."
    ::= { mplsVplsDynamicFdbEntry 1 }
        
mplsVplsDynamicFdbMacAddr OBJECT-TYPE
    SYNTAX  MacAddress
    MAX-ACCESS not-accessible
    STATUS current
    DESCRIPTION 
    	"Mac address of the fdb entry."
    ::= { mplsVplsDynamicFdbEntry 2 }
    
mplsVplsDynamicFdbIfName OBJECT-TYPE
    SYNTAX  OCTET STRING(SIZE(0..16))
    MAX-ACCESS read-only
    STATUS current
    DESCRIPTION 
    	"Out-going interface of the VPLS fdb entry."
    ::= { mplsVplsDynamicFdbEntry 3 }
    
mplsVplsDynamicFdbPeerIp OBJECT-TYPE
    SYNTAX  IpAddress
    MAX-ACCESS read-only
    STATUS current
    DESCRIPTION 
    	"Out-going peer IPV4 address of the VPLS fdb entry."
    ::= { mplsVplsDynamicFdbEntry 4 }
    
mplsVplsDynamicFdbTPPeerName OBJECT-TYPE
    SYNTAX  OCTET STRING(SIZE(1..20))
    MAX-ACCESS read-only
    STATUS current
    DESCRIPTION 
    	"Out-going tp-peer of the VPLS fdb entry."
    ::= { mplsVplsDynamicFdbEntry 5 }    

mplsGlobal OBJECT IDENTIFIER    ::= { mpls 79 }
mplsGlobalCurrentStaticLabelBlockNum OBJECT-TYPE
    SYNTAX          INTEGER (1..8192)
    MAX-ACCESS      read-only
    STATUS          current
    DESCRIPTION
        "Get current static label block number."
    ::= { mplsGlobal 1 }            

mplsGlobalCurrentDynamicLabelBlockNum OBJECT-TYPE
    SYNTAX          Integer32 (0..8192)
    MAX-ACCESS      read-only
    STATUS          current
    DESCRIPTION
        "Get current dynamic label block number."
    ::= { mplsGlobal 2 }

mplsGlobalConfigStaticLabelBlockNum OBJECT-TYPE
    SYNTAX          Integer32 (1..8192)
    MAX-ACCESS      read-write
    STATUS          current
    DESCRIPTION
        "Get static label block number configured for next reboot, 
         configure static label block number for next reboot."
    ::= { mplsGlobal 3 }
    



mplsVplsIgspGlbInfo OBJECT IDENTIFIER ::= { mpls 80 }

mplsVplsIgspGlbInfoMaxMemNum  OBJECT-TYPE
    SYNTAX          Integer32 (1..16384)
    MAX-ACCESS      read-write
    STATUS          current
    DESCRIPTION
        "Vpls IGMP Snooping Max Member Number."
    DEFVAL          { 16384 }
    ::= { mplsVplsIgspGlbInfo 1 }

mplsVplsIgspGlbInfoQuerierTcnCnt  OBJECT-TYPE
    SYNTAX          Integer32 (1..10)
    MAX-ACCESS      read-write
    STATUS          current
    DESCRIPTION
        "Vpls IGMP querier TCN query count."
    DEFVAL          { 2 }
    ::= { mplsVplsIgspGlbInfo 2 }

mplsVplsIgspGlbInfoQuerierTcnInterval  OBJECT-TYPE
    SYNTAX          Integer32 (1..255)
    MAX-ACCESS      read-write
    STATUS          current
    DESCRIPTION
        "Vpls IGMP querier TCN query interval."
    DEFVAL          { 10 }
    ::= { mplsVplsIgspGlbInfo 3 }

mplsVplsIgspGlbInfoCurrMemNum  OBJECT-TYPE
    SYNTAX          Integer32 (0..65535)
    MAX-ACCESS      read-only
    STATUS          current
    DESCRIPTION
        "Vpls IGMP snooping current member number."
    DEFVAL          { 0 }
    ::= { mplsVplsIgspGlbInfo 4 }




mplsVplsIgspCfgTable OBJECT-TYPE
    SYNTAX          SEQUENCE OF MplsVplsIgspCfgEntry
    MAX-ACCESS      not-accessible
    STATUS          current
    DESCRIPTION
        "Vpls igmp snooping config table."
    ::= { mpls 81 }

mplsVplsIgspCfgEntry OBJECT-TYPE
    SYNTAX          MplsVplsIgspCfgEntry
    MAX-ACCESS      not-accessible
    STATUS          current
    DESCRIPTION
        "Entry of mplsVplsIgspCfgTable."
    INDEX    { mplsVplsIgspVplsId }
    ::= { mplsVplsIgspCfgTable 1 }
    
MplsVplsIgspCfgEntry     ::= 
    SEQUENCE {
        mplsVplsIgspVplsId
            Integer32,
        mplsVplsIgspStatus
            INTEGER,
        mplsVplsIgspFastLeave
            INTEGER,
        mplsVplsIgspVersion
            Integer32,
        mplsVplsIgspMaxMemNum
            Integer32,
        mplsVplsIgspReportSuppr
            INTEGER,
        mplsVplsIgspLastMemQueryCnt
            Integer32,
        mplsVplsIgspLastMemQueryInteval
            Integer32,
        mplsVplsIgspRobuVari
            Integer32,
        mplsVplsIgspAccessGroup
            OCTET STRING,
        mplsVplsIgspQuerierStatus
            INTEGER,
        mplsVplsIgspQuerierTimeout
            Integer32,
        mplsVplsIgspQuerierAdd
            IpAddress,
        mplsVplsIgspQueryInterval
            Integer32,
        mplsVplsIgspQueryMaxResponTime
            Integer32,
        mplsVplsIgspElectedQuerier
            IpAddress,
        mplsVplsIgspQueryOperationalState
            INTEGER,
        mplsVplsIgspBundingCtrlVlan
            Integer32
    }

mplsVplsIgspVplsId  OBJECT-TYPE
    SYNTAX          Integer32 (1..2147483647)
    MAX-ACCESS      not-accessible
    STATUS          current
    DESCRIPTION
        "Identifying value for VPLS."
    DEFVAL          { 0 }
    ::= { mplsVplsIgspCfgEntry 1 }

mplsVplsIgspStatus  OBJECT-TYPE
    SYNTAX          INTEGER
    {enable(1),disable(2)}
    MAX-ACCESS      read-write
    STATUS          current
    DESCRIPTION
        "Configure to enable or disable VPLS IGMP Snooping."
    ::= { mplsVplsIgspCfgEntry 2 }

mplsVplsIgspFastLeave  OBJECT-TYPE
    SYNTAX          INTEGER
    {enable(1),disable(2)}
    MAX-ACCESS      read-write
    STATUS          current
    DESCRIPTION
        "Configure to enable VPLS IGMP Snooping Fast Leave."
    ::= { mplsVplsIgspCfgEntry 3 }

mplsVplsIgspVersion  OBJECT-TYPE
    SYNTAX          Integer32 (1..3)
    MAX-ACCESS      read-write
    STATUS          current
    DESCRIPTION
        "Configure to set VPLS IGMP Snooping Version."
    DEFVAL          { 2 }
    ::= { mplsVplsIgspCfgEntry 4 }

mplsVplsIgspMaxMemNum  OBJECT-TYPE
    SYNTAX          Integer32 (1..16384)
    MAX-ACCESS      read-write
    STATUS          current
    DESCRIPTION
        "VPLS IGMP Snooping Max Member Number."
    DEFVAL          { 16384 }
    ::= { mplsVplsIgspCfgEntry 5 }

mplsVplsIgspReportSuppr  OBJECT-TYPE
    SYNTAX          INTEGER
    {enable(1),disable(2)}
    MAX-ACCESS      read-write
    STATUS          current
    DESCRIPTION
        "VPLS IGMPv1/V2 Report Suppression."
    ::= { mplsVplsIgspCfgEntry 6 }

mplsVplsIgspLastMemQueryCnt  OBJECT-TYPE
    SYNTAX          Integer32 (2..7)
    MAX-ACCESS      read-write
    STATUS          current
    DESCRIPTION
        "Last Member Query Count value."
    DEFVAL          { 2 }
    ::= { mplsVplsIgspCfgEntry 7 }

mplsVplsIgspLastMemQueryInteval  OBJECT-TYPE
    SYNTAX          Integer32 (1000..25500)
    MAX-ACCESS      read-write
    STATUS          current
    DESCRIPTION
        "Last Member Query Interval value."
    DEFVAL          { 1000 }
    ::= { mplsVplsIgspCfgEntry 8 }

mplsVplsIgspRobuVari  OBJECT-TYPE
    SYNTAX          Integer32 (2..7)
    MAX-ACCESS      read-write
    STATUS          current
    DESCRIPTION
        "Robustness Variable value."
    DEFVAL          { 2 }
    ::= { mplsVplsIgspCfgEntry 9 }

mplsVplsIgspAccessGroup  OBJECT-TYPE
    SYNTAX          OCTET STRING  (SIZE (1..20))
    MAX-ACCESS      read-write
    STATUS          current
    DESCRIPTION
        "IP Named Standard Access list."
    ::= { mplsVplsIgspCfgEntry 10 }

mplsVplsIgspQuerierStatus  OBJECT-TYPE
    SYNTAX          INTEGER
    {enable(1),disable(2)}
    MAX-ACCESS      read-write
    STATUS          current
    DESCRIPTION
        "Configure to enable Vpls IGMP Snooping Query."
    ::= { mplsVplsIgspCfgEntry 11 }

mplsVplsIgspQuerierTimeout  OBJECT-TYPE
    SYNTAX          Integer32 (60..300)
    MAX-ACCESS      read-write
    STATUS          current
    DESCRIPTION
        "Vpls IGMP previous querier timeout value."
    DEFVAL          { 255 }
    ::= { mplsVplsIgspCfgEntry 12 }

mplsVplsIgspQuerierAdd  OBJECT-TYPE
    SYNTAX          IpAddress
    MAX-ACCESS      read-write
    STATUS          current
    DESCRIPTION
        "Vpls IGMP Querier IP Address."
    ::= { mplsVplsIgspCfgEntry 13 }

mplsVplsIgspQueryInterval  OBJECT-TYPE
    SYNTAX          Integer32 (2..18000)
    MAX-ACCESS      read-write
    STATUS          current
    DESCRIPTION
        "VPLS Igmp snooping Query Interval value."
    DEFVAL          { 125 }
    ::= { mplsVplsIgspCfgEntry 14 }

mplsVplsIgspQueryMaxResponTime  OBJECT-TYPE
    SYNTAX          Integer32 (1..25)
    MAX-ACCESS      read-write
    STATUS          current
    DESCRIPTION
        "VPLS IGMP Max Query Response Time."
    DEFVAL          { 10 }
    ::= { mplsVplsIgspCfgEntry 15 }

mplsVplsIgspElectedQuerier  OBJECT-TYPE
    SYNTAX          IpAddress
    MAX-ACCESS      read-only
    STATUS          current
    DESCRIPTION
        "Vpls IGMP Elected Querier IP Address."
    ::= { mplsVplsIgspCfgEntry 16 }

mplsVplsIgspQueryOperationalState  OBJECT-TYPE
    SYNTAX          INTEGER
    {querier(1), non-querier(2)}
    MAX-ACCESS      read-only
    STATUS          current
    DESCRIPTION
        "VPLS IGMP Querier Operational State."
    ::= { mplsVplsIgspCfgEntry 17 }

mplsVplsIgspBundingCtrlVlan  OBJECT-TYPE
    SYNTAX          Integer32 (0..4094)
    MAX-ACCESS      read-write
    STATUS          current
    DESCRIPTION
        "Configure to set VPLS IGMP Snooping Bunding Control Vlan.
         Set 0 means bundling-control-vlan untag."
    DEFVAL          { 1 }
    ::= { mplsVplsIgspCfgEntry 18 }

mplsVplsIgspMrouterIfTable OBJECT-TYPE
    SYNTAX          SEQUENCE OF MplsVplsIgspMrouterIfEntry
    MAX-ACCESS      not-accessible
    STATUS          current
    DESCRIPTION
        "The Vpls IGMP snooping Multicast Router Interface table."
    ::= { mpls 82 }

mplsVplsIgspMrouterIfEntry OBJECT-TYPE
    SYNTAX          MplsVplsIgspMrouterIfEntry
    MAX-ACCESS      not-accessible
    STATUS          current
    DESCRIPTION
        "Entry of mplsVplsIgspMrouterIfTable."
    INDEX    { mplsVplsIgspMrouterIfVplsId , mplsVplsIgspMrouterIfIndex }
    ::= { mplsVplsIgspMrouterIfTable 1 }
    
MplsVplsIgspMrouterIfEntry     ::= 
    SEQUENCE {
        mplsVplsIgspMrouterIfVplsId
            Integer32,
        mplsVplsIgspMrouterIfIndex
            Integer32,
        mplsVplsIgspMrouterIfRowstatus
            RowStatus
    }

mplsVplsIgspMrouterIfVplsId  OBJECT-TYPE
    SYNTAX          Integer32 (1..2147483647)
    MAX-ACCESS      not-accessible
    STATUS          current
    DESCRIPTION
        "Identifying value for VPLS."
    ::= { mplsVplsIgspMrouterIfEntry 1 }
    
mplsVplsIgspMrouterIfIndex  OBJECT-TYPE
    SYNTAX          Integer32 (1..65535)
    MAX-ACCESS      not-accessible
    STATUS          current
    DESCRIPTION
        "Index of interface."
    ::= { mplsVplsIgspMrouterIfEntry 2 }

mplsVplsIgspMrouterIfRowstatus  OBJECT-TYPE
    SYNTAX          RowStatus 
    MAX-ACCESS      read-create
    STATUS          current
    DESCRIPTION
        "The status of the conceptual row. Now only realize CreateAndGo(4)
        and Destroy(6) and Active(1)."
    ::= { mplsVplsIgspMrouterIfEntry 10 }


mplsVplsMrouterPeerTable OBJECT-TYPE
    SYNTAX          SEQUENCE OF MplsVplsMrouterPeerEntry
    MAX-ACCESS      not-accessible
    STATUS          current
    DESCRIPTION
        "MPLS-TP VPLS peer Multicast Router Table."
    ::= { mpls 83 }

mplsVplsMrouterPeerEntry OBJECT-TYPE
    SYNTAX          MplsVplsMrouterPeerEntry
    MAX-ACCESS      not-accessible
    STATUS          current
    DESCRIPTION
        "Entry of mplsVplsMrouterPeerTable."
    INDEX    { mplsVplsMrouterPeerVplsId , mplsVplsMrouterPeer }
    ::= { mplsVplsMrouterPeerTable 1 }
    
MplsVplsMrouterPeerEntry     ::= 
    SEQUENCE {
        mplsVplsMrouterPeerVplsId
            Integer32,
        mplsVplsMrouterPeer
            OCTET STRING,
        mplsVplsMrouterPeerRowstatus
            RowStatus
    }

mplsVplsMrouterPeerVplsId  OBJECT-TYPE
    SYNTAX          Integer32 (1..2147483647)
    MAX-ACCESS      not-accessible
    STATUS          current
    DESCRIPTION
        "Identifying value for VPLS."
    ::= { mplsVplsMrouterPeerEntry 1 }

mplsVplsMrouterPeer  OBJECT-TYPE
    SYNTAX          OCTET STRING  (SIZE (1..20))
    MAX-ACCESS      not-accessible
    STATUS          current
    DESCRIPTION
        "Identifying string for VPLS peer."
    ::= { mplsVplsMrouterPeerEntry 2 }

mplsVplsMrouterPeerRowstatus  OBJECT-TYPE
    SYNTAX          RowStatus 
    MAX-ACCESS      read-create
    STATUS          current
    DESCRIPTION
        "The status of the conceptual row. Now only realize CreateAndGo(4)
        and Destroy(6) and Active(1)."
    ::= { mplsVplsMrouterPeerEntry 10 }

mplsVplsIgspSgIfTable OBJECT-TYPE
    SYNTAX          SEQUENCE OF MplsVplsIgspSgIfEntry
    MAX-ACCESS      not-accessible
    STATUS          current
    DESCRIPTION
        "Vpls igmp snooping Static Group Interface Table."
    ::= { mpls 84 }

mplsVplsIgspSgIfEntry OBJECT-TYPE
    SYNTAX          MplsVplsIgspSgIfEntry
    MAX-ACCESS      not-accessible
    STATUS          current
    DESCRIPTION
        "Entry of mplsVplsIgspStaticGroupIfTable"
    INDEX    { mplsVplsIgspSgIfVplsId ,
               mplsVplsIgspSgIfMadd ,
               mplsVplsIgspSgIfIndex,
               mplsVplsIgspSgIfSourceAdd }
    ::= { mplsVplsIgspSgIfTable 1 }
    
MplsVplsIgspSgIfEntry     ::= 
    SEQUENCE {
        mplsVplsIgspSgIfVplsId
            Integer32,
        mplsVplsIgspSgIfMadd
            IpAddress,
        mplsVplsIgspSgIfIndex
            Integer32,
        mplsVplsIgspSgIfSourceAdd
            IpAddress,
        mplsVplsIgspSgIfRowstatus
            RowStatus
    }

mplsVplsIgspSgIfVplsId  OBJECT-TYPE
    SYNTAX          Integer32 (1..4294967295)
    MAX-ACCESS      not-accessible
    STATUS          current
    DESCRIPTION
        "Identifying value for VPLS."
    ::= { mplsVplsIgspSgIfEntry 1 }

mplsVplsIgspSgIfMadd  OBJECT-TYPE
    SYNTAX          IpAddress
    MAX-ACCESS      not-accessible
    STATUS          current
    DESCRIPTION
        "Multicast Address to be Joined Static Group."
    ::= { mplsVplsIgspSgIfEntry 2 }

mplsVplsIgspSgIfIndex  OBJECT-TYPE
    SYNTAX          Integer32 (1..65535)
    MAX-ACCESS      not-accessible
    STATUS          current
    DESCRIPTION
        "Index of interface."
    ::= { mplsVplsIgspSgIfEntry 3 }

mplsVplsIgspSgIfSourceAdd  OBJECT-TYPE
    SYNTAX          IpAddress
    MAX-ACCESS      not-accessible
    STATUS          current
    DESCRIPTION
        "Static Source to be Joined Static Group."
    ::= { mplsVplsIgspSgIfEntry 4 }

mplsVplsIgspSgIfRowstatus  OBJECT-TYPE
    SYNTAX          RowStatus 
    MAX-ACCESS      read-create
    STATUS          current
    DESCRIPTION
        "The status of the conceptual row. Now only realize CreateAndGo(4)
        and Destroy(6) and Active(1)."
    ::= { mplsVplsIgspSgIfEntry 10 }


mplsVplsIgspSgPeerTable OBJECT-TYPE
    SYNTAX          SEQUENCE OF MplsVplsIgspSgPeerEntry
    MAX-ACCESS      not-accessible
    STATUS          current
    DESCRIPTION
        "Igsp Static Group Table of MPLS-TP VPLS peer."
    ::= { mpls 85 }

mplsVplsIgspSgPeerEntry OBJECT-TYPE
    SYNTAX          MplsVplsIgspSgPeerEntry
    MAX-ACCESS      not-accessible
    STATUS          current
    DESCRIPTION
        "Entry of mplsVplsIgspStaticGroupPeerTable."
    INDEX    { mplsVplsIgspSgPeerVplsId ,
               mplsVplsIgspSgPeerMadd ,
               mplsVplsIgspSgPeer,
               mplsVplsIgspSgPeerSourceAdd}
    ::= { mplsVplsIgspSgPeerTable 1 }
    
MplsVplsIgspSgPeerEntry     ::= 
    SEQUENCE {
        mplsVplsIgspSgPeerVplsId
            Integer32,
        mplsVplsIgspSgPeerMadd
            IpAddress,
        mplsVplsIgspSgPeer
            OCTET STRING,
        mplsVplsIgspSgPeerSourceAdd
            IpAddress,
        mplsVplsIgspSgPeerRowstatus
            RowStatus
    }

mplsVplsIgspSgPeerVplsId  OBJECT-TYPE
    SYNTAX          Integer32 (1..4294967295)
    MAX-ACCESS      not-accessible
    STATUS          current
    DESCRIPTION
        "Identifying value for VPLS."
    ::= { mplsVplsIgspSgPeerEntry 1 }

mplsVplsIgspSgPeerMadd  OBJECT-TYPE
    SYNTAX          IpAddress
    MAX-ACCESS      not-accessible
    STATUS          current
    DESCRIPTION
        "Multicast Address to be Joined Static Group."
    ::= { mplsVplsIgspSgPeerEntry 2 }

mplsVplsIgspSgPeer  OBJECT-TYPE
    SYNTAX          OCTET STRING  (SIZE (1..20))
    MAX-ACCESS      not-accessible
    STATUS          current
    DESCRIPTION
        "Identifying string for VPLS peer."
    ::= { mplsVplsIgspSgPeerEntry 3 }

mplsVplsIgspSgPeerSourceAdd  OBJECT-TYPE
    SYNTAX          IpAddress
    MAX-ACCESS      not-accessible
    STATUS          current
    DESCRIPTION
        "Static Source to be Joined Static Group."
    ::= { mplsVplsIgspSgPeerEntry 4 }

mplsVplsIgspSgPeerRowstatus  OBJECT-TYPE
    SYNTAX          RowStatus 
    MAX-ACCESS      read-create
    STATUS          current
    DESCRIPTION
        "The status of the conceptual row. Now only realize CreateAndGo(4)
        and Destroy(6) and Active(1)."
    ::= { mplsVplsIgspSgPeerEntry 10 }

mplsVplsIgspMaxGrpMemIfTable OBJECT-TYPE
    SYNTAX          SEQUENCE OF MplsVplsIgspMaxGrpMemIfEntry
    MAX-ACCESS      not-accessible
    STATUS          current
    DESCRIPTION
        "The Vpls IGMP snooping Max Group Member Interface table."
    ::= { mpls 86 }

mplsVplsIgspMaxGrpMemIfEntry OBJECT-TYPE
    SYNTAX          MplsVplsIgspMaxGrpMemIfEntry
    MAX-ACCESS      not-accessible
    STATUS          current
    DESCRIPTION
        "Entry of mplsVplsIgspMaxGrpMemIfTable."
    INDEX    { mplsVplsIgspMaxGrpMemIfVplsId , mplsVplsIgspMaxGrpMemIfIndex }
    ::= { mplsVplsIgspMaxGrpMemIfTable 1 }
    
MplsVplsIgspMaxGrpMemIfEntry     ::= 
    SEQUENCE {
        mplsVplsIgspMaxGrpMemIfVplsId
            Integer32,
        mplsVplsIgspMaxGrpMemIfIndex
            Integer32,
        mplsVplsIgspIfMaxGrpMemNum
            Integer32,
        mplsVplsIgspMaxGrpMemIfRowstatus
            RowStatus,
        mplsVplsIgspIfMaxGrpMemCount
            Integer32   
    }

mplsVplsIgspMaxGrpMemIfVplsId  OBJECT-TYPE
    SYNTAX          Integer32 (1..2147483647)
    MAX-ACCESS      not-accessible
    STATUS          current
    DESCRIPTION
        "Identifying value for VPLS."
    ::= { mplsVplsIgspMaxGrpMemIfEntry 1 }
    
mplsVplsIgspMaxGrpMemIfIndex  OBJECT-TYPE
    SYNTAX          Integer32 (1..65535)
    MAX-ACCESS      not-accessible
    STATUS          current
    DESCRIPTION
        "Index of interface."
    ::= { mplsVplsIgspMaxGrpMemIfEntry 2 }
    
mplsVplsIgspIfMaxGrpMemNum  OBJECT-TYPE
    SYNTAX          Integer32 (0..16384)
    MAX-ACCESS      read-create
    STATUS          current
    DESCRIPTION
        "IGMP Snooping Max Allowed Group Number on this interface."
    ::= { mplsVplsIgspMaxGrpMemIfEntry 3 }

mplsVplsIgspMaxGrpMemIfRowstatus  OBJECT-TYPE
    SYNTAX          RowStatus 
    MAX-ACCESS      read-create
    STATUS          current
    DESCRIPTION
        "The status of the conceptual row. Now only realize CreateAndGo(4)
        and Destroy(6) and Active(1)."
    ::= { mplsVplsIgspMaxGrpMemIfEntry 10 }

mplsVplsIgspIfMaxGrpMemCount  OBJECT-TYPE
    SYNTAX          Integer32
    MAX-ACCESS      read-only
    STATUS          current
    DESCRIPTION
        "IGMP Snooping Max Group Number Count on this interface."
    ::= { mplsVplsIgspMaxGrpMemIfEntry 11 }

mplsVplsMaxGrpMemPeerTable OBJECT-TYPE
    SYNTAX          SEQUENCE OF MplsVplsMaxGrpMemPeerEntry
    MAX-ACCESS      not-accessible
    STATUS          current
    DESCRIPTION
        "MPLS-TP VPLS peer Multicast Router Table."
    ::= { mpls 87 }

mplsVplsMaxGrpMemPeerEntry OBJECT-TYPE
    SYNTAX          MplsVplsMaxGrpMemPeerEntry
    MAX-ACCESS      not-accessible
    STATUS          current
    DESCRIPTION
        "Entry of mplsVplsMaxGrpMemPeerTable."
    INDEX    { mplsVplsMaxGrpMemPeerVplsId , mplsVplsMaxGrpMemPeer }
    ::= { mplsVplsMaxGrpMemPeerTable 1 }
    
MplsVplsMaxGrpMemPeerEntry     ::= 
    SEQUENCE {
        mplsVplsMaxGrpMemPeerVplsId
            Integer32,
        mplsVplsMaxGrpMemPeer
            OCTET STRING,
        mplsVplsPeerMaxGrpMemNum
            Integer32,
        mplsVplsMaxGrpMemPeerRowstatus
            RowStatus,
        mplsVplsPeerMaxGrpMemCount
            Integer32
    }

mplsVplsMaxGrpMemPeerVplsId  OBJECT-TYPE
    SYNTAX          Integer32 (1..2147483647)
    MAX-ACCESS      not-accessible
    STATUS          current
    DESCRIPTION
        "Identifying value for VPLS."
    ::= { mplsVplsMaxGrpMemPeerEntry 1 }

mplsVplsMaxGrpMemPeer  OBJECT-TYPE
    SYNTAX          OCTET STRING  (SIZE (1..20))
    MAX-ACCESS      not-accessible
    STATUS          current
    DESCRIPTION
        "Identifying string for VPLS peer."
    ::= { mplsVplsMaxGrpMemPeerEntry 2 }

mplsVplsPeerMaxGrpMemNum  OBJECT-TYPE
    SYNTAX          Integer32 (0..16384)
    MAX-ACCESS      read-create
    STATUS          current
    DESCRIPTION
        "IGMP Snooping Max Allowed Group Number on this peer."
    ::= { mplsVplsMaxGrpMemPeerEntry 3 }

mplsVplsMaxGrpMemPeerRowstatus  OBJECT-TYPE
    SYNTAX          RowStatus 
    MAX-ACCESS      read-create
    STATUS          current
    DESCRIPTION
        "The status of the conceptual row. Now only realize CreateAndGo(4)
        and Destroy(6) and Active(1)."
    ::= { mplsVplsMaxGrpMemPeerEntry 10 }

mplsVplsPeerMaxGrpMemCount  OBJECT-TYPE
    SYNTAX          Integer32
    MAX-ACCESS      read-only
    STATUS          current
    DESCRIPTION
        "IGMP Snooping Max Group Number Count on this peer."
    ::= { mplsVplsMaxGrpMemPeerEntry 11 }
    
mplsVplsShowMrouterIfTable OBJECT-TYPE
    SYNTAX          SEQUENCE OF MplsVplsShowMrouterIfEntry
    MAX-ACCESS      not-accessible
    STATUS          current
    DESCRIPTION
        "The Vpls IGMP snooping Multicast Router Show Interface table."
    ::= { mpls 88 }

mplsVplsShowMrouterIfEntry OBJECT-TYPE
    SYNTAX          MplsVplsShowMrouterIfEntry
    MAX-ACCESS      not-accessible
    STATUS          current
    DESCRIPTION
        "Entry of mplsVplsShowMrouterIfTable."
    INDEX    { mplsVplsShowMrouterIfVplsId , mplsVplsShowMrouterIfIndex }
    ::= { mplsVplsShowMrouterIfTable 1 }
    
MplsVplsShowMrouterIfEntry     ::= 
    SEQUENCE {
        mplsVplsShowMrouterIfVplsId
            Integer32,
        mplsVplsShowMrouterIfIndex
            Integer32,
        mplsVplsShowMrouterIfName
            OCTET STRING,
        mplsVplsShowMrouterIfMode
            INTEGER,
        mplsVplsShowMrouterIfUptime
            OCTET STRING,
        mplsVplsShowMrouterIfExprietime
            OCTET STRING   
    }

mplsVplsShowMrouterIfVplsId  OBJECT-TYPE
    SYNTAX          Integer32 (1..2147483647)
    MAX-ACCESS      not-accessible
    STATUS          current
    DESCRIPTION
        "Identifying value for VPLS."
    ::= { mplsVplsShowMrouterIfEntry 1 }
    
mplsVplsShowMrouterIfIndex  OBJECT-TYPE
    SYNTAX          Integer32 (1..65535)
    MAX-ACCESS      not-accessible
    STATUS          current
    DESCRIPTION
        "Index of interface."
    ::= { mplsVplsShowMrouterIfEntry 2 }

mplsVplsShowMrouterIfName  OBJECT-TYPE
    SYNTAX          OCTET STRING  (SIZE (1..20)) 
    MAX-ACCESS      read-only
    STATUS          current
    DESCRIPTION
        "The Name of Interface."
    ::= { mplsVplsShowMrouterIfEntry 3 }

mplsVplsShowMrouterIfMode  OBJECT-TYPE
    SYNTAX          INTEGER
    {static(1), dynamic(2), both(3)}
    MAX-ACCESS      read-only
    STATUS          current
    DESCRIPTION
        "The Mode of VPLS Igmp Snooping Mrouter on this Interface."
    ::= { mplsVplsShowMrouterIfEntry 4 }
    
mplsVplsShowMrouterIfUptime  OBJECT-TYPE
    SYNTAX          OCTET STRING  (SIZE (1..27)) 
    MAX-ACCESS      read-only
    STATUS          current
    DESCRIPTION
        "The Uptime of VPLS Igmp Snooping Mrouter on this Interface."
    ::= { mplsVplsShowMrouterIfEntry 5 }

mplsVplsShowMrouterIfExprietime  OBJECT-TYPE
    SYNTAX          OCTET STRING  (SIZE (1..27)) 
    MAX-ACCESS      read-only
    STATUS          current
    DESCRIPTION
        "The Exprietime of VPLS Igmp Snooping Mrouter on this Interface."
    ::= { mplsVplsShowMrouterIfEntry 6 }

mplsVplsShowMrouterPeerTable OBJECT-TYPE
    SYNTAX          SEQUENCE OF MplsVplsShowMrouterPeerEntry
    MAX-ACCESS      not-accessible
    STATUS          current
    DESCRIPTION
        "The Vpls IGMP snooping Multicast Router Show Peer Table."
    ::= { mpls 89 }

mplsVplsShowMrouterPeerEntry OBJECT-TYPE
    SYNTAX          MplsVplsShowMrouterPeerEntry
    MAX-ACCESS      not-accessible
    STATUS          current
    DESCRIPTION
        "Entry of mplsVplsShowMrouterPeerTable."
    INDEX    { mplsVplsShowMrouterPeerVplsId , mplsVplsShowMrouterPeer }
    ::= { mplsVplsShowMrouterPeerTable 1 }
    
MplsVplsShowMrouterPeerEntry     ::= 
    SEQUENCE {
        mplsVplsShowMrouterPeerVplsId
            Integer32,
        mplsVplsShowMrouterPeer
            OCTET STRING,
        mplsVplsShowMrouterPeerName
            OCTET STRING,
        mplsVplsShowMrouterPeerMode
            INTEGER,
        mplsVplsShowMrouterPeerUptime
            OCTET STRING,
        mplsVplsShowMrouterPeerExprietime
            OCTET STRING
    }

mplsVplsShowMrouterPeerVplsId  OBJECT-TYPE
    SYNTAX          Integer32 (1..2147483647)
    MAX-ACCESS      not-accessible
    STATUS          current
    DESCRIPTION
        "Identifying value for VPLS."
    ::= { mplsVplsShowMrouterPeerEntry 1 }

mplsVplsShowMrouterPeer  OBJECT-TYPE
    SYNTAX          OCTET STRING  (SIZE (1..20))
    MAX-ACCESS      not-accessible
    STATUS          current
    DESCRIPTION
        "Identifying string for VPLS peer."
    ::= { mplsVplsShowMrouterPeerEntry 2 }

mplsVplsShowMrouterPeerName  OBJECT-TYPE
    SYNTAX          OCTET STRING  (SIZE (1..20)) 
    MAX-ACCESS      read-only
    STATUS          current
    DESCRIPTION
        "The Name of peer."
    ::= { mplsVplsShowMrouterPeerEntry 3 }

mplsVplsShowMrouterPeerMode  OBJECT-TYPE
    SYNTAX          INTEGER
    {static(1), dynamic(2), both(3)}
    MAX-ACCESS      read-only
    STATUS          current
    DESCRIPTION
        "The Mode of VPLS Igmp Snooping Mrouter on this peer."
    ::= { mplsVplsShowMrouterPeerEntry 4 }
    
mplsVplsShowMrouterPeerUptime  OBJECT-TYPE
    SYNTAX          OCTET STRING  (SIZE (1..27)) 
    MAX-ACCESS      read-only
    STATUS          current
    DESCRIPTION
        "The Uptime of VPLS Igmp Snooping Mrouter on this peer."
    ::= { mplsVplsShowMrouterPeerEntry 5 }

mplsVplsShowMrouterPeerExprietime  OBJECT-TYPE
    SYNTAX          OCTET STRING  (SIZE (1..27)) 
    MAX-ACCESS      read-only
    STATUS          current
    DESCRIPTION
        "The Exprietime of VPLS Igmp Snooping Mrouter on this peer."
    ::= { mplsVplsShowMrouterPeerEntry 6 }

mplsVplsShowGroupIfTable OBJECT-TYPE
    SYNTAX          SEQUENCE OF MplsVplsShowGroupIfEntry
    MAX-ACCESS      not-accessible
    STATUS          current
    DESCRIPTION
        "The Vpls IGMP snooping Show Groups Interface table."
    ::= { mpls 90 }

mplsVplsShowGroupIfEntry OBJECT-TYPE
    SYNTAX          MplsVplsShowGroupIfEntry
    MAX-ACCESS      not-accessible
    STATUS          current
    DESCRIPTION
        "Entry of mplsVplsShowGroupIfTable."
    INDEX    { mplsVplsShowGroupIfVplsId , mplsVplsShowGroupIfIndex ,mplsVplsShowGroupIfAddr}
    ::= { mplsVplsShowGroupIfTable 1 }
    
MplsVplsShowGroupIfEntry     ::= 
    SEQUENCE {
        mplsVplsShowGroupIfVplsId
            Integer32,
        mplsVplsShowGroupIfIndex
            Integer32,
        mplsVplsShowGroupIfAddr
            IpAddress,
        mplsVplsShowGroupIfName
            OCTET STRING,
        mplsVplsShowGroupIfUptime
            OCTET STRING,
        mplsVplsShowGroupIfExprietime
            OCTET STRING,
        mplsVplsShowGroupIfLastReporter
            IpAddress           
    }

mplsVplsShowGroupIfVplsId  OBJECT-TYPE
    SYNTAX          Integer32 (1..2147483647)
    MAX-ACCESS      not-accessible
    STATUS          current
    DESCRIPTION
        "Identifying value for VPLS."
    ::= { mplsVplsShowGroupIfEntry 1 }
    
mplsVplsShowGroupIfIndex  OBJECT-TYPE
    SYNTAX          Integer32 (1..65535)
    MAX-ACCESS      not-accessible
    STATUS          current
    DESCRIPTION
        "Index of interface."
    ::= { mplsVplsShowGroupIfEntry 2 }

mplsVplsShowGroupIfAddr  OBJECT-TYPE
    SYNTAX          IpAddress
    MAX-ACCESS      not-accessible
    STATUS          current
    DESCRIPTION
        "The Group Address of VPLS Igmp Snooping Group on this Interface."
    ::= { mplsVplsShowGroupIfEntry 3 }
    
mplsVplsShowGroupIfName  OBJECT-TYPE
    SYNTAX          OCTET STRING  (SIZE (1..20)) 
    MAX-ACCESS      read-only
    STATUS          current
    DESCRIPTION
        "The Name of Interface."
    ::= { mplsVplsShowGroupIfEntry 4 }
   
mplsVplsShowGroupIfUptime  OBJECT-TYPE
    SYNTAX          OCTET STRING  (SIZE (1..27)) 
    MAX-ACCESS      read-only
    STATUS          current
    DESCRIPTION
        "The Uptime of VPLS Igmp Snooping Group on this Interface."
    ::= { mplsVplsShowGroupIfEntry 5 }
    
mplsVplsShowGroupIfExprietime  OBJECT-TYPE
    SYNTAX          OCTET STRING  (SIZE (1..27)) 
    MAX-ACCESS      read-only
    STATUS          current
    DESCRIPTION
        "The Exprietime of VPLS Igmp Snooping Group on this Interface."
    ::= { mplsVplsShowGroupIfEntry 6 }
    
mplsVplsShowGroupIfLastReporter  OBJECT-TYPE
    SYNTAX          IpAddress
    MAX-ACCESS      read-only
    STATUS          current
    DESCRIPTION
        "The Address of VPLS Igmp Snooping Group Last Reporter on this Interface."
    ::= { mplsVplsShowGroupIfEntry 7 }


mplsVplsShowGroupPeerTable OBJECT-TYPE
    SYNTAX          SEQUENCE OF MplsVplsShowGroupPeerEntry
    MAX-ACCESS      not-accessible
    STATUS          current
    DESCRIPTION
        "The Vpls IGMP snooping Show Group Peer Table."
    ::= { mpls 91 }

mplsVplsShowGroupPeerEntry OBJECT-TYPE
    SYNTAX          MplsVplsShowGroupPeerEntry
    MAX-ACCESS      not-accessible
    STATUS          current
    DESCRIPTION
        "Entry of mplsVplsShowGroupPeerTable."
    INDEX    { mplsVplsShowGroupPeerVplsId , mplsVplsShowGroupPeer ,mplsVplsShowGroupPeerAddr }
    ::= { mplsVplsShowGroupPeerTable 1 }
    
MplsVplsShowGroupPeerEntry     ::= 
    SEQUENCE {
        mplsVplsShowGroupPeerVplsId
            Integer32,
        mplsVplsShowGroupPeer
            OCTET STRING,
        mplsVplsShowGroupPeerAddr
            IpAddress,
        mplsVplsShowGroupPeerName
            OCTET STRING,
        mplsVplsShowGroupPeerUptime
            OCTET STRING,
        mplsVplsShowGroupPeerExprietime
            OCTET STRING,
        mplsVplsShowGroupPeerLastReporter
            IpAddress  
    }

mplsVplsShowGroupPeerVplsId  OBJECT-TYPE
    SYNTAX          Integer32 (1..2147483647)
    MAX-ACCESS      not-accessible
    STATUS          current
    DESCRIPTION
        "Identifying value for VPLS."
    ::= { mplsVplsShowGroupPeerEntry 1 }

mplsVplsShowGroupPeer  OBJECT-TYPE
    SYNTAX          OCTET STRING  (SIZE (1..20))
    MAX-ACCESS      not-accessible
    STATUS          current
    DESCRIPTION
        "Identifying string for VPLS peer."
    ::= { mplsVplsShowGroupPeerEntry 2 }

mplsVplsShowGroupPeerAddr  OBJECT-TYPE
    SYNTAX          IpAddress
    MAX-ACCESS      not-accessible
    STATUS          current
    DESCRIPTION
        "The Group Address of VPLS Igmp Snooping Group on this peer."
    ::= { mplsVplsShowGroupPeerEntry 3 }

mplsVplsShowGroupPeerName  OBJECT-TYPE
    SYNTAX          OCTET STRING  (SIZE (1..20)) 
    MAX-ACCESS      read-only
    STATUS          current
    DESCRIPTION
        "The Name of peer."
    ::= { mplsVplsShowGroupPeerEntry 4 }
    
mplsVplsShowGroupPeerUptime  OBJECT-TYPE
    SYNTAX          OCTET STRING  (SIZE (1..27)) 
    MAX-ACCESS      read-only
    STATUS          current
    DESCRIPTION
        "The Uptime of VPLS Igmp Snooping Group on this peer."
    ::= { mplsVplsShowGroupPeerEntry 5 }

mplsVplsShowGroupPeerExprietime  OBJECT-TYPE
    SYNTAX          OCTET STRING  (SIZE (1..27)) 
    MAX-ACCESS      read-only
    STATUS          current
    DESCRIPTION
        "The Exprietime of VPLS Igmp Snooping Group on this peer."
    ::= { mplsVplsShowGroupPeerEntry 6 }

mplsVplsShowGroupPeerLastReporter  OBJECT-TYPE
    SYNTAX          IpAddress
    MAX-ACCESS      read-only
    STATUS          current
    DESCRIPTION
        "The Address of VPLS Igmp Snooping Group Last Reporter on this peer."
    ::= { mplsVplsShowGroupPeerEntry 7 }

----mpls interface vpws policy-map table
 mplsInterfaceMplsVpwsPolicyTable OBJECT-TYPE
    SYNTAX  SEQUENCE OF MplsInterfaceMplsVpwsPolicyEntry
    MAX-ACCESS not-accessible
    STATUS   current
    DESCRIPTION 
    	"One MPLS layer-2 virtual circuit can only band to one interface,
    	but one interface may be banded to many VCs."
    ::= { mpls 92 }

 mplsInterfaceMplsVpwsPolicyEntry OBJECT-TYPE
    SYNTAX  MplsInterfaceMplsVpwsPolicyEntry
    MAX-ACCESS not-accessible
    STATUS current
    DESCRIPTION 
    	"Entry of mplsInterfaceMplsVpwsPolicyTable."
    INDEX   { mplsInterfaceMplsVpwsPolicyIfIndex}
    ::= { mplsInterfaceMplsVpwsPolicyTable 1 }

MplsInterfaceMplsVpwsPolicyEntry   ::=
    SEQUENCE {
        mplsInterfaceMplsVpwsPolicyIfIndex   Integer32,
        mplsInterfaceMplsVpwsPolicyVcName 	OCTET STRING,
        mplsInterfaceMplsVpwsPolicyName   	OCTET STRING,
        mplsInterfaceMplsVpwsPolicyStatis		INTEGER,        
        mplsInterfaceMplsVpwsPolicyRowStatus	RowStatus
        }

mplsInterfaceMplsVpwsPolicyIfIndex OBJECT-TYPE
    SYNTAX  Integer32 (1..48)
    MAX-ACCESS not-accessible
    STATUS current
    DESCRIPTION 
    	"Interface index."
    ::= { mplsInterfaceMplsVpwsPolicyEntry 1 }

mplsInterfaceMplsVpwsPolicyVcName OBJECT-TYPE
    SYNTAX  OCTET STRING (SIZE(1..20))
    MAX-ACCESS not-accessible
    STATUS current
    DESCRIPTION 
    	"Identifying string for MPLS layer-2 virtual circuit."
    ::= { mplsInterfaceMplsVpwsPolicyEntry 2 }	

mplsInterfaceMplsVpwsPolicyName OBJECT-TYPE
    SYNTAX  OCTET STRING (SIZE(1..20))
    MAX-ACCESS not-accessible
    STATUS current
    DESCRIPTION 
    	"Policy map name."
    ::= { mplsInterfaceMplsVpwsPolicyEntry 3 }

mplsInterfaceMplsVpwsPolicyStatis OBJECT-TYPE
    SYNTAX  INTEGER {enable(1), disable(2)}
    MAX-ACCESS read-create
    STATUS current
    DESCRIPTION 
    	"State of bundling."
    DEFVAL { disable }
    ::= { mplsInterfaceMplsVpwsPolicyEntry 4 } 
    
mplsInterfaceMplsVpwsPolicyRowStatus OBJECT-TYPE
    SYNTAX  RowStatus
    MAX-ACCESS read-create
    STATUS current
    DESCRIPTION 
    	"The status of this conceptual row.Now only realize CreateAndGo 
            and Destroy and Active."
    ::= { mplsInterfaceMplsVpwsPolicyEntry 10 }
	
mplsTpOAMLmmTable OBJECT-TYPE
    SYNTAX  SEQUENCE OF   MplsTpOAMLmmEntry
    MAX-ACCESS not-accessible
    STATUS   current
    DESCRIPTION 
    	"Table of mpls-tp Single-ended loss measurment message."
    ::= { mpls 93 }
    
mplsTpOAMLmmEntry OBJECT-TYPE
    SYNTAX  MplsTpOAMLmmEntry
    MAX-ACCESS not-accessible
    STATUS current
    DESCRIPTION 
    	"Entry of mplsTpOAMLmmTable."
    INDEX   { oamLmmIndex }
    ::= { mplsTpOAMLmmTable 1 }

MplsTpOAMLmmEntry   ::=
    SEQUENCE {
        oamLmmIndex					Integer32,
        oamLmmServiceType		  	INTEGER,
        oamLmmServiceName			OCTET STRING,
        oamLmmRepeat				Integer32,
        oamLmmInterval				INTEGER,
        oamLmmRowstatus				RowStatus
        }	
    
oamLmmIndex OBJECT-TYPE
    SYNTAX Integer32 (1)
    MAX-ACCESS not-accessible
    STATUS current
    DESCRIPTION
      "Index of oam Single-ended loss measurment message.Must be 1."  
    ::= { mplsTpOAMLmmEntry 1 }	           
    
oamLmmServiceType OBJECT-TYPE
    SYNTAX INTEGER { section(1), lsp-pe(2), pw-tpe(3) }
    MAX-ACCESS read-write
    STATUS current
    DESCRIPTION
      "Service type of the message."  
    ::= { mplsTpOAMLmmEntry 2 }	    
            
oamLmmServiceName OBJECT-TYPE
    SYNTAX OCTET STRING (SIZE (1..20))
    MAX-ACCESS read-write
    STATUS current
    DESCRIPTION
      "Service name of the message."  
    ::= { mplsTpOAMLmmEntry 3 }	                
            
oamLmmRepeat OBJECT-TYPE
    SYNTAX Integer32 (1..255)
    MAX-ACCESS read-write
    STATUS current
    DESCRIPTION
      "Repeat count value to Single-ended loss measurment message."  
    ::= { mplsTpOAMLmmEntry 4 }                      

oamLmmInterval OBJECT-TYPE
    SYNTAX INTEGER {one-hundred-ms(1), one-sec(2), ten-sec(3)}
    MAX-ACCESS read-write
    STATUS current
    DESCRIPTION
      "LMM transmission interval."  
    DEFVAL { one-sec }      
    ::= { mplsTpOAMLmmEntry 5 }	        
    
oamLmmRowstatus OBJECT-TYPE
    SYNTAX  RowStatus
    MAX-ACCESS read-create
    STATUS current
    DESCRIPTION 
    	"The status of this conceptual row.
    	Now only realize CreateAndGo and Destroy and Active."
    ::= { mplsTpOAMLmmEntry 15 }    

mplsTpOAMLmDualTable OBJECT-TYPE
    SYNTAX  SEQUENCE OF MplsTpOAMLmDualEntry
    MAX-ACCESS not-accessible
    STATUS   current
    DESCRIPTION 
    	"MPLS-TP OAM LmDual table."
    ::= { mpls 94 }

mplsTpOAMLmDualEntry OBJECT-TYPE
    SYNTAX  MplsTpOAMLmDualEntry
    MAX-ACCESS not-accessible
    STATUS current
    DESCRIPTION 
    	"MPLS-TP LmDual entries."
    INDEX   { mplsTpOAMLmDualMegId, mplsTpOAMLmDualIndex }
    ::= { mplsTpOAMLmDualTable 1 }

MplsTpOAMLmDualEntry   ::=
    SEQUENCE {
        mplsTpOAMLmDualMegId		    	OCTET STRING,
        mplsTpOAMLmDualIndex			    Integer32,      
        mplsTpOAMLmDualService				INTEGER,
        mplsTpOAMLmDualMepId		    	Integer32,        
        mplsTpOAMLmDualExp			        Integer32,
        mplsTpOAMLmDualLocalLoss            Integer32,
		mplsTpOAMLmDualLocalLossRatio       Integer32,
		mplsTpOAMLmDualRemoteLoss           Integer32,
		mplsTpOAMLmDualRemoteLossRatio      Integer32  
        }

mplsTpOAMLmDualMegId OBJECT-TYPE
    SYNTAX OCTET STRING
    MAX-ACCESS not-accessible
    STATUS current
    DESCRIPTION
      "MEG ID."    
    ::= { mplsTpOAMLmDualEntry 1 }	

mplsTpOAMLmDualIndex OBJECT-TYPE
    SYNTAX Integer32
    MAX-ACCESS not-accessible
    STATUS current
    DESCRIPTION
      "Index of the entry."  
    ::= { mplsTpOAMLmDualEntry 2 }	
        
mplsTpOAMLmDualService OBJECT-TYPE
    SYNTAX INTEGER
    {
        section(1),
        lsp(2),
        pw-tpe(3)
    }
    MAX-ACCESS read-only
    STATUS current
    DESCRIPTION
      "Service type of the data."    
    ::= { mplsTpOAMLmDualEntry 3 }	

mplsTpOAMLmDualMepId OBJECT-TYPE
    SYNTAX Integer32
    MAX-ACCESS read-only
    STATUS current
    DESCRIPTION
      "MEP ID."    
    ::= { mplsTpOAMLmDualEntry 4 }	
    
mplsTpOAMLmDualExp OBJECT-TYPE
    SYNTAX Integer32 (0..8)
    MAX-ACCESS read-only
    STATUS current
    DESCRIPTION
      "Exp value, the range is 0 to 7 for cos and 8 for all-cos."   
    ::= { mplsTpOAMLmDualEntry 5 }	

mplsTpOAMLmDualLocalLoss OBJECT-TYPE
    SYNTAX Integer32
    MAX-ACCESS read-only
    STATUS current
    DESCRIPTION
      "Dual-lm near end loss."
    ::= { mplsTpOAMLmDualEntry 6 }

mplsTpOAMLmDualLocalLossRatio OBJECT-TYPE
    SYNTAX Integer32
    MAX-ACCESS read-only
    STATUS current
    DESCRIPTION
      "Dual-lm near end loss ratio, the range is 0 - 1000000, 
      unit is one in a million."
    ::= { mplsTpOAMLmDualEntry 7 }

mplsTpOAMLmDualRemoteLoss OBJECT-TYPE
    SYNTAX Integer32
    MAX-ACCESS read-only
    STATUS current
    DESCRIPTION
      "Dual-lm far end loss."
    ::= { mplsTpOAMLmDualEntry 8 }

mplsTpOAMLmDualRemoteLossRatio OBJECT-TYPE
    SYNTAX Integer32
    MAX-ACCESS read-only
    STATUS current
    DESCRIPTION
      "Dual-lm far end loss ratio, the range is 0 - 1000000, 
      unit is one in a million."
    ::= { mplsTpOAMLmDualEntry 9 }    

mplsTpOAMLmDualLossTable OBJECT-TYPE
    SYNTAX  SEQUENCE OF MplsTpOAMLmDualLossEntry
    MAX-ACCESS not-accessible
    STATUS   current
    DESCRIPTION 
    	"MPLS-TP OAM LmDualLoss table."
    ::= { mpls 95 }

mplsTpOAMLmDualLossEntry OBJECT-TYPE
    SYNTAX  MplsTpOAMLmDualLossEntry
    MAX-ACCESS not-accessible
    STATUS current
    DESCRIPTION 
    	"MPLS-TP LmDualLoss entries."
    INDEX   { mplsTpOAMLmDualLossMegId }
    ::= { mplsTpOAMLmDualLossTable 1 }

MplsTpOAMLmDualLossEntry   ::=
    SEQUENCE {
        mplsTpOAMLmDualLossMegId		    	OCTET STRING,
		mplsTpOAMLmDualLossMepId		    	Integer32,
		mplsTpOAMLmDualLossStartTime        	OCTET STRING,
		mplsTpOAMLmDualLossEndTime		    	OCTET STRING,
		mplsTpOAMLmDualStatusInterval           Integer32,
        mplsTpOAMLmDualMaxLocalLoss             Integer32,
        mplsTpOAMLmDualMaxLocalLossRatio        Integer32,     
        mplsTpOAMLmDualMinLocalLoss             Integer32,
        mplsTpOAMLmDualMinLocalLossRatio        Integer32, 		
        mplsTpOAMLmDualMaxRemoteLoss            Integer32,
        mplsTpOAMLmDualMaxRemoteLossRatio       Integer32,     
        mplsTpOAMLmDualMinRemoteLoss            Integer32,
        mplsTpOAMLmDualMinRemoteLossRatio       Integer32
        }

mplsTpOAMLmDualLossMegId OBJECT-TYPE
    SYNTAX OCTET STRING (SIZE (1..12))
    MAX-ACCESS not-accessible
    STATUS current
    DESCRIPTION
      "MEG ID."    
    ::= { mplsTpOAMLmDualLossEntry 1 }	

mplsTpOAMLmDualLossMepId OBJECT-TYPE
    SYNTAX Integer32
    MAX-ACCESS read-only
    STATUS current
    DESCRIPTION
      "Mep Id."    
    ::= { mplsTpOAMLmDualLossEntry 2 }	 
	
mplsTpOAMLmDualLossStartTime OBJECT-TYPE
    SYNTAX OCTET STRING (SIZE (1..50))
    MAX-ACCESS read-only
    STATUS current
    DESCRIPTION
      "Lm dual Start Time."    
    ::= { mplsTpOAMLmDualLossEntry 3 }	
	
mplsTpOAMLmDualLossEndTime OBJECT-TYPE
    SYNTAX OCTET STRING (SIZE (1..50))
    MAX-ACCESS read-only
    STATUS current
    DESCRIPTION
      "Lm dual End Time."    
    ::= { mplsTpOAMLmDualLossEntry 4 }	
	
mplsTpOAMLmDualStatusInterval OBJECT-TYPE
    SYNTAX Integer32
    MAX-ACCESS read-only
    STATUS current
    DESCRIPTION
      "Dual-lm status interval."
    ::= { mplsTpOAMLmDualLossEntry 5 }
    
mplsTpOAMLmDualMaxLocalLoss OBJECT-TYPE
    SYNTAX Integer32
    MAX-ACCESS read-only
    STATUS current
    DESCRIPTION
      "Dual-lm max near end loss."
    ::= { mplsTpOAMLmDualLossEntry 6 }

mplsTpOAMLmDualMaxLocalLossRatio OBJECT-TYPE
    SYNTAX Integer32
    MAX-ACCESS read-only
    STATUS current
    DESCRIPTION
      "Dual-lm max near end loss ratio, the range is 0 - 1000000, 
      unit is one in a million."
    ::= { mplsTpOAMLmDualLossEntry 7 }
	
mplsTpOAMLmDualMinLocalLoss OBJECT-TYPE
    SYNTAX Integer32
    MAX-ACCESS read-only
    STATUS current
    DESCRIPTION
      "Dual-lm min near end loss."
    ::= { mplsTpOAMLmDualLossEntry 8}

mplsTpOAMLmDualMinLocalLossRatio OBJECT-TYPE
    SYNTAX Integer32
    MAX-ACCESS read-only
    STATUS current
    DESCRIPTION
      "Dual-lm min near end loss ratio, the range is 0 - 1000000, 
      unit is one in a million."
    ::= { mplsTpOAMLmDualLossEntry 9 }

mplsTpOAMLmDualMaxRemoteLoss OBJECT-TYPE
    SYNTAX Integer32
    MAX-ACCESS read-only
    STATUS current
    DESCRIPTION
      "Dual-lm max far end loss."
    ::= { mplsTpOAMLmDualLossEntry 10 }

mplsTpOAMLmDualMaxRemoteLossRatio OBJECT-TYPE
    SYNTAX Integer32
    MAX-ACCESS read-only
    STATUS current
    DESCRIPTION
      "Dual-lm max far end loss ratio, the range is 0 - 1000000, 
      unit is one in a million."
    ::= { mplsTpOAMLmDualLossEntry 11 }       

mplsTpOAMLmDualMinRemoteLoss OBJECT-TYPE
    SYNTAX Integer32
    MAX-ACCESS read-only
    STATUS current
    DESCRIPTION
      "Dual-lm min far end loss."
    ::= { mplsTpOAMLmDualLossEntry 12 }

mplsTpOAMLmDualMinRemoteLossRatio OBJECT-TYPE
    SYNTAX Integer32
    MAX-ACCESS read-only
    STATUS current
    DESCRIPTION
      "Dual-lm min far end loss ratio, the range is 0 - 1000000, 
      unit is one in a million."
    ::= { mplsTpOAMLmDualLossEntry 13 } 
	
mplsTpOAMLmSingleTable OBJECT-TYPE
    SYNTAX  SEQUENCE OF MplsTpOAMLmSingleEntry
    MAX-ACCESS not-accessible
    STATUS   current
    DESCRIPTION 
    	"MPLS-TP OAM LmSingle table."
    ::= { mpls 96 }

mplsTpOAMLmSingleEntry OBJECT-TYPE
    SYNTAX  MplsTpOAMLmSingleEntry
    MAX-ACCESS not-accessible
    STATUS current
    DESCRIPTION 
    	"MPLS-TP LmSingle entries."
    INDEX   { mplsTpOAMLmSingleMegId, mplsTpOAMLmSingleIndex }
    ::= { mplsTpOAMLmSingleTable 1 }

MplsTpOAMLmSingleEntry   ::=
    SEQUENCE {
        mplsTpOAMLmSingleMegId		    	  OCTET STRING,
        mplsTpOAMLmSingleIndex			      Integer32,      
        mplsTpOAMLmSingleService			  INTEGER,
        mplsTpOAMLmSingleMepId		    	  Integer32,        
        mplsTpOAMLmSingleExp			      Integer32,
        mplsTpOAMLmSingleLocalLoss            Integer32,
		mplsTpOAMLmSingleLocalLossRatio       Integer32,
		mplsTpOAMLmSingleRemoteLoss           Integer32,
		mplsTpOAMLmSingleRemoteLossRatio      Integer32  
        }

mplsTpOAMLmSingleMegId OBJECT-TYPE
    SYNTAX OCTET STRING
    MAX-ACCESS not-accessible
    STATUS current
    DESCRIPTION
      "MEG ID."    
    ::= { mplsTpOAMLmSingleEntry 1 }	

mplsTpOAMLmSingleIndex OBJECT-TYPE
    SYNTAX Integer32
    MAX-ACCESS not-accessible
    STATUS current
    DESCRIPTION
      "Index of the entry."  
    ::= { mplsTpOAMLmSingleEntry 2 }	
        
mplsTpOAMLmSingleService OBJECT-TYPE
    SYNTAX INTEGER
    {
        section(1),
        lsp(2),
        pw-tpe(3)
    }
    MAX-ACCESS read-only
    STATUS current
    DESCRIPTION
      "Service type of the data."    
    ::= { mplsTpOAMLmSingleEntry 3 }	

mplsTpOAMLmSingleMepId OBJECT-TYPE
    SYNTAX Integer32
    MAX-ACCESS read-only
    STATUS current
    DESCRIPTION
      "MEP ID."    
    ::= { mplsTpOAMLmSingleEntry 4 }	
    
mplsTpOAMLmSingleExp OBJECT-TYPE
    SYNTAX Integer32 (0..8)
    MAX-ACCESS read-only
    STATUS current
    DESCRIPTION
      "Exp value, the range is 0 to 7 for cos and 8 for all-cos."   
    ::= { mplsTpOAMLmSingleEntry 5 }	

mplsTpOAMLmSingleLocalLoss OBJECT-TYPE
    SYNTAX Integer32
    MAX-ACCESS read-only
    STATUS current
    DESCRIPTION
      "Single-lm near end loss."
    ::= { mplsTpOAMLmSingleEntry 6 }

mplsTpOAMLmSingleLocalLossRatio OBJECT-TYPE
    SYNTAX Integer32
    MAX-ACCESS read-only
    STATUS current
    DESCRIPTION
      "Single-lm near end loss ratio, the range is 0 - 1000000, 
      unit is one in a million."
    ::= { mplsTpOAMLmSingleEntry 7 }

mplsTpOAMLmSingleRemoteLoss OBJECT-TYPE
    SYNTAX Integer32
    MAX-ACCESS read-only
    STATUS current
    DESCRIPTION
      "Single-lm far end loss."
    ::= { mplsTpOAMLmSingleEntry 8 }

mplsTpOAMLmSingleRemoteLossRatio OBJECT-TYPE
    SYNTAX Integer32
    MAX-ACCESS read-only
    STATUS current
    DESCRIPTION
      "Single-lm far end loss ratio, the range is 0 - 1000000, 
      unit is one in a million."
    ::= { mplsTpOAMLmSingleEntry 9 }    

mplsTpOAMLmSingleLossTable OBJECT-TYPE
    SYNTAX  SEQUENCE OF MplsTpOAMLmSingleLossEntry
    MAX-ACCESS not-accessible
    STATUS   current
    DESCRIPTION 
    	"MPLS-TP OAM LmSingleLoss table."
    ::= { mpls 97 }

mplsTpOAMLmSingleLossEntry OBJECT-TYPE
    SYNTAX  MplsTpOAMLmSingleLossEntry
    MAX-ACCESS not-accessible
    STATUS current
    DESCRIPTION 
    	"MPLS-TP LmSingleLoss entries."
    INDEX   { mplsTpOAMLmSingleLossMegId }
    ::= { mplsTpOAMLmSingleLossTable 1 }

MplsTpOAMLmSingleLossEntry   ::=
    SEQUENCE {
        mplsTpOAMLmSingleLossMegId		    	OCTET STRING,
		mplsTpOAMLmSingleLossMepId		    	Integer32,
		mplsTpOAMLmSingleLossStartTime        	OCTET STRING,
		mplsTpOAMLmSingleLossEndTime		    OCTET STRING,
        mplsTpOAMLmSingleMaxLocalLoss             Integer32,
        mplsTpOAMLmSingleMaxLocalLossRatio        Integer32,     
        mplsTpOAMLmSingleMinLocalLoss             Integer32,
        mplsTpOAMLmSingleMinLocalLossRatio        Integer32, 		
        mplsTpOAMLmSingleMaxRemoteLoss            Integer32,
        mplsTpOAMLmSingleMaxRemoteLossRatio       Integer32,     
        mplsTpOAMLmSingleMinRemoteLoss            Integer32,
        mplsTpOAMLmSingleMinRemoteLossRatio       Integer32
        }

mplsTpOAMLmSingleLossMegId OBJECT-TYPE
    SYNTAX OCTET STRING (SIZE (1..12))
    MAX-ACCESS not-accessible
    STATUS current
    DESCRIPTION
      "MEG ID."    
    ::= { mplsTpOAMLmSingleLossEntry 1 }	

mplsTpOAMLmSingleLossMepId OBJECT-TYPE
    SYNTAX Integer32
    MAX-ACCESS read-only
    STATUS current
    DESCRIPTION
      "Mep Id."    
    ::= { mplsTpOAMLmSingleLossEntry 2 }	 
	
mplsTpOAMLmSingleLossStartTime OBJECT-TYPE
    SYNTAX OCTET STRING (SIZE (1..50))
    MAX-ACCESS read-only
    STATUS current
    DESCRIPTION
      "Lm Single Start Time."    
    ::= { mplsTpOAMLmSingleLossEntry 3 }	
	
mplsTpOAMLmSingleLossEndTime OBJECT-TYPE
    SYNTAX OCTET STRING (SIZE (1..50))
    MAX-ACCESS read-only
    STATUS current
    DESCRIPTION
      "Lm Single End Time."    
    ::= { mplsTpOAMLmSingleLossEntry 4 }	
    
mplsTpOAMLmSingleMaxLocalLoss OBJECT-TYPE
    SYNTAX Integer32
    MAX-ACCESS read-only
    STATUS current
    DESCRIPTION
      "Single-lm max near end loss."
    ::= { mplsTpOAMLmSingleLossEntry 5 }

mplsTpOAMLmSingleMaxLocalLossRatio OBJECT-TYPE
    SYNTAX Integer32
    MAX-ACCESS read-only
    STATUS current
    DESCRIPTION
      "Single-lm max near end loss ratio, the range is 0 - 1000000, 
      unit is one in a million."
    ::= { mplsTpOAMLmSingleLossEntry 6 }
	
mplsTpOAMLmSingleMinLocalLoss OBJECT-TYPE
    SYNTAX Integer32
    MAX-ACCESS read-only
    STATUS current
    DESCRIPTION
      "Single-lm min near end loss."
    ::= { mplsTpOAMLmSingleLossEntry 7}

mplsTpOAMLmSingleMinLocalLossRatio OBJECT-TYPE
    SYNTAX Integer32
    MAX-ACCESS read-only
    STATUS current
    DESCRIPTION
      "Single-lm min near end loss ratio, the range is 0 - 1000000, 
      unit is one in a million."
    ::= { mplsTpOAMLmSingleLossEntry 8 }

mplsTpOAMLmSingleMaxRemoteLoss OBJECT-TYPE
    SYNTAX Integer32
    MAX-ACCESS read-only
    STATUS current
    DESCRIPTION
      "Single-lm max far end loss."
    ::= { mplsTpOAMLmSingleLossEntry 9 }

mplsTpOAMLmSingleMaxRemoteLossRatio OBJECT-TYPE
    SYNTAX Integer32
    MAX-ACCESS read-only
    STATUS current
    DESCRIPTION
      "Single-lm max far end loss ratio, the range is 0 - 1000000, 
      unit is one in a million."
    ::= { mplsTpOAMLmSingleLossEntry 10 }       

mplsTpOAMLmSingleMinRemoteLoss OBJECT-TYPE
    SYNTAX Integer32
    MAX-ACCESS read-only
    STATUS current
    DESCRIPTION
      "Single-lm min far end loss."
    ::= { mplsTpOAMLmSingleLossEntry 11 }

mplsTpOAMLmSingleMinRemoteLossRatio OBJECT-TYPE
    SYNTAX Integer32
    MAX-ACCESS read-only
    STATUS current
    DESCRIPTION
      "Single-lm min far end loss ratio, the range is 0 - 1000000, 
      unit is one in a million."
    ::= { mplsTpOAMLmSingleLossEntry 12 } 
	
mplsTpOAMSingleLMCacheTable OBJECT-TYPE
    SYNTAX  SEQUENCE OF MplsTpOAMSingleLMCacheEntry
    MAX-ACCESS not-accessible
    STATUS   current
    DESCRIPTION 
    	"MPLS-TP OAM single lm cache table."
    ::= { mpls 100 }

mplsTpOAMSingleLMCacheEntry OBJECT-TYPE
    SYNTAX  MplsTpOAMSingleLMCacheEntry
    MAX-ACCESS not-accessible
    STATUS current
    DESCRIPTION 
    	"MPLS-TP single lm cache entries."
    INDEX   { mplsTpOAMSingleLMCacheMegId, mplsTpOAMSingleLMCacheIndex }
    ::= { mplsTpOAMSingleLMCacheTable 1 }

MplsTpOAMSingleLMCacheEntry   ::=
    SEQUENCE {
        mplsTpOAMSingleLMCacheMegId		    	     OCTET STRING,
        mplsTpOAMSingleLMCacheIndex			         Integer32,      
        mplsTpOAMSingleLMCacheExpValue           Integer32,
        mplsTpOAMSingleLMCacheLocalLoss          Integer32,
        mplsTpOAMSingleLMCacheLocalLossRatio     Integer32,
        mplsTpOAMSingleLMCacheRemoteLoss         Integer32,
        mplsTpOAMSingleLMCacheRemoteLossRatio    Integer32,
        mplsTpOAMSingleLMCacheTime               OCTET STRING  
        }

mplsTpOAMSingleLMCacheMegId OBJECT-TYPE
    SYNTAX OCTET STRING
    MAX-ACCESS not-accessible
    STATUS current
    DESCRIPTION
      "MEG ID."    
    ::= { mplsTpOAMSingleLMCacheEntry 1 }	

mplsTpOAMSingleLMCacheIndex OBJECT-TYPE
    SYNTAX Integer32
    MAX-ACCESS not-accessible
    STATUS current
    DESCRIPTION
      "Index of the entry."  
    ::= { mplsTpOAMSingleLMCacheEntry 2 }	

mplsTpOAMSingleLMCacheExpValue     OBJECT-TYPE
    SYNTAX          Integer32 (0..8) 
    MAX-ACCESS      read-only
    STATUS          current
    DESCRIPTION
        "Exp value, the range is 0 to 7 for cos and 8 for all-cos."
    ::= { mplsTpOAMSingleLMCacheEntry 3 }
    
mplsTpOAMSingleLMCacheLocalLoss OBJECT-TYPE
    SYNTAX Integer32
    MAX-ACCESS read-only
    STATUS current
    DESCRIPTION
      "Single-lm near end loss."
    ::= { mplsTpOAMSingleLMCacheEntry 4 }

mplsTpOAMSingleLMCacheLocalLossRatio OBJECT-TYPE
    SYNTAX Integer32
    MAX-ACCESS read-only
    STATUS current
    DESCRIPTION
      "Single-lm near end loss ratio, the range is 1 - 1000000, 
      unit is one in a million."
    ::= { mplsTpOAMSingleLMCacheEntry 5 }

mplsTpOAMSingleLMCacheRemoteLoss OBJECT-TYPE
    SYNTAX Integer32
    MAX-ACCESS read-only
    STATUS current
    DESCRIPTION
      "Single-lm far end loss."
    ::= { mplsTpOAMSingleLMCacheEntry 6 }

mplsTpOAMSingleLMCacheRemoteLossRatio OBJECT-TYPE
    SYNTAX Integer32
    MAX-ACCESS read-only
    STATUS current
    DESCRIPTION
      "Single-lm far end loss ratio, the range is 1 - 1000000, 
      unit is one in a million."
    ::= { mplsTpOAMSingleLMCacheEntry 7 }

mplsTpOAMSingleLMCacheTime OBJECT-TYPE
    SYNTAX OCTET STRING
    MAX-ACCESS read-only
    STATUS current
    DESCRIPTION
      "Cache time."    
    ::= { mplsTpOAMSingleLMCacheEntry 8 }	  

mplsTrapGroup OBJECT IDENTIFIER    ::= { mpls 1000 }

    tpOAMEventTrap NOTIFICATION-TYPE
      OBJECTS { mplsTpOAMEventService,  mplsTpOAMEventMegId, mplsTpOAMEventMepId, mplsTpOAMEventId, mplsTpOAMEventAction }
      STATUS  current
      DESCRIPTION
              "Mpls-tp OAM event."
      ::= { mplsTrapGroup 1 }  
      
    mplsTunnelSwitch NOTIFICATION-TYPE
      OBJECTS { mplsTunnelSelectedLspPe, mplsTunnelG8131CurrentState }
      STATUS  current
      DESCRIPTION
              "Lsp switchover of mpls tunnel."
      ::= { mplsTrapGroup 2 }        
      
    mplsTPVpwsSwitch NOTIFICATION-TYPE
      OBJECTS { mplsTPVpwsSelectedPw, mplsTPVpwsG8131CurrentState }
      STATUS  current
      DESCRIPTION
              "PW switchover of mpls-tp vpws."
      ::= { mplsTrapGroup 3 }        

    mplsVplsTPPeerSwitch NOTIFICATION-TYPE
      OBJECTS { mplsVplsTPPeerSelectedPw, mplsVplsTPPeerG8131CurrentState }
      STATUS  current
      DESCRIPTION
              "PW switchover of mpls-tp vpls peer."
      ::= { mplsTrapGroup 4 }       

    mplsVpwsStateChange NOTIFICATION-TYPE
      OBJECTS { mplsVpwsState }
      STATUS  current
      DESCRIPTION
              "Active or inactive of vpws."
      ::= { mplsTrapGroup 5 } 
      
    mplsVplsPeerStateChange NOTIFICATION-TYPE
      OBJECTS { mplsVplsPeerState }
      STATUS  current
      DESCRIPTION
              "Active or inactive of vpls peer."
      ::= { mplsTrapGroup 6 }             
    
    mplsVpwsOAMCsfStateChange NOTIFICATION-TYPE
      OBJECTS { mplsTPVpwsOAMCsfSrvState, mplsTPVpwsOAMCsfClientState, mplsTPVpwsOAMCsfDCReason, mplsTPVpwsOAMCsfClientInterval }
      STATUS  current
      DESCRIPTION
              "Vpws OAM csf state change."
      ::= { mplsTrapGroup 7 }                            

    tpOAMSingleLmLocalLossTrap NOTIFICATION-TYPE
      OBJECTS { mplsTpOAMSingleLMCacheLocalLoss, mplsTpOAMSingleLMCacheLocalLossRatio, mplsTpOAMSingleLMCacheTime}
      STATUS  current
      DESCRIPTION
              "Single lm local loss reaches threshold."
      ::= { mplsTrapGroup 8 } 

    tpOAMSingleLmLocalLossClearTrap NOTIFICATION-TYPE
      OBJECTS { mplsTpOAMSingleLMCacheLocalLoss, mplsTpOAMSingleLMCacheLocalLossRatio, mplsTpOAMSingleLMCacheTime}
      STATUS  current
      DESCRIPTION
              "Single lm local loss reaches threshold."
      ::= { mplsTrapGroup 9 } 

    tpOAMSingleLmRemoteLossTrap NOTIFICATION-TYPE
      OBJECTS { mplsTpOAMSingleLMCacheRemoteLoss, mplsTpOAMSingleLMCacheLocalLossRatio, mplsTpOAMSingleLMCacheTime}
      STATUS  current
      DESCRIPTION
              "Single lm local loss reaches threshold."
      ::= { mplsTrapGroup 10 } 

    tpOAMSingleLmRemoteLossClearTrap NOTIFICATION-TYPE
      OBJECTS { mplsTpOAMSingleLMCacheRemoteLoss, mplsTpOAMSingleLMCacheRemoteLossRatio, mplsTpOAMSingleLMCacheTime}
      STATUS  current
      DESCRIPTION
              "Single lm local loss reaches threshold."
      ::= { mplsTrapGroup 11 } 
                                                                                                 
    writeSuccessTrap NOTIFICATION-TYPE
      OBJECTS { configSave }
      STATUS  current
      DESCRIPTION
              "Config write success"
      ::= { sysTrap 1 }

    writeFailureTrap NOTIFICATION-TYPE
      OBJECTS { configSave }
      STATUS  current
      DESCRIPTION
              "Config write failure"
      ::= { sysTrap 2 }

    rebootSendTrap NOTIFICATION-TYPE
      OBJECTS { reload }
      STATUS  current
      DESCRIPTION
              "Reload send trap"
      ::= { sysTrap 3 }


    memUsageHigher NOTIFICATION-TYPE
      OBJECTS { memTotalFree }
      STATUS  current
      DESCRIPTION
              "Memory usage higher"
      ::= { sysTrap 4 }

    memUsageFormHigherToNormal NOTIFICATION-TYPE
      OBJECTS { memTotalFree }
      STATUS  current
      DESCRIPTION
              "Memory usage from higher to normal"
      ::= { sysTrap 5 }


    vtySessionStartTrap NOTIFICATION-TYPE
      OBJECTS { usersLineIndex, usersname, usersLocation }
      STATUS  current
      DESCRIPTION
              "Virtual terminal session start"
      ::= { sysTrap 6 }

    vtySessionStopTrap NOTIFICATION-TYPE
      OBJECTS { usersLineIndex, usersname, usersLocation }
      STATUS  current
      DESCRIPTION
              "Virtual terminal session stop"
      ::= { sysTrap 7 }

    timeChangeTrap NOTIFICATION-TYPE
      OBJECTS { timeSetClock, timeSetMonth, timeSetDay, timeSetYear }
      STATUS  current
      DESCRIPTION
              "Time Change Trap"
      ::= { sysTrap 8 }

    cpuUsageHigher NOTIFICATION-TYPE
      OBJECTS { ssCpuIdle }
      STATUS  current
      DESCRIPTION
              "Cpu Usage higher"
      ::= { sysTrap 9 }

    cpuUsageFormHigherToNormal NOTIFICATION-TYPE
      OBJECTS { ssCpuIdle }
      STATUS  current
      DESCRIPTION
              "Cpu Usage from higher to normal"
      ::= { sysTrap 10 }

    lastCommandTrap NOTIFICATION-TYPE
      OBJECTS { lastCommand }
      STATUS  current
      DESCRIPTION
              "The trap of the last command line and time."
      ::= { sysTrap 11 }

    cFInserted NOTIFICATION-TYPE
      OBJECTS { cfIndex }
      STATUS  current
      DESCRIPTION
              "Insert CF card."
      ::= { sysTrap 12 }

    cFRemoved NOTIFICATION-TYPE
      OBJECTS { cfIndex }
      STATUS  current
      DESCRIPTION
              "Remove CF card."
      ::= { sysTrap 13 }

    loginFailTrap NOTIFICATION-TYPE
      OBJECTS { loginFail }
      STATUS  current
      DESCRIPTION
              "Login fail for three times."
      ::= { sysTrap 14 }

    processDumpTrap NOTIFICATION-TYPE
      OBJECTS { lastDumpedProcess }
      STATUS  current
      DESCRIPTION
              "The trap of the last dumped process id."
      ::= { sysTrap 15 }

-- Sub Module: SMART-LINK

--
-- Node definitions
--

smartlinkRelayEnable     OBJECT-TYPE
    SYNTAX          INTEGER {enabled(1),disabled(2)}
    MAX-ACCESS      read-write
    STATUS          current
    DESCRIPTION
        "Relay flush packet is enabled on the device or not.
        The meanings of the values are:
        enabled(1) -  Enable smart-link relay;
        disabled(2) - Disable smart-link relay;"
    ::= { smartlink 1 }

smartlinkClearStatistic     OBJECT-TYPE
    SYNTAX          INTEGER { yes(1)}
    MAX-ACCESS      read-write
    STATUS          current
    DESCRIPTION
        " Clear the statistic infomation smart link module.
        The meanings of the values are:
        YES(1) -  Clear it;"
    ::= { smartlink 2 }

-- smartlinkGroupTable

smartlinkGroupTable     OBJECT-TYPE
    SYNTAX          SEQUENCE OF SmartlinkGroupEntry
    MAX-ACCESS      not-accessible
    STATUS          current
    DESCRIPTION
        "A table that contains smart-link group information."
    ::= { smartlink 3 }

smartlinkGroupEntry     OBJECT-TYPE
    SYNTAX          SmartlinkGroupEntry
    MAX-ACCESS      not-accessible
    STATUS          current
    DESCRIPTION
        "A list of smart-link group information "
    INDEX     { smartlinkGroupindex  }
    ::= { smartlinkGroupTable 1 }

SmartlinkGroupEntry    ::=
    SEQUENCE
    {
       smartlinkGroupindex
           INTEGER,
     smartlinkGroupRowStatus
           RowStatus,
       smartlinkGroupMasterIntf
           InterfaceIndex,
       smartlinkGroupMasterDnCnt
           INTEGER,
       smartlinkGroupMasterlstDnTime
           OCTET STRING,
       smartlinkGroupMasterflhCnt
           INTEGER,
       smartlinkGroupMasterlstflhTime
           OCTET STRING,
       smartlinkGroupSlaveIntf
           InterfaceIndex,
        smartlinkGroupSlaveDnCnt
           INTEGER,
       smartlinkGroupSlavelstDnTime
           OCTET STRING,
       smartlinkGroupSlaveflhCnt
           INTEGER,
       smartlinkGroupSlavelstflhTime
           OCTET STRING,
       smartlinkGroupMstpInstance
           OCTET STRING,
       smartlinkGroupLoadBalanceInstance
           OCTET STRING,
       smartlinkGroupRestoreEnable
           INTEGER,
       smartlinkGroupRestoreTime
           INTEGER,           
       smartlinkGroupControlVlan
           INTEGER,
       smartlinkGroupControlVlanPassword
           OCTET STRING,
       smartlinkGroupEnable
           INTEGER
    }

smartlinkGroupindex         OBJECT-TYPE
    SYNTAX          INTEGER (1..16)
    MAX-ACCESS      not-accessible
    STATUS          current
    DESCRIPTION
        "An index that uniquely identifies an group in the smart link table."
    ::= { smartlinkGroupEntry 1 }   

smartlinkGroupRowStatus         OBJECT-TYPE
  SYNTAX          RowStatus
  MAX-ACCESS      read-create
  STATUS          current
  DESCRIPTION
        "The status of this conceptual row.Now only realize CreateAndGo and Destroy and Active.
        1 means Active
        4 means CreateAndGo
        6 means Destroy"
  ::= { smartlinkGroupEntry 2 }    

smartlinkGroupMasterIntf      OBJECT-TYPE
    SYNTAX          InterfaceIndex
    MAX-ACCESS      read-write
    STATUS          current
    DESCRIPTION
        "The port number of the port for which this smart-link contains master interface.
        0 means delete"
    ::= { smartlinkGroupEntry 3 }

smartlinkGroupMasterDnCnt     OBJECT-TYPE
    SYNTAX          INTEGER
    MAX-ACCESS      read-only
    STATUS          current
    DESCRIPTION
        "Smart-link master down count."
    ::= { smartlinkGroupEntry 4 }

smartlinkGroupMasterlstDnTime     OBJECT-TYPE
    SYNTAX          OCTET STRING
    MAX-ACCESS      read-only
    STATUS          current
    DESCRIPTION
        "Smart-link master last down time."
    ::= { smartlinkGroupEntry 5 }

smartlinkGroupMasterflhCnt     OBJECT-TYPE
    SYNTAX          INTEGER
    MAX-ACCESS      read-only
    STATUS          current
    DESCRIPTION
        "Smart-link master flush count."
    ::= { smartlinkGroupEntry 6 }

smartlinkGroupMasterlstflhTime     OBJECT-TYPE
    SYNTAX          OCTET STRING
    MAX-ACCESS      read-only
    STATUS          current
    DESCRIPTION
        "Smart-link master last flush time."
    ::= { smartlinkGroupEntry 7 }

smartlinkGroupSlaveIntf      OBJECT-TYPE
    SYNTAX          InterfaceIndex
    MAX-ACCESS      read-write
    STATUS          current
    DESCRIPTION
        "The port number of the port for which this smart-link contains slave interface.
        0 means delete"
    ::= { smartlinkGroupEntry 8 }

smartlinkGroupSlaveDnCnt     OBJECT-TYPE
    SYNTAX          INTEGER
    MAX-ACCESS      read-only
    STATUS          current
    DESCRIPTION
        "Smart-link master down count."
    ::= { smartlinkGroupEntry 9 }

smartlinkGroupSlavelstDnTime     OBJECT-TYPE
    SYNTAX          OCTET STRING
    MAX-ACCESS      read-only
    STATUS          current
    DESCRIPTION
        "Smart-link master last down time."
    ::= { smartlinkGroupEntry 10 }

smartlinkGroupSlaveflhCnt     OBJECT-TYPE
    SYNTAX          INTEGER
    MAX-ACCESS      read-only
    STATUS          current
    DESCRIPTION
        "Smart-link master flush count."
    ::= { smartlinkGroupEntry 11 }

smartlinkGroupSlavelstflhTime     OBJECT-TYPE
    SYNTAX          OCTET STRING
    MAX-ACCESS      read-only
    STATUS          current
    DESCRIPTION
        "Smart-link master last flush time."
    ::= { smartlinkGroupEntry 12 }

smartlinkGroupMstpInstance         OBJECT-TYPE
    SYNTAX          OCTET STRING (SIZE(0..4094))
    MAX-ACCESS      read-write
    STATUS          current
    DESCRIPTION
        "Protected mstp instance ID.
         -1 means delete"
    ::= { smartlinkGroupEntry 13 }

smartlinkGroupLoadBalanceInstance         OBJECT-TYPE
    SYNTAX          OCTET STRING (SIZE(0..4094))
    MAX-ACCESS      read-write
    STATUS          current
    DESCRIPTION
        "Load-balance instance ID.
        -1 means delete"
    ::= { smartlinkGroupEntry 14 }

smartlinkGroupRestoreEnable         OBJECT-TYPE
    SYNTAX          INTEGER
    {
        enable(1),
        disable(2)
    }
    MAX-ACCESS      read-write
    STATUS          current
    DESCRIPTION
         "Auto-restore of the smart link group is enabled on the device or not.
          The meanings of the values are:
          enabled(1) -  Enable auto-restore of the smart link group;
          disabled(2) - Disable auto-restore of the smart link group;"
    ::= { smartlinkGroupEntry 15 }

smartlinkGroupRestoreTime       OBJECT-TYPE
    SYNTAX          INTEGER(30..1200)
    MAX-ACCESS      read-write
    STATUS          current
    DESCRIPTION
        "The time range(Second) of Restore time. Range <30-1200>"
    ::= { smartlinkGroupEntry 16 }

smartlinkGroupControlVlan         OBJECT-TYPE
    SYNTAX          INTEGER (0..4094)
    MAX-ACCESS      read-write
    STATUS          current
    DESCRIPTION
        "The vlan id of the smart-link control vlan.
        Set 0 to delete the control vlan."
    ::= { smartlinkGroupEntry 17 }

smartlinkGroupControlVlanPassword         OBJECT-TYPE
    SYNTAX          OCTET STRING (SIZE (1..15))
    MAX-ACCESS      read-write
    STATUS          current
    DESCRIPTION
        "The password of the smart-link control vlan.
        By default the password is 'default'"
    DEFVAL          {"default"}
    ::= { smartlinkGroupEntry 18 }

smartlinkGroupEnable         OBJECT-TYPE
    SYNTAX          INTEGER
    {
      enabled(1),
      disabled(2)
    }
    MAX-ACCESS      read-write
    STATUS          current
    DESCRIPTION
        "The state of smart-link group .
        The meanings of the values are:
        enabled(1) -  Enable smart-link group;
        disabled(2) - Disable smart-link group;"
    ::= { smartlinkGroupEntry 19 }


-- smartlinkRcvFlushintfTable

smartlinkRcvFlushintfTable     OBJECT-TYPE
    SYNTAX          SEQUENCE OF SmartlinkRcvFlushintfEntry
    MAX-ACCESS      not-accessible
    STATUS          current
    DESCRIPTION
        "A table that contains smart-link group information."
    ::= { smartlink 4 }

smartlinkRcvFlushintfEntry     OBJECT-TYPE
    SYNTAX          SmartlinkRcvFlushintfEntry
    MAX-ACCESS      not-accessible
    STATUS          current
    DESCRIPTION
        "A list of smart-link group information. "
    INDEX     { smartlinkGroupindex  }
    ::= { smartlinkRcvFlushintfTable 1 }

SmartlinkRcvFlushintfEntry    ::=
    SEQUENCE
    {
    	 smartlinkRcvFlushintfindex
    	 		 InterfaceIndex,
       smartlinkRcvFlushintfVlan
           INTEGER,               
  		 smartlinkRcvFlushintfVlanPassword
           OCTET STRING,
        martlinkRcvFlushintfSetState
            RowStatus 
    }  

smartlinkRcvFlushintfindex      OBJECT-TYPE
    SYNTAX          InterfaceIndex
    MAX-ACCESS      not-accessible
    STATUS          current
    DESCRIPTION
        "The index of the interface which smart-link receive flush from."    
    ::= { smartlinkRcvFlushintfEntry 1 }  
    
smartlinkRcvFlushintfVlan         OBJECT-TYPE
    SYNTAX          INTEGER (1..4094)
    MAX-ACCESS      read-write
    STATUS          current
    DESCRIPTION
        "The vlan id of the interface which smart-link receive flush from."
    ::= { smartlinkRcvFlushintfEntry 2 }

smartlinkRcvFlushintfVlanPassword         OBJECT-TYPE
    SYNTAX          OCTET STRING (SIZE (1..16))
    MAX-ACCESS      read-write
    STATUS          current
    DESCRIPTION
        "The password of the interface which smart-link receive flush from."
    ::= { smartlinkRcvFlushintfEntry 3 }

martlinkRcvFlushintfSetState         OBJECT-TYPE
    SYNTAX          RowStatus 
    MAX-ACCESS      read-write
    STATUS          current
    DESCRIPTION
        "The status of this conceptual row.Now only realize CreateAndGo and Destroy and Active.
        1 means Active
        4 means CreateAndGo
        6 means Destroy"
    ::= { smartlinkRcvFlushintfEntry 4 }
--

smartlinkRcvFlushPktNum     OBJECT-TYPE
    SYNTAX          INTEGER
    MAX-ACCESS      read-only
    STATUS          current
    DESCRIPTION
        "Smart-link received flush packet number."
    ::= { smartlink 5 }

smartlinkProcFlushPktNum     OBJECT-TYPE
    SYNTAX          INTEGER
    MAX-ACCESS      read-only
    STATUS          current
    DESCRIPTION
        "Smart-link processed flush packet number."
    ::= { smartlink 6 }



--flowctrl                OBJECT IDENTIFIER ::= { OID 71 }

-- Sub Module: FLOW-CONTROL

--
-- Node definitions
--

-- flowctrlSendEnableTable

flowctrlSendEnableTable     OBJECT-TYPE
    SYNTAX          SEQUENCE OF FlowctrlSendEnableEntry
    MAX-ACCESS      not-accessible
    STATUS          current
    DESCRIPTION
        "Enable or disable flow control send function.
        The meanings of the values are:
        on(1) -  Set send flowcontrol enable;
        off(2) - Set send flowcontrol disable;
        Default setting is off(2)."
    ::= { flowctrl 1 }

flowctrlSendEnableEntry     OBJECT-TYPE
    SYNTAX          FlowctrlSendEnableEntry
    MAX-ACCESS      not-accessible
    STATUS          current
    DESCRIPTION
        "A list of flowctrl Send Enable group information. "
    INDEX     { interfaceIndex  }
    ::= { flowctrlSendEnableTable 1 }

FlowctrlSendEnableEntry    ::=
    SEQUENCE
    {
       flowctrlSendEnable
           INTEGER
    }

flowctrlSendEnable     OBJECT-TYPE
    SYNTAX          INTEGER {on(1),off(2)}
    MAX-ACCESS      read-write
    STATUS          current
    DESCRIPTION
        "Enable or disable flow control send function.
        The meanings of the values are:
        on(1) -  Set send flowcontrol enable;
        off(2) - Set send flowcontrol disable;
        Default setting is off(2."
  DEFVAL { 2 }
    ::= { flowctrlSendEnableEntry 1 }


-- flowctrlReceiveEnableTable

flowctrlReceiveEnableTable     OBJECT-TYPE
    SYNTAX          SEQUENCE OF FlowctrlReceiveEnableEntry
    MAX-ACCESS      not-accessible
    STATUS          current
    DESCRIPTION
        "Enable or disable flow control Receive function.
        The meanings of the values are:
        on(1) -  Set Receive flowcontrol enable;
        off(2) - Set Receive flowcontrol disable;
        Default setting is off(2)."
    ::= { flowctrl 2 }

flowctrlReceiveEnableEntry     OBJECT-TYPE
    SYNTAX          FlowctrlReceiveEnableEntry
    MAX-ACCESS      not-accessible
    STATUS          current
    DESCRIPTION
        "A list of smart-link group information "
    INDEX     { interfaceIndex  }
    ::= { flowctrlReceiveEnableTable 1 }

FlowctrlReceiveEnableEntry    ::=
    SEQUENCE
    {
       flowctrlReceiveEnable
           INTEGER
    }

flowctrlReceiveEnable     OBJECT-TYPE
    SYNTAX          INTEGER {on(1),off(2)}
    MAX-ACCESS      read-write
    STATUS          current
    DESCRIPTION
        "Enable or disable flow control Receive function.
        The meanings of the values are:
        on(1) -  Set Receive flowcontrol enable;
        off(2) - Set Receive flowcontrol disable;
        Default setting is off(2)."
  DEFVAL { 2 }
    ::= { flowctrlReceiveEnableEntry 1 }


--cputraffic                 OBJECT IDENTIFIER ::= { OID 72 }


-- Sub Module: CPU-TRAFFIC

--
-- Node definitions
--

cputrafficLimitTotalRate     OBJECT-TYPE
    SYNTAX          INTEGER (0..1000000)
    MAX-ACCESS      read-write
    STATUS          current
    DESCRIPTION
        "Set the total rate of all streams destined to CPU. Value range 0~1000000 pps. Default 2048 pps"
  DEFVAL { 2048 }
    ::= { cputraffic 1 }

cputrafficLimitReasonRate OBJECT IDENTIFIER    ::= { cputraffic 2 }


arpReasonRate         OBJECT-TYPE
    SYNTAX          INTEGER (0..1000000)
    MAX-ACCESS      read-write
    STATUS          current
    DESCRIPTION
        " Address Resolution Protocol.
          Rate range 0~1000000.
         Default value 256 pps."
  DEFVAL { 256 }
    ::= { cputrafficLimitReasonRate 1 }

bpduReasonRate         OBJECT-TYPE
    SYNTAX          INTEGER (0..1000000)
    MAX-ACCESS      read-write
    STATUS          current
    DESCRIPTION
        " Bridge Protocol Data Unit.
          Rate range 0~1000000.
         Default value 64 pps."
  DEFVAL { 64 }
    ::= { cputrafficLimitReasonRate 2 }

cfmReasonRate         OBJECT-TYPE
    SYNTAX          INTEGER (0..1000000)
    MAX-ACCESS      read-write
    STATUS          current
    DESCRIPTION
        " Connectivity Fault Management.
          Rate range 0~1000000.
         Default value 512 pps."
  DEFVAL { 512 }
    ::= { cputrafficLimitReasonRate 3 }

dhcpReasonRate         OBJECT-TYPE
    SYNTAX          INTEGER (0..1000000)
    MAX-ACCESS      read-write
    STATUS          current
    DESCRIPTION
        " Dynamic Host Configuration Protocol.
          Rate range 0~1000000.
         Default value 128 pps."
  DEFVAL { 128 }
    ::= { cputrafficLimitReasonRate 4 }

eapolReasonRate         OBJECT-TYPE
    SYNTAX          INTEGER (0..1000000)
    MAX-ACCESS      read-write
    STATUS          current
    DESCRIPTION
        " Extensible Authentication Protocol Over Lan.
          Rate range 0~1000000.
         Default value 128 pps."
  DEFVAL { 128 }
    ::= { cputrafficLimitReasonRate 5 }

erpsReasonRate         OBJECT-TYPE
    SYNTAX          INTEGER (0..1000000)
    MAX-ACCESS      read-write
    STATUS          current
    DESCRIPTION
        " Ethernet Ring Protection Switching.
          Rate range 0~1000000.
         Default value 128 pps."
  DEFVAL { 128 }
    ::= { cputrafficLimitReasonRate 6 }

sflowIngressReasonRate         OBJECT-TYPE
    SYNTAX          INTEGER (0..1000000)
    MAX-ACCESS      read-write
    STATUS          current
    DESCRIPTION
        " Sampled flow at ingress direction.
          Rate range 0~1000000.
         Default value 128 pps."
  DEFVAL { 128 }
    ::= { cputrafficLimitReasonRate 7 }

icmpRedirectReasonRate         OBJECT-TYPE
    SYNTAX          INTEGER (0..1000000)
    MAX-ACCESS      read-write
    STATUS          current
    DESCRIPTION
        " ICMP Redirect.
          Rate range 0~1000000.
         Default value 128 pps."
  DEFVAL { 128 }
    ::= { cputrafficLimitReasonRate 8 }

--icmpV6ReasonRate         OBJECT-TYPE
--    SYNTAX          INTEGER (1..1000000)
--    MAX-ACCESS      read-write
--    STATUS          current
--    DESCRIPTION
--        " Internet Control Message Protocol Version 6.
--          Rate range 0~1000000.
--         Default value 500 kbps."
--  DEFVAL { 500 }
--    ::= { cputrafficLimitReasonRate 9 }

igmpReasonRate         OBJECT-TYPE
    SYNTAX          INTEGER (0..1000000)
    MAX-ACCESS      read-write
    STATUS          current
    DESCRIPTION
        " IGMP/IGMP Snooping Protocol.
          Rate range 0~1000000.
         Default value 128 pps."
  DEFVAL { 128 }
    ::= { cputrafficLimitReasonRate 9 }

ipOptionReasonRate         OBJECT-TYPE
    SYNTAX          INTEGER (1..1000000)
    MAX-ACCESS      read-write
    STATUS          current
    DESCRIPTION
        " Packets with IP Option.
          Rate range 0~1000000.
         Default value 512 pps."
  DEFVAL { 512 }
    ::= { cputrafficLimitReasonRate 10 }

ipDaReasonRate         OBJECT-TYPE
    SYNTAX          INTEGER (0..1000000)
    MAX-ACCESS      read-write
    STATUS          current
    DESCRIPTION
        " IP Destination to Router-self.
          Rate range 0~1000000.
         Default value 1024 pps."
  DEFVAL { 1024 }
    ::= { cputrafficLimitReasonRate 11 }

ldpReasonRate         OBJECT-TYPE
    SYNTAX          INTEGER (0..1000000)
    MAX-ACCESS      read-write
    STATUS          current
    DESCRIPTION
        " Label Distribution Protocol.
          Rate range 0~1000000.
         Default value 512 pps."
  DEFVAL { 512 }
    ::= { cputrafficLimitReasonRate 12 }

macSaMismatchReasonRate         OBJECT-TYPE
    SYNTAX          INTEGER (0..1000000)
    MAX-ACCESS      read-write
    STATUS          current
    DESCRIPTION
        " Port Security for source mac learned.
          Rate range 0~1000000.
         Default value 128 pps."
  DEFVAL { 128 }
    ::= { cputrafficLimitReasonRate 13 }

mcastRpfFailReasonRate         OBJECT-TYPE
    SYNTAX          INTEGER (0..1000000)
    MAX-ACCESS      read-write
    STATUS          current
    DESCRIPTION
        " Multicast with rpf fail or first multicast packet.
          Rate range 0~1000000.
         Default value 128 pps."
  DEFVAL { 128 }
    ::= { cputrafficLimitReasonRate 14 }

mplsTtlFailReasonRate         OBJECT-TYPE
    SYNTAX          INTEGER (0..1000000)
    MAX-ACCESS      read-write
    STATUS          current
    DESCRIPTION
        " Mpls Packets with ttl fail.
          Rate range 0~1000000.
         Default value 64 pps."
  DEFVAL { 64 }
    ::= { cputrafficLimitReasonRate 15 }

mtuDontFragReasonRate         OBJECT-TYPE
    SYNTAX          INTEGER (0..1000000)
    MAX-ACCESS      read-write
    STATUS          current
    DESCRIPTION
        " Fragment with Flag dont-frag Set.
          Rate range 0~1000000.
         Default value 64 pps."
  DEFVAL { 64 }
    ::= { cputrafficLimitReasonRate 16 }

mtuFragReasonRate         OBJECT-TYPE
    SYNTAX          INTEGER (0..1000000)
    MAX-ACCESS      read-write
    STATUS          current
    DESCRIPTION
        " Need Fragment.
          Rate range 0~1000000.
         Default value 64 pps."
  DEFVAL { 64 }
    ::= { cputrafficLimitReasonRate 17 }

ospfReasonRate         OBJECT-TYPE
    SYNTAX          INTEGER (0..1000000)
    MAX-ACCESS      read-write
    STATUS          current
    DESCRIPTION
        " Open Shortest Path First.
          Rate range 0~1000000.
         Default value 256 pps."
  DEFVAL { 256 }
    ::= { cputrafficLimitReasonRate 18 }

pimReasonRate         OBJECT-TYPE
    SYNTAX          INTEGER (0..1000000)
    MAX-ACCESS      read-write
    STATUS          current
    DESCRIPTION
        " Protocol Independent Multicast.
          Rate range 0~1000000.
         Default value 128 pps."
  DEFVAL { 128 }
    ::= { cputrafficLimitReasonRate 19 }

portSecurityDiscardReasonRate         OBJECT-TYPE
    SYNTAX          INTEGER (0..1000000)
    MAX-ACCESS      read-write
    STATUS          current
    DESCRIPTION
        " Port Security for exceeding fdb maxnum.
          Rate range 0~1000000.
         Default value 128 pps."
  DEFVAL { 128 }
    ::= { cputrafficLimitReasonRate 20 }

ptpReasonRate         OBJECT-TYPE
    SYNTAX          INTEGER (1..1000000)
    MAX-ACCESS      read-write
    STATUS          current
    DESCRIPTION
        " Precision Time Synchronization Protocol.
          Rate range 0~1000000.
         Default value 512 pps."
  DEFVAL { 512 }
    ::= { cputrafficLimitReasonRate 21 }

ripReasonRate         OBJECT-TYPE
    SYNTAX          INTEGER (0..1000000)
    MAX-ACCESS      read-write
    STATUS          current
    DESCRIPTION
        " Routing Information Protocol.
          Rate range 0~1000000.
         Default value 64 pps."
  DEFVAL { 64 }
    ::= { cputrafficLimitReasonRate 22 }

rsvpReasonRate         OBJECT-TYPE
    SYNTAX          INTEGER (1..1000000)
    MAX-ACCESS      read-write
    STATUS          current
    DESCRIPTION
        " Resource Reservation Protocol.
          Rate range 0~1000000.
         Default value 512 pps."
  DEFVAL { 512 }
    ::= { cputrafficLimitReasonRate 23 }

slowProtoReasonRate         OBJECT-TYPE
    SYNTAX          INTEGER (0..1000000)
    MAX-ACCESS      read-write
    STATUS          current
    DESCRIPTION
        " Slow Protocol.
          Rate range 0~1000000.
         Default value 128 pps."
  DEFVAL { 128 }
    ::= { cputrafficLimitReasonRate 24 }

smartLinkReasonRate         OBJECT-TYPE
    SYNTAX          INTEGER (0..1000000)
    MAX-ACCESS      read-write
    STATUS          current
    DESCRIPTION
        " Smart Link Protocol.
          Rate range 0~1000000.
         Default value 128 pps."
  DEFVAL { 128 }
    ::= { cputrafficLimitReasonRate 25 }

ucastIpTtlFailReasonRate         OBJECT-TYPE
    SYNTAX          INTEGER (0..1000000)
    MAX-ACCESS      read-write
    STATUS          current
    DESCRIPTION
        " Unicast Packets with ttl fail.
          Rate range 0~1000000.
         Default value 64 pps."
  DEFVAL { 64 }
    ::= { cputrafficLimitReasonRate 26 }

vlanSecurityDiscardReasonRate         OBJECT-TYPE
    SYNTAX          INTEGER (1..1000000)
    MAX-ACCESS      read-write
    STATUS          current
    DESCRIPTION
        " Vlan Security for exceeding fdb maxnum.
          Rate range 0~1000000.
         Default value 128 pps."
  DEFVAL { 128 }
    ::= { cputrafficLimitReasonRate 27 }

vrrpReasonRate         OBJECT-TYPE
    SYNTAX          INTEGER (1..1000000)
    MAX-ACCESS      read-write
    STATUS          current
    DESCRIPTION
        " Virtual Router Redundancy Protocol.
          Rate range 0~1000000.
         Default value 512 pps."
  DEFVAL { 512 }
    ::= { cputrafficLimitReasonRate 28 }
    
mldReasonRate         OBJECT-TYPE
    SYNTAX          INTEGER (1..1000000)
    MAX-ACCESS      read-write
    STATUS          current
    DESCRIPTION
        " MLD/MLD Snooping Protocol.
          Rate range 0~1000000.
         Default value 128 pps."
  DEFVAL { 128 }
    ::= { cputrafficLimitReasonRate 29 }
    
sflowEgressReasonRate         OBJECT-TYPE
    SYNTAX          INTEGER (1..1000000)
    MAX-ACCESS      read-write
    STATUS          current
    DESCRIPTION
        " Sampled flow at egress direction.
          Rate range 0~1000000.
         Default value 128 pps."
  DEFVAL { 128 }
    ::= { cputrafficLimitReasonRate 30 }
    
udldReasonRate         OBJECT-TYPE
    SYNTAX          INTEGER (1..1000000)
    MAX-ACCESS      read-write
    STATUS          current
    DESCRIPTION
        " Unidirectional Link Detection Protocol.
          Rate range 0~1000000.
         Default value 128 pps."
  DEFVAL { 128 }
    ::= { cputrafficLimitReasonRate 31 }
    

fwdToCpuReasonRate         OBJECT-TYPE
    SYNTAX          INTEGER (1..1000000)
    MAX-ACCESS      read-write
    STATUS          current
    DESCRIPTION
        " Packets forwarding to cpu.
          Rate range 0~1000000.
         Default value 64 pps."
  DEFVAL { 64 }
    ::= { cputrafficLimitReasonRate 32 }

mplsTpPwOamReasonRate         OBJECT-TYPE
    SYNTAX          INTEGER (1..1000000)
    MAX-ACCESS      read-write
    STATUS          current
    DESCRIPTION
        "  MPLS-TP-OAM for PW.
          Rate range 0~1000000.
        	Default value 128 pps."
		DEFVAL { 128 }
    ::= { cputrafficLimitReasonRate 33 } 

dot1xMacBypassReasonRate         OBJECT-TYPE
    SYNTAX          INTEGER (1..1000000)
    MAX-ACCESS      read-write
    STATUS          current
    DESCRIPTION
        " Dot1x Mac Auth Bypass.
          Rate range 0~1000000.
        	Default value 64 pps."
		DEFVAL { 64 }
    ::= { cputrafficLimitReasonRate 34 } 

cputrafficLimitReasonClass OBJECT IDENTIFIER    ::= { cputraffic 3 }



arpReasonClass         OBJECT-TYPE
    SYNTAX          INTEGER (0..3)
    MAX-ACCESS      read-write
    STATUS          current
    DESCRIPTION
        " Address Resolution Protocol.
         Class range 0~3.
         Default Class is 1 ."
  DEFVAL { 1 }
    ::= { cputrafficLimitReasonClass 1 }

bpduReasonClass         OBJECT-TYPE
    SYNTAX          INTEGER (0..3)
    MAX-ACCESS      read-write
    STATUS          current
    DESCRIPTION
        " Bridge Protocol Data Unit.
         Class range 0~3.
         Default Class is 3 "
  DEFVAL { 3 }
    ::= { cputrafficLimitReasonClass 2 }

cfmReasonClass         OBJECT-TYPE
    SYNTAX          INTEGER (0..3)
    MAX-ACCESS      read-write
    STATUS          current
    DESCRIPTION
        " Connectivity Fault Management.
         Class range 0~3.
         Default Class is 2. "
  DEFVAL { 2 }
    ::= { cputrafficLimitReasonClass 3 }

dhcpReasonClass         OBJECT-TYPE
    SYNTAX          INTEGER (0..3)
    MAX-ACCESS      read-write
    STATUS          current
    DESCRIPTION
        " Dynamic Host Configuration Protocol.
         Class range 0~3.
         Default Class is 0. "
  DEFVAL { 0 }
    ::= { cputrafficLimitReasonClass 4 }

eapolReasonClass         OBJECT-TYPE
    SYNTAX          INTEGER (0..3)
    MAX-ACCESS      read-write
    STATUS          current
    DESCRIPTION
        " Extensible Authentication Protocol Over Lan.
         Class range 0~3.
         Default Class is 0. "
  DEFVAL { 0 }
    ::= { cputrafficLimitReasonClass 5 }

erpsReasonClass         OBJECT-TYPE
    SYNTAX          INTEGER (0..3)
    MAX-ACCESS      read-write
    STATUS          current
    DESCRIPTION
        " Ethernet Ring Protection Switching.
         Class range 0~3.
         Default Class is 2. "
  DEFVAL { 2 }
    ::= { cputrafficLimitReasonClass 6 }

sflowIngressReasonClass         OBJECT-TYPE
    SYNTAX          INTEGER (0..3)
    MAX-ACCESS      read-write
    STATUS          current
    DESCRIPTION
        " Sampled flow at ingress direction.
         Class range 0~3.
         Default Class is 0. "
  DEFVAL { 0 }
    ::= { cputrafficLimitReasonClass 7 }

icmpRedirectReasonClass         OBJECT-TYPE
    SYNTAX          INTEGER (0..3)
    MAX-ACCESS      read-write
    STATUS          current
    DESCRIPTION
        " ICMP Redirect.
         Class range 0~3.
         Default Class is 0. "
  DEFVAL { 0 }
    ::= { cputrafficLimitReasonClass 8 }

--icmpV6ReasonClass         OBJECT-TYPE
--    SYNTAX          INTEGER (0..3)
--    MAX-ACCESS      read-write
--    STATUS          current
--    DESCRIPTION
--        " Internet Control Message Protocol Version 6.
--         Class range 0~3.
--         Default Class is 1. "
--  DEFVAL { 1 }
--    ::= { cputrafficLimitReasonClass 9 }

igmpReasonClass         OBJECT-TYPE
    SYNTAX          INTEGER (0..3)
    MAX-ACCESS      read-write
    STATUS          current
    DESCRIPTION
        " IGMP/IGMP Snooping Protocol.
         Class range 0~3.
         Default Class is 2. "
  DEFVAL { 2 }
    ::= { cputrafficLimitReasonClass 9 }

ipOptionReasonClass         OBJECT-TYPE
    SYNTAX          INTEGER (0..3)
    MAX-ACCESS      read-write
    STATUS          current
    DESCRIPTION
        " Packets with IP Option.
         Class range 0~3.
         Default Class is 0. "
  DEFVAL { 0 }
    ::= { cputrafficLimitReasonClass 10 }

ipDaReasonClass         OBJECT-TYPE
    SYNTAX          INTEGER (0..3)
    MAX-ACCESS      read-write
    STATUS          current
    DESCRIPTION
        " IP Destination to Router-self.
         Class range 0~3.
         Default Class is 0. "
  DEFVAL { 0 }
    ::= { cputrafficLimitReasonClass 11 }

ldpReasonClass         OBJECT-TYPE
    SYNTAX          INTEGER (0..3)
    MAX-ACCESS      read-write
    STATUS          current
    DESCRIPTION
        " Label Distribution Protocol.
         Class range 0~3.
         Default Class is 1. "
  DEFVAL { 1 }
    ::= { cputrafficLimitReasonClass 12 }

macSaMismatchReasonClass         OBJECT-TYPE
    SYNTAX          INTEGER (0..3)
    MAX-ACCESS      read-write
    STATUS          current
    DESCRIPTION
        " Port Security for source mac learned.
         Class range 0~3.
         Default Class is 0. "
  DEFVAL { 0 }
    ::= { cputrafficLimitReasonClass 13 }

mcastRpfFailReasonClass         OBJECT-TYPE
    SYNTAX          INTEGER (0..3)
    MAX-ACCESS      read-write
    STATUS          current
    DESCRIPTION
        " Multicast with rpf fail or first multicast packet.
         Class range 0~3.
         Default Class is 1. "
  DEFVAL { 1 }
    ::= { cputrafficLimitReasonClass 14 }

--mcastTtlReasonClass         OBJECT-TYPE
--    SYNTAX          INTEGER (0..3)
--    MAX-ACCESS      read-write
--    STATUS          current
--    DESCRIPTION
--        " Multicast Packets with ttl fail.
--         Class range 0~3.
--         Default Class is 0. "
--  DEFVAL { 0 }
--    ::= { cputrafficLimitReasonClass 15 }

mplsTtlFailReasonClass         OBJECT-TYPE
    SYNTAX          INTEGER (0..3)
    MAX-ACCESS      read-write
    STATUS          current
    DESCRIPTION
        " Mpls Packets with ttl fail.
         Class range 0~3.
         Default Class is 0. "
  DEFVAL { 0 }
    ::= { cputrafficLimitReasonClass 15 }

mtuDontFragReasonClass         OBJECT-TYPE
    SYNTAX          INTEGER (0..3)
    MAX-ACCESS      read-write
    STATUS          current
    DESCRIPTION
        " Fragment with Flag dont-frag Set.
         Class range 0~3.
         Default Class is 0. "
  DEFVAL { 0 }
    ::= { cputrafficLimitReasonClass 16 }

mtuFragReasonClass         OBJECT-TYPE
    SYNTAX          INTEGER (0..3)
    MAX-ACCESS      read-write
    STATUS          current
    DESCRIPTION
        " Need Fragment.
         Class range 0~3.
         Default Class is 0. "
  DEFVAL { 0 }
    ::= { cputrafficLimitReasonClass 17 }

ospfReasonClass         OBJECT-TYPE
    SYNTAX          INTEGER (0..3)
    MAX-ACCESS      read-write
    STATUS          current
    DESCRIPTION
        " Open Shortest Path First.
         Class range 0~3.
         Default Class is 1. "
  DEFVAL { 1 }
    ::= { cputrafficLimitReasonClass 18 }

pimReasonClass         OBJECT-TYPE
    SYNTAX          INTEGER (0..3)
    MAX-ACCESS      read-write
    STATUS          current
    DESCRIPTION
        " Protocol Independent Multicast.
         Class range 0~3.
         Default Class is 1. "
  DEFVAL { 1 }
    ::= { cputrafficLimitReasonClass 19 }

portSecurityDiscardReasonClass         OBJECT-TYPE
    SYNTAX          INTEGER (0..3)
    MAX-ACCESS      read-write
    STATUS          current
    DESCRIPTION
        " Port Security for exceeding fdb maxnum.
         Class range 0~3.
         Default Class is 0. "
  DEFVAL { 0 }
    ::= { cputrafficLimitReasonClass 20 }

ptpReasonClass         OBJECT-TYPE
    SYNTAX          INTEGER (0..3)
    MAX-ACCESS      read-write
    STATUS          current
    DESCRIPTION
        " Precision Time Synchronization Protocol.
         Class range 0~3.
         Default Class is 2. "
  DEFVAL { 2 }
    ::= { cputrafficLimitReasonClass 21 }

ripReasonClass         OBJECT-TYPE
    SYNTAX          INTEGER (0..3)
    MAX-ACCESS      read-write
    STATUS          current
    DESCRIPTION
        " Routing Information Protocol.
         Class range 0~3.
         Default Class is 1. "
  DEFVAL { 1 }
    ::= { cputrafficLimitReasonClass 22 }

rsvpReasonClass         OBJECT-TYPE
    SYNTAX          INTEGER (0..3)
    MAX-ACCESS      read-write
    STATUS          current
    DESCRIPTION
        " Resource Reservation Protocol.
         Class range 0~3.
         Default Class is 1. "
  DEFVAL { 1 }
    ::= { cputrafficLimitReasonClass 23 }

slowProtoReasonClass         OBJECT-TYPE
    SYNTAX          INTEGER (0..3)
    MAX-ACCESS      read-write
    STATUS          current
    DESCRIPTION
        " Slow Protocol.
         Class range 0~3.
         Default Class is 1. "
  DEFVAL { 1 }
    ::= { cputrafficLimitReasonClass 24 }

smartLinkReasonClass         OBJECT-TYPE
    SYNTAX          INTEGER (0..3)
    MAX-ACCESS      read-write
    STATUS          current
    DESCRIPTION
        " Smart Link Protocol.
         Class range 0~3.
         Default Class is 2. "
  DEFVAL { 2 }
    ::= { cputrafficLimitReasonClass 25 }

ucastIpTtlFailReasonClass         OBJECT-TYPE
    SYNTAX          INTEGER (0..3)
    MAX-ACCESS      read-write
    STATUS          current
    DESCRIPTION
        " Unicast Packets with ttl fail.
         Class range 0~3.
         Default Class is 0. "
  DEFVAL { 0 }
    ::= { cputrafficLimitReasonClass 26 }

vlanSecurityDiscardReasonClass         OBJECT-TYPE
    SYNTAX          INTEGER (0..3)
    MAX-ACCESS      read-write
    STATUS          current
    DESCRIPTION
        " Vlan Security for exceeding fdb maxnum.
         Class range 0~3.
         Default Class is 0. "
  DEFVAL { 0 }
    ::= { cputrafficLimitReasonClass 27 }

vrrpReasonClass         OBJECT-TYPE
    SYNTAX          INTEGER (0..3)
    MAX-ACCESS      read-write
    STATUS          current
    DESCRIPTION
        " Virtual Router Redundancy Protocol.
         Class range 0~3.
         Default Class is 1. "
  DEFVAL { 1 }
    ::= { cputrafficLimitReasonClass 28 }

mldReasonClass         OBJECT-TYPE
    SYNTAX          INTEGER (0..3)
    MAX-ACCESS      read-write
    STATUS          current
    DESCRIPTION
        " MLD/MLD Snooping Protocol.
         Class range 0~3.
         Default Class is 2. "
  DEFVAL { 2 }
    ::= { cputrafficLimitReasonClass 29 }
    

sflowEgressReasonClass       OBJECT-TYPE
    SYNTAX          INTEGER (0..3)
    MAX-ACCESS      read-write
    STATUS          current
    DESCRIPTION
        " Sampled flow at egress direction.
         Class range 0~3.
         Default Class is 0. "
  DEFVAL { 0 }
    ::= { cputrafficLimitReasonClass 30 }

udldReasonClass         OBJECT-TYPE
    SYNTAX          INTEGER (0..3)
    MAX-ACCESS      read-write
    STATUS          current
    DESCRIPTION
        " Sampled flow at egress direction.
         Class range 0~3.
         Default Class is 3. "
  DEFVAL { 3 }
    ::= { cputrafficLimitReasonClass 31 }

mplsTpPwOamReasonClass         OBJECT-TYPE
    SYNTAX          INTEGER (0..3)
    MAX-ACCESS      read-write
    STATUS          current
    DESCRIPTION
        " MPLS-TP-OAM for PW.
        	Class range 0~3.
        	Default Class is 2. "
		DEFVAL { 2 }
    ::= { cputrafficLimitReasonClass 33 } 

dot1xMacBypassReasonClass         OBJECT-TYPE
    SYNTAX          INTEGER (0..3)
    MAX-ACCESS      read-write
    STATUS          current
    DESCRIPTION
        " Dot1x Mac Auth Bypass.
        	Class range 0~3.
        	Default Class is 2. "
		DEFVAL { 2 }
    ::= { cputrafficLimitReasonClass 34 } 

-- Sub Module: PORT-ISOLATE
-- portisolate               OBJECT IDENTIFIER ::= { OID 73 }
--
-- Node definitions
--

portIsolateMode     OBJECT-TYPE
    SYNTAX          INTEGER {l2(1),all(2)}
    MAX-ACCESS      read-write
    STATUS          current
    DESCRIPTION
        "Set isolate mode on the switch The default setting is l2.
        The meanings of the values are:
        l2(1)  -  Isolate bridged packets;
        all(2) -  Isolate bridged packtes and routed packets;"
  DEFVAL { all }
    ::= { portisolate 1 }

-- Sub Module: PHY-LOOKBACK

-- phyloopback                 OBJECT IDENTIFIER ::= { OID 74 }

--
-- Node definitions
--

-- phyloopbackTable


phyloopbackTable     OBJECT-TYPE
    SYNTAX          SEQUENCE OF PhyloopbackEntry
    MAX-ACCESS      not-accessible
    STATUS          current
    DESCRIPTION
        "A table that contains phy-loopback internal group information."
    ::= { phyloopback 1 }

phyloopbackEntry     OBJECT-TYPE
    SYNTAX          PhyloopbackEntry
    MAX-ACCESS      not-accessible
    STATUS          current
    DESCRIPTION
        "A list of phy-loopback internal group information "
    INDEX     { phyloopbackIfindex  }
    ::= { phyloopbackTable 1 }

PhyloopbackEntry    ::=
    SEQUENCE
    {
       phyloopbackIfindex
           INTEGER,
       phyloopbackType
           INTEGER,
       phyloopbackDstIfindex
           INTEGER,
       phyloopbackMacAddrSwap
           INTEGER,
       phyloopbackRowStatus
           RowStatus
    }

phyloopbackIfindex         OBJECT-TYPE
    SYNTAX          INTEGER (1..52)
    MAX-ACCESS      not-accessible
    STATUS          current
    DESCRIPTION
        "An index of interface that uniquely identifies an phyloopback entry in the phyloopback table."
    ::= { phyloopbackEntry 1 }

phyloopbackType         OBJECT-TYPE
    SYNTAX          INTEGER {internal(0), external(1), port(2)}
    MAX-ACCESS      read-write
    STATUS          current
    DESCRIPTION
        "Phy loopback commands type. internal(0), external(1), port(2). "
    ::= { phyloopbackEntry 2 }

phyloopbackDstIfindex         OBJECT-TYPE
    SYNTAX          INTEGER (1..52)
    MAX-ACCESS      read-write
    STATUS          current
    DESCRIPTION
        "An index that uniquely identifies phyloopback destination physical interface."
    ::= { phyloopbackEntry 3 }

phyloopbackMacAddrSwap         OBJECT-TYPE
    SYNTAX          INTEGER {enable(1), disable(2)}
    MAX-ACCESS      read-write
    STATUS          current
    DESCRIPTION
        "The packet's SMAC incoming from port level loopback interface will be swaped with it's DMAC, 
        and the FCS will be updated. enable(1), disable(2). Default setting is disable(2). 
        For other types, should always be disable(2)."
    ::= { phyloopbackEntry 4 }

phyloopbackRowStatus         OBJECT-TYPE
  SYNTAX          RowStatus
  MAX-ACCESS      read-create
  STATUS          current
  DESCRIPTION
      "The status of this conceptual row.Now only realize CreateAndGo(4) and Destroy(6) and Active(1)."
  ::= { phyloopbackEntry 5 }


-- Sub Module: Monitor link
monitorLinkRecoverTime      OBJECT-TYPE
    SYNTAX                  Integer32 (3..60)
    MAX-ACCESS              read-write
    STATUS                  current
    DESCRIPTION
        "Set the recover time for down_link port, when the up_link up."
    DEFVAL                  { 3 }
    ::= { monitorlink 1 }

monitorLinkGroupTable         OBJECT-TYPE
    SYNTAX                    SEQUENCE OF MonitorLinkGroupEntry
    MAX-ACCESS                not-accessible
    STATUS                    current
    DESCRIPTION
        "The table of Monitor link group."
    ::= { monitorlink 2 }

monitorLinkGroupEntry         OBJECT-TYPE
    SYNTAX                    MonitorLinkGroupEntry
    MAX-ACCESS                not-accessible
    STATUS                    current
    DESCRIPTION
        "The entry of Monitor link group."
    INDEX     { groupIndex}
    ::= { monitorLinkGroupTable 1 }

MonitorLinkGroupEntry    ::=
    SEQUENCE
    {
        groupIndex
            Integer32,
        groupStatus
            INTEGER,
        groupRowStatus
            RowStatus
    }

groupIndex          OBJECT-TYPE
    SYNTAX          Integer32 (0..15)
    MAX-ACCESS      not-accessible
    STATUS          current
    DESCRIPTION
        "The index of Monitor link group. The index value is group id minus 1."
    ::= { monitorLinkGroupEntry 1 }

groupStatus        OBJECT-TYPE
    SYNTAX          INTEGER {up(1), down(2), idle(3)}
    MAX-ACCESS      read-only
    STATUS          current
    DESCRIPTION
        "The current status of group."
    ::= { monitorLinkGroupEntry 2 }

groupRowStatus      OBJECT-TYPE
    SYNTAX          RowStatus
    MAX-ACCESS      read-create
    STATUS          current
    DESCRIPTION
        "The status of this conceptual row. Now only realize Destroy and Active."
    ::= { monitorLinkGroupEntry 3 }


monitorLinkMemberTable        OBJECT-TYPE
    SYNTAX                    SEQUENCE OF MonitorLinkMemberEntry
    MAX-ACCESS                not-accessible
    STATUS                    current
    DESCRIPTION
        "The table of Monitor link member."
    ::= { monitorlink 3 }

monitorLinkMemberEntry        OBJECT-TYPE
    SYNTAX                    MonitorLinkMemberEntry
    MAX-ACCESS                not-accessible
    STATUS                    current
    DESCRIPTION
        "The entry of Monitor link member."
    INDEX     { groupIndex, memberLinkType, memberIndex}
    ::= { monitorLinkMemberTable 1 }

MonitorLinkMemberEntry    ::=
    SEQUENCE
    {
        memberLinkType
            INTEGER,
        memberIndex
            Integer32,
        memberType
            INTEGER,
        memberIdentify
            Integer32,
        memberUptime
            TimeTicks,
        memberDowntime
            TimeTicks,
        memberUpCounter
            Counter32,
        memberDownCounter
            Counter32,
        memberRowStatus
            RowStatus
    }
memberLinkType      OBJECT-TYPE
    SYNTAX          INTEGER {up-link(0), down-link(1)}
    MAX-ACCESS      not-accessible
    STATUS          current
    DESCRIPTION
        "The type of Monitor link member."
    ::= { monitorLinkMemberEntry 1 }

memberIndex         OBJECT-TYPE
    SYNTAX          Integer32 (0..15)
    MAX-ACCESS      not-accessible
    STATUS          current
    DESCRIPTION
        "The index of Monitor link member."
    ::= { monitorLinkMemberEntry 2 }

memberType          OBJECT-TYPE
    SYNTAX          INTEGER {smart-link(0), interface(1)}
    MAX-ACCESS      read-create
    STATUS          current
    DESCRIPTION
        "The type of Monitor link member. Type of smart-link can only used as up-link."
    ::= { monitorLinkMemberEntry 3 }

memberIdentify      OBJECT-TYPE
    SYNTAX          Integer32 (0..65536)
    MAX-ACCESS      read-create
    STATUS          current
    DESCRIPTION
        "If the memberType type is interface, this value should be ifindex.
         if the memberType type is smart-link, this value should be smartlinkGroupindex."
    ::= { monitorLinkMemberEntry 4 }

memberUptime        OBJECT-TYPE
    SYNTAX          TimeTicks
    MAX-ACCESS      read-only
    STATUS          current
    DESCRIPTION
        "The last-up-time of member."
    ::= { monitorLinkMemberEntry 5 }

memberDowntime      OBJECT-TYPE
    SYNTAX          TimeTicks
    MAX-ACCESS      read-only
    STATUS          current
    DESCRIPTION
        "The last-down-time of member."
    ::= { monitorLinkMemberEntry 6 }

memberUpCounter     OBJECT-TYPE
    SYNTAX          Counter32
    MAX-ACCESS      read-only
    STATUS          current
    DESCRIPTION
        "The counter of up time of the member."
    ::= { monitorLinkMemberEntry 7 }

memberDownCounter   OBJECT-TYPE
    SYNTAX          Counter32
    MAX-ACCESS      read-only
    STATUS          current
    DESCRIPTION
        "TThe counter of down time of the member."
    ::= { monitorLinkMemberEntry 8 }

memberRowStatus     OBJECT-TYPE
    SYNTAX          RowStatus
    MAX-ACCESS      read-create
    STATUS          current
    DESCRIPTION
        "The status of this conceptual row. Now only realize Destroy and Active."
    ::= { monitorLinkMemberEntry 9 }

-- Sub Module: UDLD
-- udld               OBJECT IDENTIFIER ::= { OID 76 }
--
-- Node definitions
--

udldGlobalState     OBJECT-TYPE
    SYNTAX          INTEGER {enable(1),disable(2)}
    MAX-ACCESS      read-write
    STATUS          current
    DESCRIPTION
        "Set UDLD global state.The meanings of the values are:
        enable(1)  -  Globally enable UDLD;
        disable(2) -  Globally disable UDLD;"
    DEFVAL { disable }
    ::= { udld 1 }

udldMsgInterval     OBJECT-TYPE
    SYNTAX          INTEGER (1..90)
    MAX-ACCESS      read-write
    STATUS          current
    DESCRIPTION
        "Set UDLD message interval.The default value is 15 seconds."
    DEFVAL { 15 }
    ::= { udld 2 }

udldOperate         OBJECT-TYPE
    SYNTAX          INTEGER {reset(1)}
    MAX-ACCESS      read-write
    STATUS          current
    DESCRIPTION
        "UDLD global operations.The meanings of the values are:
        reset(1) -  Reset the interfaces disabled by UDLD;"
    ::= { udld 3 }

udldIfTable         OBJECT-TYPE
    SYNTAX          SEQUENCE OF UDLDIfEntry
    MAX-ACCESS      not-accessible
    STATUS          current
    DESCRIPTION
        "A table that contains UDLD interface information."
    ::= { udld 4  }

udldIfEntry         OBJECT-TYPE
    SYNTAX          UDLDIfEntry
    MAX-ACCESS      not-accessible
    STATUS          current
    DESCRIPTION
        "A list of UDLD interface information "
    INDEX     { udldIfIndex  }
    ::= { udldIfTable 1 }

UDLDIfEntry    ::=
    SEQUENCE
    {
        udldIfIndex
            Integer32,
        udldIfName
            OCTET STRING,
        udldState
            INTEGER,
        udldLinkState
            INTEGER
     }

udldIfIndex         OBJECT-TYPE
    SYNTAX          Integer32 (0..65535)
    MAX-ACCESS      not-accessible
    STATUS          current
    DESCRIPTION     "Interface index."
    ::= { udldIfEntry 1 }

udldIfName          OBJECT-TYPE
    SYNTAX          OCTET STRING (SIZE (1..16))
    MAX-ACCESS      read-only
    STATUS          current
    DESCRIPTION     "Interface name."
    ::= { udldIfEntry 2 }

udldState           OBJECT-TYPE
    SYNTAX          INTEGER {disable(1),normal(2),aggressive(3)}
    MAX-ACCESS      read-create
    STATUS          current
    DESCRIPTION     "UDLD state of an interface.The meanings of the values are:
        disable(0)    -  Disable UDLD;
        normal(1)     -  Enable UDLD normal mode;
        aggressive(2) -  Enable UDLD aggressive mode;"
    DEFVAL { disable }
    ::= { udldIfEntry 3 }

udldLinkState       OBJECT-TYPE
    SYNTAX          INTEGER {linkUp(0),unknown(1),detection(2),exDetection(3),bidirectional(4),unidirectional(5),selfLoop(7),linkdown(8),inActive(9)}
    MAX-ACCESS      read-only
    STATUS          current
    DESCRIPTION     "UDLD operation state of an interface."
    ::= { udldIfEntry 4 }

-- Sub Module: POLICYBASEDROUTING

--
-- Nodes of policyBaseRoutingIpPolicyRouteMap entry table
--
pbrTable   OBJECT-TYPE
    SYNTAX          SEQUENCE OF PBREntry
    MAX-ACCESS      not-accessible
    STATUS          current
    DESCRIPTION
        "table of Policy based routing entry."
    ::= { policyBasedRouting 1 }

pbrEntry   OBJECT-TYPE
    SYNTAX          PBREntry
    MAX-ACCESS      not-accessible
    STATUS          current
    DESCRIPTION
        "Policy based routing entry"
    INDEX     { pbrIfIndex}
    ::= { pbrTable 1 }

PBREntry    ::=
    SEQUENCE
    {
        pbrIfIndex
            Integer32,
        pbrPolicyRmapName
            OCTET STRING,
		pbrRowStatus
            RowStatus
    }

pbrIfIndex	OBJECT-TYPE
    SYNTAX          Integer32 (0..65535)
    MAX-ACCESS      not-accessible
    STATUS          current
    DESCRIPTION        
        "interface index which is applying the policy route-map."
    ::= { pbrEntry 1 }
            
pbrPolicyRmapName	OBJECT-TYPE
    SYNTAX          OCTET STRING (SIZE (1..20))
    MAX-ACCESS      read-write
    STATUS          current
    DESCRIPTION        "pbr policy route-map name."
    ::= { pbrEntry 2 }

pbrRowStatus OBJECT-TYPE
    SYNTAX          RowStatus
    MAX-ACCESS      read-create
    STATUS          current
    DESCRIPTION
        "The status of this conceptual row.Now only realize CreateAndGo 
        and Destroy and Active.
        1 means Active
        4 means CreateAndGo
        6 means Destroy"
    ::= { pbrEntry 9}
    
-- Sub Module: DDOS prevent
-- ddos               OBJECT IDENTIFIER ::= { OID 78 }
--
-- Node definitions
--

ddosICMPIntercept     OBJECT-TYPE
    SYNTAX          Integer32 (-1|0..1000)
    MAX-ACCESS      read-write
    STATUS          current
    DESCRIPTION
        "Set Ip ICMP intercept maxcount.The meanings of the values are:
        -1  -  no Ip ICMP intercept;
        0-1000 -  Ip ICMP intercept maxcount."
    DEFVAL { -1 }
    ::= { ddos 1 }

ddosUDPIntercept     OBJECT-TYPE
    SYNTAX          Integer32 (-1|0..1000)
    MAX-ACCESS      read-write
    STATUS          current
    DESCRIPTION
        "Set Ip UDP intercept maxcount.The meanings of the values are:
        -1  -  no Ip UDP intercept;
        0-1000 -  Ip UDP intercept maxcount."
    DEFVAL { -1 }
    ::= { ddos 2 }

ddosTCPIntercept     OBJECT-TYPE
    SYNTAX          Integer32 (-1|0..1000)
    MAX-ACCESS      read-write
    STATUS          current
    DESCRIPTION
        "Set Ip TCP intercept maxcount.The meanings of the values are:
        -1  -  no Ip TCP intercept;
        0-1000 -  Ip TCP intercept maxcount."
    DEFVAL { -1 }
    ::= { ddos 3 }

ddosSmurfIntercept     OBJECT-TYPE
    SYNTAX          INTEGER {enable(1),disable(2)}
    MAX-ACCESS      read-write
    STATUS          current
    DESCRIPTION
        "Set Ip Smurf intercept maxcount.The meanings of the values are:
        enable(1)  -  Ip Fraggle intercept;
        disable(2) -  no Ip Fraggle intercept."
    DEFVAL { disable }
    ::= { ddos 4 }

ddosSmalpktIntercept     OBJECT-TYPE
    SYNTAX          Integer32 (-1|28..65535)
    MAX-ACCESS      read-write
    STATUS          current
    DESCRIPTION
        "Set Ip Small-packet intercept maxcount.The meanings of the values are:
        -1  -  no Ip Small-packet intercept;
        28-65535 -  Ip Small-packet intercept maxlength."
    DEFVAL { -1 }
    ::= { ddos 5 }

ddosFraggleIntercept     OBJECT-TYPE
    SYNTAX          INTEGER {enable(1),disable(2)}
    MAX-ACCESS      read-write
    STATUS          current
    DESCRIPTION
        "Set Ip Fraggle intercept.The meanings of the values are:
        enable(1)  -  Ip Fraggle intercept;
        disable(2) -  no Ip Fraggle intercept."
    DEFVAL { disable }
    ::= { ddos 6 }

ddosIpeqIntercept     OBJECT-TYPE
    SYNTAX          INTEGER {enable(1),disable(2)}
    MAX-ACCESS      read-write
    STATUS          current
    DESCRIPTION
        "Set Ip Ipeq intercept.The meanings of the values are:
        enable(1)  -  Ip Ipeq intercept;
        disable(2) -  no Ip Ipeq intercept."
    DEFVAL { disable }
    ::= { ddos 7 }

ddosMaceqIntercept     OBJECT-TYPE
    SYNTAX          INTEGER {enable(1),disable(2)}
    MAX-ACCESS      read-write
    STATUS          current
    DESCRIPTION
        "Set Ip Maceq intercept.The meanings of the values are:
        enable(1)  -  Ip Maceq intercept;
        disable(2) -  no Ip Maceq intercept."
    DEFVAL { disable }
    ::= { ddos 8 }

ddosSmalPktStatistic       OBJECT-TYPE
    SYNTAX          Counter32
    MAX-ACCESS      read-only
    STATUS          current
    DESCRIPTION
        "Show Resist Small-packet Attack packets number."
    DEFVAL { 0 }
    ::= { ddos 9 }

ddosICMPStatistic          OBJECT-TYPE
    SYNTAX          Counter32
    MAX-ACCESS      read-only
    STATUS          current
    DESCRIPTION
        "Show Resist ICMP Flood packets number."
    DEFVAL { 0 }
    ::= { ddos 10 }

ddosSmurfStatistic          OBJECT-TYPE
    SYNTAX          Counter32
    MAX-ACCESS      read-only
    STATUS          current
    DESCRIPTION
        "Show Resist Smurf Attack packets number."
    DEFVAL { 0 }
    ::= { ddos 11 }

ddosTCPStatistic          OBJECT-TYPE
    SYNTAX          Counter32
    MAX-ACCESS      read-only
    STATUS          current
    DESCRIPTION
        "Show Resist SYN Flood packets number."
    DEFVAL { 0 }
    ::= { ddos 12 }


ddosFraggleStatistic          OBJECT-TYPE
    SYNTAX          Counter32
    MAX-ACCESS      read-only
    STATUS          current
    DESCRIPTION
        "Show Resist Fraggle Attack packets number."
    DEFVAL { 0 }
    ::= { ddos 13 }

ddosUDPStatistic         OBJECT-TYPE
    SYNTAX          Counter32
    MAX-ACCESS      read-only
    STATUS          current
    DESCRIPTION
        "Show Resist UDP Flood packets number."
    DEFVAL { 0 }
    ::= { ddos 14 }

ddosClearStatistic        OBJECT-TYPE
    SYNTAX          INTEGER {clearStatistic(1)}
    MAX-ACCESS      read-write
    STATUS          current
    DESCRIPTION        "Clear IP intercept Statistic.1:clear statistic. "
    ::= { ddos 15 }

ddosmgifSmalPktStatistic       OBJECT-TYPE
    SYNTAX          Counter32
    MAX-ACCESS      read-only
    STATUS          current
    DESCRIPTION
        "Show Resist mgmt-if Small-packet Attack packets number."
    DEFVAL { 0 }
    ::= { ddos 16 }

ddosmgifICMPStatistic          OBJECT-TYPE
    SYNTAX          Counter32
    MAX-ACCESS      read-only
    STATUS          current
    DESCRIPTION
        "Show Resist mgmt-if ICMP Flood packets number."
    DEFVAL { 0 }
    ::= { ddos 17 }

ddosmgifSmurfStatistic          OBJECT-TYPE
    SYNTAX          Counter32
    MAX-ACCESS      read-only
    STATUS          current
    DESCRIPTION
        "Show Resist mgmt-if Smurf Attack packets number."
    DEFVAL { 0 }
    ::= { ddos 18 }

ddosmgifTCPStatistic          OBJECT-TYPE
    SYNTAX          Counter32
    MAX-ACCESS      read-only
    STATUS          current
    DESCRIPTION
        "Show Resist mgmt-if SYN Flood packets number."
    DEFVAL { 0 }
    ::= { ddos 19 }


ddosmgifFraggleStatistic          OBJECT-TYPE
    SYNTAX          Counter32
    MAX-ACCESS      read-only
    STATUS          current
    DESCRIPTION
        "Show Resist mgmt-if Fraggle Attack packets number."
    DEFVAL { 0 }
    ::= { ddos 20 }

ddosmgifUDPStatistic         OBJECT-TYPE
    SYNTAX          Counter32
    MAX-ACCESS      read-only
    STATUS          current
    DESCRIPTION
        "Show Resist mgmt-if UDP Flood packets number."
    DEFVAL { 0 }
    ::= { ddos 21 }

-- l2ping   OBJECT IDENTIFIER ::= { OID 79 }

l2PingResponseTable     OBJECT-TYPE
    SYNTAX          SEQUENCE OF L2PingResponseEntry
    MAX-ACCESS      not-accessible
    STATUS          current
    DESCRIPTION
        "A table that contains l2 ping response information."
    ::= { l2ping 1 }

l2PingResponseEntry     OBJECT-TYPE
    SYNTAX          L2PingResponseEntry
    MAX-ACCESS      not-accessible
    STATUS          current
    DESCRIPTION
        "A list of interface l2ping response information"
    INDEX     { l2pingResponseIfindex  }
    ::= { l2PingResponseTable 1 }

L2PingResponseEntry    ::=
    SEQUENCE
    {
       l2pingResponseIfindex
           INTEGER,
       l2pingResponseEnable
           INTEGER
    }

l2pingResponseIfindex         OBJECT-TYPE
    SYNTAX          INTEGER (1..1023)
    MAX-ACCESS      not-accessible
    STATUS          current
    DESCRIPTION
        "An index of interface that uniquely identifies an l2ping entry in the l2PingResponseTable table.
  interface should be physical l2 interface"
    ::= { l2PingResponseEntry 1 }

l2pingResponseEnable         OBJECT-TYPE
    SYNTAX          INTEGER {enable(1), disable(2)}
    MAX-ACCESS      read-write
    STATUS          current
    DESCRIPTION
        "L2 ping response enable(1), or disable(2).
         Default : disable(2)."
    DEFVAL {disable}
    ::= { l2PingResponseEntry 2 }


--ssm                       OBJECT IDENTIFIER ::= { OID 81 }

ssmDeviceClockID    OBJECT-TYPE
    SYNTAX          OCTET STRING (SIZE(0..256))
    MAX-ACCESS      read-only
    STATUS          current
    DESCRIPTION
        "A exclusive flag to distinguish every device"
    ::= { ssm 1 }

ssmSyncEGlbEnable    OBJECT-TYPE
    SYNTAX          INTEGER {enable(1), disable(2)}
    MAX-ACCESS      read-write
    STATUS          current
    DESCRIPTION
        "Set whether the device is a synchronous equipment.
        The meanings of the values are:
        enable(1)  -  A synchronous equipment;
        disable(2) -  Not a synchronous equipment"
    DEFVAL { disable }
    ::= { ssm 2 }

ssmGlbEnable    OBJECT-TYPE
    SYNTAX          INTEGER {enable(1), disable(2)}
    MAX-ACCESS      read-write
    STATUS          current
    DESCRIPTION
        "Set whether the device work under synchronous
        operation mode. The meanings of the values are:
        enable(1)  -  Under synchronous operation mode;
        disable(2) -  Under non-sync operation mode"
    DEFVAL { disable }
    ::= { ssm 3 }

ssmDeviceType    OBJECT-TYPE
    SYNTAX          INTEGER {master-only(1), slave-only(2), none(3)}
    MAX-ACCESS      read-write
    STATUS          current
    DESCRIPTION
        "Set the device type. The meanings of the values are:
        master-olny(1) -  master-only type;
        slave-only(2)  -  slave-only type;
        none(3)        -  default type"
    DEFVAL { none }
    ::= { ssm 4 }

ssmLocalQuality    OBJECT-TYPE
    SYNTAX          INTEGER {op2-prs(1), op1-prc(2), op2-eec2(3), op1-eec1(4),op1-dnu(5), op2-dus(6)}
    MAX-ACCESS      read-write
    STATUS          current
    DESCRIPTION
        "Set the device quality globally under option1.
        The meanings of the values are:
        op2-prs(1)  -  Primary reference source;
        op1-prc(2)  -  Primary reference clock;
        op2-eec2(3) -  EEC2 clock(ITU-T G.8264);
        op1-eec1(4) -  EEC1 clock(ITU-T G.8264);
        op1-dnu(5)  -  Do not use this quality;
        op2-dus(6)  -  Do not use for synchronization"

    DEFVAL { op1-dnu }
    ::= { ssm 5 }


ssmLockedQuality    OBJECT-TYPE
    SYNTAX          INTEGER {prs(1), prc(2), stu(3), ssua(4), tnc(5), st2(6), ssub(7), eec2(8), eec1(9), smc(10), st3e(11), prov(12), dnu(13), dus(14)}
    MAX-ACCESS      read-only
    STATUS          current
    DESCRIPTION
        "Get the locked quality.The meanings of the values are:
        prs(1)   -  PRS traceable (ITU-T G.811);
        prc(2)   -  Primary reference clock;
        stu(3)   -  Synchronized – Traceability unknown;
        ssua(4)  -  Type I or V slave clock
                    defined in ITU-T G.812;
        tnc(5)   -  Traceable to transit node clock
                    (ITU-T G.812, type V);
        st2(6)   -  Traceable to stratum 2
                    (ITU-T G.812, type II);
        ssub(7)  -  Type VI slave clock defined in ITU-T G.812;
        eec2(8)  -  EEC2 clock or st3 clock;
        eec1(9)  -   EEC1 clock or SEC clock;
        smc(10)  -  Traceable to SONET clock self timed;
        st3e(11) -  Traceable to stratum 3E
                    (ITU-T G.812, type III);
        prov(12) -  Provisionable by the network operator;
        dnu(13)  -  Do not use this quality;
        dus(14)  -  Do not use for synchronization"

    ::= { ssm 6 }

ssmLocalPriority    OBJECT-TYPE
    SYNTAX          Integer32 (1..255)
    MAX-ACCESS      read-write
    STATUS          current
    DESCRIPTION
        "Set the device priority globally.
        The range is 1 ~ 255"
    DEFVAL { 255 }
    ::= { ssm 7 }

ssmSelectedInterface    OBJECT-TYPE
    SYNTAX          OCTET STRING
    MAX-ACCESS      read-only
    STATUS          current
    DESCRIPTION
        "Get the current selected port."
    ::= { ssm 8 }

ssmExtensionEnable    OBJECT-TYPE
    SYNTAX          INTEGER {enable(1), disable(2)}
    MAX-ACCESS      read-write
    STATUS          current
    DESCRIPTION
        "Set whether the device start extend ssm.
        The meanings of the values are:
        enable(1)  -  Start extend ssm;
        disable(2) -  Not start extend ssm"
    DEFVAL { disable }
    ::= { ssm 9 }

ssmClockState    OBJECT-TYPE
    SYNTAX       INTEGER {master-clock(1), freerun(2), holdover(3), lock(4)}
    MAX-ACCESS      read-only
    STATUS          current
    DESCRIPTION
        "Get the device clock status.
        The meanings of the values are:
        master-clock(1) -  Master-only device
                            affords time signal;
        freerun(2)      -  Device has not been synchronized;
        holdover(3)     -  Device going to holdover;
        lock(4)         -  Device select and lock a time signal"
    ::= { ssm 10 }

ssmOptionMode    OBJECT-TYPE
    SYNTAX          INTEGER {op1(1), op2(2)}
    MAX-ACCESS      read-only
    STATUS          current
    DESCRIPTION
        "Get the device clock ssm option mode.
        op1(1) - Option mode 1;
        op2(2) - Option mode 2"
    ::= { ssm 11 }

ssmSwitchForceIF    OBJECT-TYPE
    SYNTAX          Integer32 (0..65536)
    MAX-ACCESS      read-write
    STATUS          current
    DESCRIPTION
        "Switch time resource to one interface forcibaly.
        The value is the ifindex.
        Value 0 cancles configuration"
    DEFVAL { 0 }
    ::= { ssm 12 }

ssmIfTable   OBJECT-TYPE
    SYNTAX          SEQUENCE OF SSMIFEntry
    MAX-ACCESS      not-accessible
    STATUS          current
    DESCRIPTION
        "Table of ssm interface entry."
    ::= { ssm 13 }    
      
ssmGlbHoldOffTime    OBJECT-TYPE
    SYNTAX          INTEGER (0..18)
    MAX-ACCESS      read-write
    STATUS          current
    DESCRIPTION
        "Get global holdoff time."    
    DEFVAL { 0 }    
    ::= { ssm 16 }  
            
    
ssmGlbWtrTime    OBJECT-TYPE
    SYNTAX          INTEGER (0..12)
    MAX-ACCESS      read-write
    STATUS          current
    DESCRIPTION
        "Get golobal wtr time."  
    DEFVAL { 0 }    
    ::= { ssm 17 }
    

ssmIfEntry   OBJECT-TYPE
    SYNTAX          SSMIFEntry
    MAX-ACCESS      not-accessible
    STATUS          current
    DESCRIPTION
        "Ssm interface entry"
    INDEX     { ssmIfIndex }
    ::= { ssmIfTable 1 }

SSMIFEntry    ::=
    SEQUENCE
    {
        ssmIfIndex             Integer32,
        ssmIfSyncEEnable       INTEGER,
        ssmIfSyncEPduMode     INTEGER,
        ssmIfPortPriority      Integer32,
    ssmIfPortUp       INTEGER,
    ssmIfPortQuality    INTEGER,
    ssmIfSendTimerState   INTEGER,
    ssmIfTimeoutTimerState INTEGER,
    ssmIfSendQuality        INTEGER,
    ssmIFDNUgroup           Integer32,
       ssmIfReplaceClockId   INTEGER,
       ssmIfForcibleRxQL       INTEGER,
       ssmIfForcibleTxQL       INTEGER
    }

ssmIfIndex OBJECT-TYPE
    SYNTAX          Integer32 (0..65535)
    MAX-ACCESS      not-accessible
    STATUS          current
    DESCRIPTION
        "Interface index which is able to apply ssm."
    ::= { ssmIfEntry 1 }

ssmIfSyncEEnable OBJECT-TYPE
    SYNTAX          INTEGER {enable(1), disable(2)}
    MAX-ACCESS      read-write
    STATUS          current
    DESCRIPTION
        "Set whether the port is a synchronous port.
        The meanings of the values are:
        enable(1)  -  a synchronous port;
        disable(2) -  not a synchronous port"
    DEFVAL { disable }
    ::= { ssmIfEntry 2 }

ssmIfSyncEPduMode OBJECT-TYPE
    SYNTAX          INTEGER {rx(1), tx(2), all(3), none-all(4), none-rx(5), none-tx(6)}
    MAX-ACCESS      read-write
    STATUS          current
    DESCRIPTION
        "Set whether the interface can receive or send PDU.
        The meanings of the values are:
        rx(1)   -  receive PDU only;
        tx(2)   -  send PDU only;
        all(3)  -  receive and send PDU;
        none-all(4) - disable receive and send PDU;
        none-rx(5)  - receive PDU only;
        none-tx(6)  - send PDU only"
    DEFVAL { all }
    ::= { ssmIfEntry 3 }

ssmIfPortPriority OBJECT-TYPE
    SYNTAX          Integer32 (1..255)
    MAX-ACCESS      read-write
    STATUS          current
    DESCRIPTION
        "Set the port priority. The range is 1 ~ 255."
    DEFVAL { 255 }
    ::= { ssmIfEntry 4 }

ssmIfPortUp OBJECT-TYPE
    SYNTAX          INTEGER {enable(1), disable(2)}
    MAX-ACCESS      read-only
    STATUS          current
    DESCRIPTION
      "Get the status of whether the port is up.
      The meanings of the values are:
      enable(1)  -  Port is up;
      disable(2) -  Port is down"
    ::= { ssmIfEntry 5 }

ssmIfPortQuality OBJECT-TYPE
    SYNTAX          INTEGER {prs(1), prc(2), stu(3), ssua(4), tnc(5), st2(6), ssub(7), eec2(8), eec1(9), smc(10), st3e(11), prov(12), dnu(13), dus(14), na(15)}
    MAX-ACCESS      read-only
    STATUS          current
    DESCRIPTION
        "Get the current received quality of port.
        The meanings of the values are:
        prs(1)   -  PRS traceable (ITU-T G.811);
        prc(2)   -  Primary reference clock;
        stu(3)   -  Synchronized – Traceability unknown;
        ssua(4)  -  Type I or V slave clock
                    defined in ITU-T G.812;
        tnc(5)   -  Traceable to transit node clock
                    (ITU-T G.812, type V);
        st2(6)   -  Traceable to stratum 2
                    (ITU-T G.812, type II);
        ssub(7)  -  Type VI slave clock defined in ITU-T G.812;
        eec2(8)  -  EEC2 clock or st3 clock;
        eec1(9)  -  EEC1 clock or SEC clock;
        smc(10)  -  Traceable to SONET clock self timed;
        st3e(11) -  Traceable to stratum 3E
                    (ITU-T G.812, type III);
        prov(12) -  Provisionable by the network operator;
        dnu(13)  -  Do not use this quality;
        dus(14)  -  Do not use for synchronization;
        na(15)   -  N/A"
    ::= { ssmIfEntry 6 }

ssmIfSendTimerState OBJECT-TYPE
    SYNTAX          INTEGER {enable(1), disable(2)}
    MAX-ACCESS      read-only
    STATUS          current
    DESCRIPTION
      "Get the status of Send timer.
      The meanings of the values are:
      enable(1)  -  Enable;
      disable(2) -  Disable"
    ::= { ssmIfEntry 7 }

ssmIfTimeoutTimerState OBJECT-TYPE
    SYNTAX          INTEGER {enable(1), disable(2)}
    MAX-ACCESS      read-only
    STATUS          current
    DESCRIPTION
      "Get the status of Timeout timer.
      The meanings of the values are:
      enable(1)  -  Enable;
      disable(2) -  Disable"
    ::= { ssmIfEntry 8 }

ssmIfSendQuality OBJECT-TYPE
    SYNTAX          INTEGER {prs(1), prc(2), stu(3), ssua(4), tnc(5), st2(6), ssub(7), eec2(8), eec1(9), smc(10), st3e(11), prov(12), dnu(13), dus(14), na(15)}
    MAX-ACCESS      read-only
    STATUS          current
    DESCRIPTION
        "Get the current sending quality of port.
        The meanings of the values are:
        prs(1)   -  PRS traceable (ITU-T G.811);
        prc(2)   -  Primary reference clock;
        stu(3)   -  Synchronized – Traceability unknown;
        ssua(4)  -  Type I or V slave clock
                    defined in ITU-T G.812;
        tnc(5)   -  Traceable to transit node clock
                    (ITU-T G.812, type V);
        st2(6)   -  Traceable to stratum 2
                    (ITU-T G.812, type II);
        ssub(7)  -  Type VI slave clock defined in ITU-T G.812;
        eec2(8)  -  EEC2 clock or st3 clock;
        eec1(9)  -  EEC1 clock or SEC clock;
        smc(10)  -  Traceable to SONET clock self timed;
        st3e(11) -  Traceable to stratum 3E
                    (ITU-T G.812, type III);
        prov(12) -  Provisionable by the network operator;
        dnu(13)  -  Do not use this quality;
        dus(14)  -  Do not use for synchronization;
        na(15)   -  N/A"
    ::= { ssmIfEntry 9 }

ssmIFDNUgroup OBJECT-TYPE
    SYNTAX          Integer32 (0..255)
    MAX-ACCESS      read-write
    STATUS          current
    DESCRIPTION
        "Add the port into DNU group. The range is 0 ~ 255.
        value 0 is delete port from DNU group."
    DEFVAL { 0 }
    ::= { ssmIfEntry 10 }

ssmIfReplaceClockId OBJECT-TYPE
    SYNTAX          INTEGER {enable(1), disable(2)}
    MAX-ACCESS      read-write
    STATUS          current
    DESCRIPTION
      "Get or set the status of replace clockid.
      The meanings of the values are:
      enable(1)  -  Enable;
      disable(2) -  Disable"
    DEFVAL { disable }
    ::= { ssmIfEntry 11 }

ssmIfForcibleRxQL    OBJECT-TYPE
    SYNTAX          INTEGER {prs(1), prc(2), stu(3), ssua(4), tnc(5), st2(6), ssub(7), eec2(8), eec1(9), smc(10), st3e(11), prov(12), dnu(13), dus(14), na(15)}
    MAX-ACCESS      read-write
    STATUS          current
    DESCRIPTION
        "Get and set Rx quality of physical port.
        The meanings of the values are:
        prs(1)   -  PRS traceable (ITU-T G.811);
        prc(2)   -  Primary reference clock;
        stu(3)   -  Synchronized – Traceability unknown;
        ssua(4)  -  Type I or V slave clock
                    defined in ITU-T G.812;
        tnc(5)   -  Traceable to transit node clock
                    (ITU-T G.812, type V);
        st2(6)   -  Traceable to stratum 2
                    (ITU-T G.812, type II);
        ssub(7)  -  Type VI slave clock defined in ITU-T G.812;
        eec2(8)  -  EEC2 clock or st3 clock;
        eec1(9)  -  EEC1 clock or SEC clock;
        smc(10)  -  Traceable to SONET clock self timed;
        st3e(11) -  Traceable to stratum 3E
                    (ITU-T G.812, type III);
        prov(12) -  Provisionable by the network operator;
        dnu(13)  -  Do not use this quality;
        dus(14)  -  Do not use for synchronization;
        na(15)   -  N/A"
    DEFVAL { 15 }
    ::= { ssmIfEntry 12 }

ssmIfForcibleTxQL    OBJECT-TYPE
    SYNTAX          INTEGER {prs(1), prc(2), stu(3), ssua(4), tnc(5), st2(6), ssub(7), eec2(8), eec1(9), smc(10), st3e(11), prov(12), dnu(13), dus(14), na(15)}
    MAX-ACCESS      read-write
    STATUS          current
    DESCRIPTION
        "Get and set Tx quality of physical port.
        The meanings of the values are:
        prs(1)   -  PRS traceable (ITU-T G.811);
        prc(2)   -  Primary reference clock;
        stu(3)   -  Synchronized – Traceability unknown;
        ssua(4)  -  Type I or V slave clock
                    defined in ITU-T G.812;
        tnc(5)   -  Traceable to transit node clock
                    (ITU-T G.812, type V);
        st2(6)   -  Traceable to stratum 2
                    (ITU-T G.812, type II);
        ssub(7)  -  Type VI slave clock defined in ITU-T G.812;
        eec2(8)  -  EEC2 clock or st3 clock;
        eec1(9)  -  EEC1 clock or SEC clock;
        smc(10)  -  Traceable to SONET clock self timed;
        st3e(11) -  Traceable to stratum 3E
                    (ITU-T G.812, type III);
        prov(12) -  Provisionable by the network operator;
        dnu(13)  -  Do not use this quality;
        dus(14)  -  Do not use for synchronization;
        na(15)   -  N/A"
    DEFVAL { 15 }
    ::= { ssmIfEntry 13 }

--ssmForcibleE1RxQL    OBJECT-TYPE
--    SYNTAX          INTEGER {prs(1), prc(2), stu(3), ssua(4), tnc(5), st2(6), ssub(7), eec2(8), eec1(9), smc(10), st3e(11), prov(12), dnu(13), dus(14), na(15)}
--    MAX-ACCESS      read-write
--    STATUS          current
--    DESCRIPTION
--        "Get and set Rx quality of E1 port.
--        The meanings of the values are:
--        prs(1)   -  PRS traceable (ITU-T G.811);
--        prc(2)   -  Primary reference clock;
--        stu(3)   -  Synchronized – Traceability unknown;
--        ssua(4)  -  Type I or V slave clock
--                    defined in ITU-T G.812;
--        tnc(5)   -  Traceable to transit node clock
--                    (ITU-T G.812, type V);
--        st2(6)   -  Traceable to stratum 2
--                    (ITU-T G.812, type II);
--        ssub(7)  -  Type VI slave clock defined in ITU-T G.812;
--        eec2(8)  -  EEC2 clock or st3 clock;
--        eec1(9)  -  EEC1 clock or SEC clock;
--        smc(10)  -  Traceable to SONET clock self timed;
--        st3e(11) -  Traceable to stratum 3E
--                    (ITU-T G.812, type III);
--        prov(12) -  Provisionable by the network operator;
--        dnu(13)  -  Do not use this quality;
--        dus(14)  -  Do not use for synchronization;
--        na(15)   -  N/A"
--    DEFVAL { 15 }
--    ::= { ssm 14 }
--
--ssmForcibleE1TxQL    OBJECT-TYPE
--    SYNTAX          INTEGER {prs(1), prc(2), stu(3), ssua(4), tnc(5), st2(6), ssub(7), eec2(8), eec1(9), smc(10), st3e(11), prov(12), dnu(13), dus(14), na(15)}
--    MAX-ACCESS      read-write
--    STATUS          current
--    DESCRIPTION
--        "Get and set Tx quality of E1 port.
--        The meanings of the values are:
--        prs(1)   -  PRS traceable (ITU-T G.811);
--        prc(2)   -  Primary reference clock;
--        stu(3)   -  Synchronized – Traceability unknown;
--        ssua(4)  -  Type I or V slave clock
--                    defined in ITU-T G.812;
--        tnc(5)   -  Traceable to transit node clock
--                    (ITU-T G.812, type V);
--        st2(6)   -  Traceable to stratum 2
--                    (ITU-T G.812, type II);
--        ssub(7)  -  Type VI slave clock defined in ITU-T G.812;
--        eec2(8)  -  EEC2 clock or st3 clock;
--        eec1(9)  -  EEC1 clock or SEC clock;
--        smc(10)  -  Traceable to SONET clock self timed;
--        st3e(11) -  Traceable to stratum 3E
--                    (ITU-T G.812, type III);
--        prov(12) -  Provisionable by the network operator;
--        dnu(13)  -  Not to be used for synchronization;
--        dus(14)  -  Not to be used for synchronization;
--        na(15)   -  N/A"
--    DEFVAL { 15 }
--    ::= { ssm 15 }

--arpConfig               OBJECT IDENTIFIER ::= { OID 82 }
arpGratuitousRecvEn     OBJECT-TYPE
    SYNTAX          INTEGER {enable(1),disable(2)}
    MAX-ACCESS      read-write
    STATUS          current
    DESCRIPTION
        " Enable or disable receiving gratuitous ARP packets."
    DEFVAL { disable }
    ::= { arpConfig 1 }

arpAllEntries     OBJECT-TYPE
    SYNTAX          INTEGER
    MAX-ACCESS      read-only
    STATUS          current
    DESCRIPTION
        " All arp entries."
    ::= { arpConfig 2 }

arpAllIncompleteEntries     OBJECT-TYPE
    SYNTAX          INTEGER
    MAX-ACCESS      read-only
    STATUS          current
    DESCRIPTION
        " All arp incomplete entries."
    ::= { arpConfig 3 }




-- ptp   OBJECT IDENTIFIER ::= { OID 85 }

ptpGlobalInfo   OBJECT IDENTIFIER ::= { ptp 1 }

ptpDomainIndex           OBJECT-TYPE
    SYNTAX          Integer32 (0..255)
    MAX-ACCESS      read-only
    STATUS          current
    DESCRIPTION     "Ptp domain index."
    ::= { ptpGlobalInfo 1 }

ptpPortNum           OBJECT-TYPE
    SYNTAX          Integer32
    MAX-ACCESS      read-only
    STATUS          current
    DESCRIPTION     "Ptp port number."
    ::= { ptpGlobalInfo 2 }

ptpUtcOffset           OBJECT-TYPE
    SYNTAX                  Integer32 (0..255)
    MAX-ACCESS      read-only
    STATUS          current
    DESCRIPTION     "Ptp utc offset."
    ::= { ptpGlobalInfo 3 }

ptpLocalClockIdentity              OBJECT-TYPE
    SYNTAX                  OCTET STRING
    MAX-ACCESS      read-only
    STATUS          current
    DESCRIPTION     "Ptp local clock identiry."
    ::= { ptpGlobalInfo 4 }

ptpBMCRecMem              OBJECT-TYPE
    SYNTAX                  OCTET STRING
    MAX-ACCESS      read-only
    STATUS          current
    DESCRIPTION     "Ptp bmc reciver member"
    ::= { ptpGlobalInfo 5 }

ptpBMCParentClockId                OBJECT-TYPE
    SYNTAX                  OCTET STRING
    MAX-ACCESS      read-only
    STATUS          current
    DESCRIPTION     "Ptp bmc parent clock id."
    ::= { ptpGlobalInfo 6 }

ptpBMCParentPortNum                     OBJECT-TYPE
    SYNTAX                  Integer32 (0..255)
    MAX-ACCESS      read-only
    STATUS          current
    DESCRIPTION     "Ptp bmc parent port number."
    ::= { ptpGlobalInfo 7 }

ptpBMCMeanPathDelay                             OBJECT-TYPE
    SYNTAX                  Counter64
    MAX-ACCESS      read-only
    STATUS          current
    DESCRIPTION     "Ptp bmc mean path delay."
    ::= { ptpGlobalInfo 8 }

ptpBMCOffsetFromMaster                                  OBJECT-TYPE
    SYNTAX                  Counter64
    MAX-ACCESS      read-only
    STATUS          current
    DESCRIPTION     "Ptp bmc offset from master."
    ::= { ptpGlobalInfo 9 }

ptpBMCStepRemoved                             OBJECT-TYPE
    SYNTAX                  Integer32 (0..255)
    MAX-ACCESS      read-only
    STATUS          current
    DESCRIPTION     "Ptp bmc step removed."
    ::= { ptpGlobalInfo 10 }

ptpBMCGMClockId                OBJECT-TYPE
    SYNTAX                  OCTET STRING
    MAX-ACCESS      read-only
    STATUS          current
    DESCRIPTION     "Ptp bmc gm clock id."
    ::= { ptpGlobalInfo 11 }

ptpBMCGMPriority1                             OBJECT-TYPE
    SYNTAX                  Integer32 (0..255)
    MAX-ACCESS      read-only
    STATUS          current
    DESCRIPTION     "Ptp bmc gm priority1."
    ::= { ptpGlobalInfo 12 }

ptpBMCGMPriority2                             OBJECT-TYPE
    SYNTAX                  Integer32 (0..255)
    MAX-ACCESS      read-only
    STATUS          current
    DESCRIPTION     "Ptp bmc gm priority2."
    ::= { ptpGlobalInfo 13 }

ptpBMCGMClockAccuracy                                   OBJECT-TYPE
    SYNTAX                  Integer32 (0..255)
    MAX-ACCESS      read-only
    STATUS          current
    DESCRIPTION     "Ptp bmc gm clock accuracy."
    ::= { ptpGlobalInfo 14 }

ptpBMCGMClockClass                             OBJECT-TYPE
    SYNTAX                  Integer32 (0..255)
    MAX-ACCESS      read-only
    STATUS          current
    DESCRIPTION     "Ptp bmc gm clock class."
    ::= { ptpGlobalInfo 15 }

ptpBMCGMTimeSource                             OBJECT-TYPE
    SYNTAX                  OCTET STRING
    MAX-ACCESS      read-only
    STATUS          current
    DESCRIPTION     "Ptp bmc gm time source."
    ::= { ptpGlobalInfo 16 }

ptpBMCGMUtcOffset                             OBJECT-TYPE
    SYNTAX                  Integer32 (0..255)
    MAX-ACCESS      read-only
    STATUS          current
    DESCRIPTION     "Ptp bmc gm utc offset."
    ::= { ptpGlobalInfo 17 }

ptpBMCGMUTCOffsetValid                                 OBJECT-TYPE
    SYNTAX                  TruthValue
    MAX-ACCESS      read-only
    STATUS          current
    DESCRIPTION     "Ptp bmc gm utc offset valid."
    ::= { ptpGlobalInfo 18 }

ptpBMCGMTimeScale                                           OBJECT-TYPE
    SYNTAX                  OCTET STRING
    MAX-ACCESS      read-only
    STATUS          current
    DESCRIPTION     "Ptp bmc gm time scale."
    ::= { ptpGlobalInfo 19 }

ptpBMCGMTimeTraceable                                           OBJECT-TYPE
    SYNTAX                  INTEGER{true(1),false(2)}
    MAX-ACCESS      read-only
    STATUS          current
    DESCRIPTION     "Ptp bmc gm time trace able."
    DEFVAL { false }
    ::= { ptpGlobalInfo 20 }

ptpBMCGMLeap59                                           OBJECT-TYPE
    SYNTAX                  INTEGER{true(1),false(2)}
    MAX-ACCESS      read-only
    STATUS          current
    DESCRIPTION     "Ptp bmc gm leap59."
    DEFVAL { false }
    ::= { ptpGlobalInfo 21 }

ptpBMCGMLeap61                                           OBJECT-TYPE
    SYNTAX                  INTEGER{true(1),false(2)}
    MAX-ACCESS      read-only
    STATUS          current
    DESCRIPTION     "Ptp bmc gm leap61."
    DEFVAL { false }
    ::= { ptpGlobalInfo 22 }

ptpBMCGMFrequencyTraceable                                           OBJECT-TYPE
    SYNTAX                  INTEGER{true(1),false(2)}
    MAX-ACCESS      read-only
    STATUS          current
    DESCRIPTION     "Ptp bmc gm frequency traceable."
    DEFVAL { false }
    ::= { ptpGlobalInfo 23 }


ptpClearStatistics      OBJECT-TYPE
    SYNTAX                  INTEGER
    MAX-ACCESS              read-write
    STATUS                  current
    DESCRIPTION
        "Clear all statistics for the ptp. 0 mean clear all ptp interface statistics."
    ::= { ptpGlobalInfo 24 }

ptpDeviceType        OBJECT-TYPE
    SYNTAX                  INTEGER
    {
        oc(0),
        bc (1),
        e2etc(2),
        p2ptc(3)
    }
    MAX-ACCESS              read-write
    STATUS                  current
    DESCRIPTION
        "The type of the clock. oc(0), bc(1), e2etc(2), p2ptc(3). "
    DEFVAL { bc }
    ::= { ptpGlobalInfo 25 }

ptpGlobalEnable        OBJECT-TYPE
    SYNTAX              INTEGER {enable(1), disable(2)}
    MAX-ACCESS              read-write
    STATUS                  current
    DESCRIPTION
        "Enable Precision Time Protocol (IEEE1588). enable(1), disable(2). "
    DEFVAL { disable }
    ::= { ptpGlobalInfo 26 }

ptpDomain         OBJECT-TYPE
    SYNTAX                  Integer32 (0..255)
    MAX-ACCESS              read-write
    STATUS                  current
    DESCRIPTION
        "The domain attribute of the local clock. Range 0~255. "
    DEFVAL { 0 }
    ::= { ptpGlobalInfo 27 }

ptpTcPrimaryDomain      OBJECT-TYPE
    SYNTAX                  Integer32 (0..255)
    MAX-ACCESS              read-write
    STATUS                  current
    DESCRIPTION
        "The primary syntonization domain. Range 0~255. "
    DEFVAL { 0 }
    ::= { ptpGlobalInfo 28 }

ptpSlaveOnly        OBJECT-TYPE
    SYNTAX                  INTEGER
    {
        disable(2),
        enable (1)
   }
    MAX-ACCESS              read-write
    STATUS                  current
    DESCRIPTION
        "Slave-only clock can never enter the MASTER state. Disable(2), Enable(1). "
    DEFVAL { disable }
    ::= { ptpGlobalInfo 29 }

ptpPriority1      OBJECT-TYPE
    SYNTAX                  Integer32 (0..255)
    MAX-ACCESS              read-write
    STATUS                  current
    DESCRIPTION
        "The priority1 attribute of the local clock. Range 0~255. "
    DEFVAL { 128 }
    ::= { ptpGlobalInfo 30 }

ptpPriority2      OBJECT-TYPE
    SYNTAX                  Integer32 (0..255)
    MAX-ACCESS              read-write
    STATUS                  current
    DESCRIPTION
        "The priority2 attribute of the local clock. Range 0~255. "
    DEFVAL { 128 }
    ::= { ptpGlobalInfo 31 }

ptpClockAccuracy      OBJECT-TYPE
    SYNTAX                  Integer32 (1..19)
    MAX-ACCESS              read-write
    STATUS                  current
    DESCRIPTION
        "The clock accuracy characterizes a clock for the purpose of the best master clock(BMC) algorithm.
        Value:
        1: The time is accurate to within 25 ns.
        2: The time is accurate to within 100 ns.
        3: The time is accurate to within 250 ns
        4: The time is accurate to within 1 us.
        5: The time is accurate to within 2.5 us.
        6: The time is accurate to within 10 us.
        7: The time is accurate to within 25 us.
        8: The time is accurate to within 100 us.
        9: The time is accurate to within 250 us.
        10: The time is accurate to within 1 ms.
        11: The time is accurate to within 2.5 ms.
        12: The time is accurate to within 10 ms.
        13: The time is accurate to within 25 ms.
        14: The time is accurate to within 100 ms.
        15: The time is accurate to within 250 ms.
        16: The time is accurate to within 1 s.
        17: The time is accurate to within 10 s.
        18: The time is accurate to > 10 s.
        19: The time is accurate to unknown.
        "
--    DEFVAL { 0xFE }
    ::= { ptpGlobalInfo 32 }

ptpClockClass       OBJECT-TYPE
    SYNTAX                  INTEGER
    {
        class6(6),
        class7(7),
        class13(13),
        class14(14),
        class52(52),
        class58(58),
        class187(187),
        class193(193),
        class248(248)
    }
    MAX-ACCESS              read-write
    STATUS                  current
    DESCRIPTION
        "The clockClass attribute of an ordinary or boundary clock denotes the traceability of the time or frequency distributed by the grandmaster clock. Value only is 6,7,13,14,52,58,187,193,248."
--    DEFVAL { 0xFE }
    ::= { ptpGlobalInfo 33 }

ptpLeap59        OBJECT-TYPE
    SYNTAX          INTEGER
        {
            enable(1),
            disable(2)
        }
    MAX-ACCESS              read-write
    STATUS                  current
    DESCRIPTION
        "The last minute of the current UTC day contains 59 seconds. Disable(2), Enable(1). "
    DEFVAL { disable }
    ::= { ptpGlobalInfo 34 }

ptpLeap61        OBJECT-TYPE
    SYNTAX          INTEGER 
        {
            enable(1),
            disable(2)
        }
    MAX-ACCESS              read-write
    STATUS                  current
    DESCRIPTION
        "The last minute of the current UTC day contains 61 seconds. Disable(2), Enable(1). "
    DEFVAL { disable }
    ::= { ptpGlobalInfo 35 }

ptpTimeSource      		OBJECT-TYPE
    SYNTAX                  INTEGER
    {
        atomic-clock(1),
        gps(2),
        internal-oscillator(3),
        ptp(4),
        ntp(5),
        hand-set(6),        
        other(7),
        terrestrial-radio(8)
   }
    MAX-ACCESS              read-write
    STATUS                  current
    DESCRIPTION
        "The attribute indicates the source of time used by the local clock. 
        atomic-clock(1),
        gps(2),
        internal-oscillator(3),
        ptp(4),
        ntp(5),
        hand-set(6),        
        other(7),
        terrestrial-radio(8)."
    DEFVAL { internal-oscillator }
    ::= { ptpGlobalInfo 36 }

-- ## 1.2	show ptp interface

ptpIfConfigureTable         OBJECT-TYPE
    SYNTAX                    SEQUENCE OF PtpIfConfigureEntry
    MAX-ACCESS                not-accessible
    STATUS                    current
    DESCRIPTION
        "The table of Monitor link group."
    ::= { ptp 2 }
                
ptpIfConfigureEntry         OBJECT-TYPE
    SYNTAX                    PtpIfConfigureEntry
    MAX-ACCESS                not-accessible
    STATUS                    current
    DESCRIPTION
        "The entry of Monitor link group."
    INDEX     { ptpIfIndex}
    ::= { ptpIfConfigureTable 1 }

PtpIfConfigureEntry    ::=
    SEQUENCE
    {
        ptpIfIndex
            Integer32,
        ptpAnnounceInterval
            Integer32,
        ptpSyncInterval
            Integer32, 
        ptpMinDelayreqInterval
            Integer32,
        ptpMinPdelayreqInterval
            Integer32,
        ptpAnnounceReceiptTimeout
            Integer32,
        ptpDelayMechanism
            INTEGER,
        ptpEnable
            INTEGER,
        ptpAsymmetryCorrection
            Integer32,
        ptpProtocolMac
            INTEGER,
        ptpUdpSrcIp
            OCTET STRING,
        ptpVlanId
            Integer32,
        ptpCos
            Integer32,
        ptpIfName
            OCTET STRING,
        ptpIfState
            OCTET STRING,
        ptpIfStep
            Integer32,
        ptpIfPortId
            OCTET STRING,
        ptpIfRcvAnn
            Integer32,
        ptpIfRcvDelayReq
            Integer32,
        ptpIfRcvDelayResp
            Integer32,
        ptpIfRcvFollowUp
            Integer32,
        ptpIfRcvUnknown
            Integer32,
        ptpIfRcvSync
            Integer32,
        ptpIfRcvPDelayReq
            Integer32,
        ptpIfRcvPDelayResp
            Integer32,
        ptpIfRcvPDelayRespFowllowUp
            Integer32,
        ptpIfSendAnn
            Integer32,
        ptpIfSendDelayReq
            Integer32,
        ptpIfSendDelayResp
            Integer32,
        ptpIfSendFollowUp
            Integer32,
        ptpIfSendUnknown
            Integer32,
        ptpIfSendSync
            Integer32,
        ptpIfSendPDelayReq
            Integer32,
        ptpIfSendPDelayResp
            Integer32,
        ptpIfSendPDelayRespFowllowUp
            Integer32,
        ptpIfDiscardAnn
            Integer32,
        ptpIfDiscardDelayReq
            Integer32,
        ptpIfDiscardDelayResp
            Integer32,
        ptpIfDiscardFollowUp
            Integer32,
        ptpIfDiscardUnknown
            Integer32,
        ptpIfDiscardSync
            Integer32,
        ptpIfDiscardPDelayReq
            Integer32,
        ptpIfDiscardPDelayResp
            Integer32,
        ptpIfDiscardPDelayRespFowllowUp
            Integer32
    }

ptpIfIndex          OBJECT-TYPE
    SYNTAX          Integer32 (1..1024)
    MAX-ACCESS      not-accessible
    STATUS          current
    DESCRIPTION        
        "The index of ptp interface."
    ::= { ptpIfConfigureEntry 1 }

ptpAnnounceInterval      OBJECT-TYPE
    SYNTAX                  Integer32 (-1..10)
    MAX-ACCESS              read-write
    STATUS                  current
    DESCRIPTION
        "The mean announce interval. Range -1~10. "
    DEFVAL { 1 }
    ::= { ptpIfConfigureEntry 2 }
   
ptpSyncInterval      OBJECT-TYPE
    SYNTAX                  Integer32 (-1..10)
    MAX-ACCESS              read-write
    STATUS                  current
    DESCRIPTION
        "The mean sync interval for multicast messages. Range -1~10. "
    DEFVAL { 1 }
    ::= { ptpIfConfigureEntry 3 }

ptpMinDelayreqInterval      OBJECT-TYPE
    SYNTAX                  Integer32 (-1..10)
    MAX-ACCESS              read-write
    STATUS                  current
    DESCRIPTION
        "The minimum delay request interval for multicast messages. Range -1~10. "
    DEFVAL { 0 }
    ::= { ptpIfConfigureEntry 4 }

ptpMinPdelayreqInterval      OBJECT-TYPE
    SYNTAX                  Integer32 (-1..10)
    MAX-ACCESS              read-write
    STATUS                  current
    DESCRIPTION
        "The minimum peer delay request interval for multicast messages. Range -1~10. "
    DEFVAL { 0 }
    ::= { ptpIfConfigureEntry 5 }

ptpAnnounceReceiptTimeout      OBJECT-TYPE
    SYNTAX                  Integer32 (3..255)
    MAX-ACCESS              read-write
    STATUS                  current
    DESCRIPTION
        "The number of announce interval that has to pass without receipt of an Announce message before the occurrence of the event ANNOUNCE_RECEIPT_TIMEOUT_EXPIRES. Range 3~255. "
    DEFVAL { 4 }
    ::= { ptpIfConfigureEntry 6 }

ptpDelayMechanism      		OBJECT-TYPE
    SYNTAX                  INTEGER
    {
        normal  (1),
        peer  (2),
        disable(3)
   }
    MAX-ACCESS              read-write
    STATUS                  current
    DESCRIPTION
        "The propagation delay measuring option used by the port in computing meanPathDelay. normal(1).peer(2).disable(3)."
    DEFVAL { normal }
    ::= { ptpIfConfigureEntry 7 }

ptpEnable      		OBJECT-TYPE
    SYNTAX                  INTEGER
    {
        disable(2),
        enable (1)
   }
    MAX-ACCESS              read-write
    STATUS                  current
    DESCRIPTION
        "Enable Precision Time Protocol (IEEE1588). Disable(2), Enable(1). "
    DEFVAL { disable }
    ::= { ptpIfConfigureEntry 8 }

ptpAsymmetryCorrection      OBJECT-TYPE
    SYNTAX                  Integer32 
    MAX-ACCESS              read-write
    STATUS                  current
    DESCRIPTION
        "The asymmetry correction of the path. Range -2000000 - 2000000. "
    DEFVAL { 0 }
    ::= { ptpIfConfigureEntry 9 }

ptpProtocolMac      		OBJECT-TYPE
    SYNTAX                  INTEGER
    {
        enable (1)
   }
    MAX-ACCESS              read-write
    STATUS                  current
    DESCRIPTION
        "Transport PTP messages directly over Ethernet frames as specified in IEEE Std 802.3-2005.Note: IF set value (1), ptpUdpSrcIp(11) will invalid. "
    ::= { ptpIfConfigureEntry 10 }

ptpUdpSrcIp      		OBJECT-TYPE
    SYNTAX                  OCTET STRING (SIZE (0..255))
    MAX-ACCESS              read-write
    STATUS                  current
    DESCRIPTION
        "Transport PTP messages over the User Datagram Protocol (UDP) as defined in IETF RFC 768 (1980), and Internet Protocol version 4 (IPv4), as defined in IETF RFC 791 (1981). Note: IF set value, ptpProtocolMac(10) will invalid. "
    ::= { ptpIfConfigureEntry 11 }

ptpVlanId          OBJECT-TYPE
    SYNTAX          Integer32 (1..4094)
    MAX-ACCESS      read-create
    STATUS          current
    DESCRIPTION     "Vlan ID. Range 1~4094. -1 mean delete."
    ::= { ptpIfConfigureEntry 12 }
  
ptpCos	          OBJECT-TYPE
    SYNTAX          Integer32 (0..7)
    MAX-ACCESS      read-create
    STATUS          current
    DESCRIPTION     "Class of Services. Range 0~7. -1 mean delete."
    ::= { ptpIfConfigureEntry 13 }

ptpIfName      OBJECT-TYPE
    SYNTAX                  OCTET STRING (SIZE (0..255))
    MAX-ACCESS              read-only
    STATUS                  current
    DESCRIPTION
        "Ptp interface name. "
    ::= { ptpIfConfigureEntry 14 }

ptpIfState                                	          OBJECT-TYPE
    SYNTAX                  OCTET STRING (SIZE (0..255)) 
    MAX-ACCESS      read-only
    STATUS          current
    DESCRIPTION     "Ptp interface state."
    ::= { ptpIfConfigureEntry 15 }  

ptpIfStep                               	          OBJECT-TYPE
    SYNTAX                  Integer32 
    MAX-ACCESS      read-only
    STATUS          current
    DESCRIPTION     "Ptp interface step."
    ::= { ptpIfConfigureEntry 16 }  

ptpIfPortId                               	          OBJECT-TYPE
    SYNTAX                  OCTET STRING (SIZE (0..255)) 
    MAX-ACCESS      read-only
    STATUS          current
    DESCRIPTION     "Ptp interface id."
    ::= { ptpIfConfigureEntry 17 }  

ptpIfRcvAnn                               	          OBJECT-TYPE
    SYNTAX                  Integer32 
    MAX-ACCESS      read-only
    STATUS          current
    DESCRIPTION     "Ptp interface receive announce packet."
    ::= { ptpIfConfigureEntry 18 }  

ptpIfRcvDelayReq                              	          OBJECT-TYPE
    SYNTAX                  Integer32 
    MAX-ACCESS      read-only
    STATUS          current
    DESCRIPTION     "Ptp interface receive delay packet."
    ::= { ptpIfConfigureEntry 19 }  

ptpIfRcvDelayResp                              	          OBJECT-TYPE
    SYNTAX                  Integer32 
    MAX-ACCESS      read-only
    STATUS          current
    DESCRIPTION     "Ptp interface receive delay response packet."
    ::= { ptpIfConfigureEntry 20 }  

ptpIfRcvFollowUp                              	          OBJECT-TYPE
    SYNTAX                  Integer32 
    MAX-ACCESS      read-only
    STATUS          current
    DESCRIPTION     "Ptp interface receive follow up packet."
    ::= { ptpIfConfigureEntry 21 }  

ptpIfRcvUnknown                              	          OBJECT-TYPE
    SYNTAX                  Integer32 
    MAX-ACCESS      read-only
    STATUS          current
    DESCRIPTION     "Ptp interface receive unknown packet."
    ::= { ptpIfConfigureEntry 22 }  

ptpIfRcvSync                              	          OBJECT-TYPE
    SYNTAX                  Integer32 
    MAX-ACCESS      read-only
    STATUS          current
    DESCRIPTION     "Ptp interface receive sync packet."
    ::= { ptpIfConfigureEntry 23 }  

ptpIfRcvPDelayReq                              	          OBJECT-TYPE
    SYNTAX                  Integer32 
    MAX-ACCESS      read-only
    STATUS          current
    DESCRIPTION     "Ptp interface receive peer delay packet."
    ::= { ptpIfConfigureEntry 24 }  

ptpIfRcvPDelayResp                              	          OBJECT-TYPE
    SYNTAX                  Integer32 
    MAX-ACCESS      read-only
    STATUS          current
    DESCRIPTION     "Ptp interface receive delay response packet."
    ::= { ptpIfConfigureEntry 25 }  

ptpIfRcvPDelayRespFowllowUp                              	          OBJECT-TYPE
    SYNTAX                  Integer32 
    MAX-ACCESS      read-only
    STATUS          current
    DESCRIPTION     "Ptp interface receive delay response follow up packet."
    ::= { ptpIfConfigureEntry 26 }  

ptpIfSendAnn                               	          OBJECT-TYPE
    SYNTAX                  Integer32 
    MAX-ACCESS      read-only
    STATUS          current
    DESCRIPTION     "Ptp interface send announce packet."
    ::= { ptpIfConfigureEntry 27 }  

ptpIfSendDelayReq                              	          OBJECT-TYPE
    SYNTAX                  Integer32 
    MAX-ACCESS      read-only
    STATUS          current
    DESCRIPTION     "Ptp interface send delay request packet."
    ::= { ptpIfConfigureEntry 28 }  

ptpIfSendDelayResp                              	          OBJECT-TYPE
    SYNTAX                  Integer32 
    MAX-ACCESS      read-only
    STATUS          current
    DESCRIPTION     "Ptp interface send delay response packet."
    ::= { ptpIfConfigureEntry 29 }  

ptpIfSendFollowUp                              	          OBJECT-TYPE
    SYNTAX                  Integer32 
    MAX-ACCESS      read-only
    STATUS          current
    DESCRIPTION     "Ptp interface send follow up packet."
    ::= { ptpIfConfigureEntry 30 }  

ptpIfSendUnknown                              	          OBJECT-TYPE
    SYNTAX                  Integer32 
    MAX-ACCESS      read-only
    STATUS          current
    DESCRIPTION     "Ptp interface send unknown packet."
    ::= { ptpIfConfigureEntry 31 }  

ptpIfSendSync                              	          OBJECT-TYPE
    SYNTAX                  Integer32 
    MAX-ACCESS      read-only
    STATUS          current
    DESCRIPTION     "Ptp interface send sync packet."
    ::= { ptpIfConfigureEntry 32 }  

ptpIfSendPDelayReq                              	          OBJECT-TYPE
    SYNTAX                  Integer32 
    MAX-ACCESS      read-only
    STATUS          current
    DESCRIPTION     "Ptp interface send peer delay request packet."
    ::= { ptpIfConfigureEntry 33 }  

ptpIfSendPDelayResp                              	          OBJECT-TYPE
    SYNTAX                  Integer32 
    MAX-ACCESS      read-only
    STATUS          current
    DESCRIPTION     "Ptp interface send peer delay response packet."
    ::= { ptpIfConfigureEntry 34 }  

ptpIfSendPDelayRespFowllowUp                              	          OBJECT-TYPE
    SYNTAX                  Integer32 
    MAX-ACCESS      read-only
    STATUS          current
    DESCRIPTION     "Ptp interface send peer delay response follow up packet."
    ::= { ptpIfConfigureEntry 35 }  

ptpIfDiscardAnn                               	          OBJECT-TYPE
    SYNTAX                  Integer32 
    MAX-ACCESS      read-only
    STATUS          current
    DESCRIPTION     "Ptp interface discard announce packet."
    ::= { ptpIfConfigureEntry 36 }  

ptpIfDiscardDelayReq                              	          OBJECT-TYPE
    SYNTAX                  Integer32 
    MAX-ACCESS      read-only
    STATUS          current
    DESCRIPTION     "Ptp interface discard delay request packet."
    ::= { ptpIfConfigureEntry 37 }  

ptpIfDiscardDelayResp                              	          OBJECT-TYPE
    SYNTAX                  Integer32 
    MAX-ACCESS      read-only
    STATUS          current
    DESCRIPTION     "Ptp interface discard delay response packet."
    ::= { ptpIfConfigureEntry 38 }  

ptpIfDiscardFollowUp                              	          OBJECT-TYPE
    SYNTAX                  Integer32 
    MAX-ACCESS      read-only
    STATUS          current
    DESCRIPTION     "Ptp interface discard follow up packet."
    ::= { ptpIfConfigureEntry 39 }  

ptpIfDiscardUnknown                              	          OBJECT-TYPE
    SYNTAX                  Integer32 
    MAX-ACCESS      read-only
    STATUS          current
    DESCRIPTION     "Ptp interface discard unknown packet."
    ::= { ptpIfConfigureEntry 40 }  

ptpIfDiscardSync                              	          OBJECT-TYPE
    SYNTAX                  Integer32 
    MAX-ACCESS      read-only
    STATUS          current
    DESCRIPTION     "Ptp interface discard sync packet."
    ::= { ptpIfConfigureEntry 41 }  

ptpIfDiscardPDelayReq                              	          OBJECT-TYPE
    SYNTAX                  Integer32 
    MAX-ACCESS      read-only
    STATUS          current
    DESCRIPTION     "Ptp interface discard delay request packet."
    ::= { ptpIfConfigureEntry 42 }  

ptpIfDiscardPDelayResp                              	          OBJECT-TYPE
    SYNTAX                  Integer32 
    MAX-ACCESS      read-only
    STATUS          current
    DESCRIPTION     "Ptp interface discard peer delay response packet."
    ::= { ptpIfConfigureEntry 43 }  

ptpIfDiscardPDelayRespFowllowUp                              	          OBJECT-TYPE
    SYNTAX                  Integer32 
    MAX-ACCESS      read-only
    STATUS          current
    DESCRIPTION     "Ptp interface discard peer delay response follow up packet."
    ::= { ptpIfConfigureEntry 44 }


-- ## 1.3 show ptp foreign-master


ptpForeignMasterTable         OBJECT-TYPE
    SYNTAX                    SEQUENCE OF PtpForeignMasterEntry
    MAX-ACCESS                not-accessible
    STATUS                    current
    DESCRIPTION
        "The table of Monitor link group."
    ::= { ptp 3 }

ptpForeignMasterEntry         OBJECT-TYPE
    SYNTAX                    PtpForeignMasterEntry
    MAX-ACCESS                not-accessible
    STATUS                    current
    DESCRIPTION
        "The entry of Monitor link group."
    INDEX     { ptpFMIndex,  ptpFMNodeIndex}
    ::= { ptpForeignMasterTable 1 }

PtpForeignMasterEntry    ::=
    SEQUENCE
    {
        ptpFMIndex
            Integer32,
        ptpFMNodeIndex
            Integer32,
        ptpFMBest
            TruthValue,
        ptpFMClockID
            OCTET STRING,
        ptpFMPortNum
            Integer32,
        ptpFMQualification
            Integer32,
        ptpFMIfName
            OCTET STRING
    }

ptpFMIndex           OBJECT-TYPE
    SYNTAX                  Integer32
    MAX-ACCESS              not-accessible
    STATUS                  current
    DESCRIPTION
        "Ptp foreign master interface index. "
    ::= { ptpForeignMasterEntry 1 }

ptpFMNodeIndex           OBJECT-TYPE
    SYNTAX                  Integer32
    MAX-ACCESS              not-accessible
    STATUS                  current
    DESCRIPTION
        "Ptp foreign master node index. "
    ::= { ptpForeignMasterEntry 2 }

ptpFMBest          OBJECT-TYPE
    SYNTAX                  TruthValue
    MAX-ACCESS              read-only
    STATUS                  current
    DESCRIPTION
        "The state of foreign master: true(1): best.false(2): not best."
    ::= { ptpForeignMasterEntry 3 }

ptpFMClockID          OBJECT-TYPE
    SYNTAX                  OCTET STRING (SIZE (0..255))
    MAX-ACCESS              read-only
    STATUS                  current
    DESCRIPTION
        "Ptp foreign master clock id. "
    ::= { ptpForeignMasterEntry 4 }

ptpFMPortNum           OBJECT-TYPE
    SYNTAX                  Integer32
    MAX-ACCESS              read-only
    STATUS                  current
    DESCRIPTION
        "Ptp foreign master port num. "
    ::= { ptpForeignMasterEntry 5 }

ptpFMQualification           OBJECT-TYPE
    SYNTAX                  Integer32
    MAX-ACCESS              read-only
    STATUS                  current
    DESCRIPTION
        "Ptp foreign master qualification. "
    ::= { ptpForeignMasterEntry 6 }

ptpFMIfName         OBJECT-TYPE
    SYNTAX                  OCTET STRING (SIZE (0..255))
    MAX-ACCESS              read-only
    STATUS                  current
    DESCRIPTION
        "Ptp foreign master interface name. "
    ::= { ptpForeignMasterEntry 7 }

--pm                       OBJECT IDENTIFIER ::= { OID 90 }

pmThresholdTable     OBJECT-TYPE
    SYNTAX          SEQUENCE OF PMThresholdEntry
    MAX-ACCESS      not-accessible
    STATUS          current
    DESCRIPTION
        "A table that contains all pm threshold information."
    ::= { pm 1 }

pmThresholdEntry     OBJECT-TYPE
    SYNTAX          PMThresholdEntry
    MAX-ACCESS      not-accessible
    STATUS          current
    DESCRIPTION
        "A list of all pm threshold information."
    INDEX     { pmThresholdIndex  }
    ::= { pmThresholdTable 1 }

PMThresholdEntry    ::=
    SEQUENCE
    {
       pmThresholdIndex           INTEGER,
       pmThreshold15mValue        OCTET STRING,
       pmThreshold1hValue         OCTET STRING,
       pmThreshold1dValue     OCTET STRING
    }

pmThresholdIndex         OBJECT-TYPE
    SYNTAX          INTEGER
    {
        unit-temperature-min(1),
        unit-temperature-max(2),
        sfp-rx-power-min(3),
        sfp-rx-power-max(4),
        sfp-tx-power-min(5),
        sfp-tx-power-max(6),
        if-dropped-events(7),
        if-input-packets(8),
        if-input-bytes(9),
        if-input-broadcasts(10),
        if-input-multicasts(11),
        if-crc-errors(12),
        if-collisions(13),
        if-undersized-packets(14),
        if-oversized-packets(15),
        if-fragments(16),
        if-jabbers(17),
        if-packet-64(18),
        if-packet-65-127(19),
        if-packet-128-255(20),
        if-packet-256-511(21),
        if-packet-512-1023(22),
        if-packet-1024(23),
        if-output-packets(24),
        if-output-bytes(25),
        lsp-pe-out-packets(26),
        lsp-pe-out-bytes(27),
        lsp-p-east-ingress-packets(28),
        lsp-p-east-ingress-bytes(29),
        lsp-p-west-ingress-packets(30),
        lsp-p-west-ingress-bytes(31),
        vpws-ingress-packets(32),
        vpws-ingress-bytes(33),
        vpws-egress-packets(34),
        vpws-egress-bytes(35),
        vpls-ingress-packets(36),
        vpls-ingress-bytes(37),
        vpls-egress-packets(38),
        vpls-egress-bytes(39)
    }
    MAX-ACCESS      not-accessible
    STATUS          current
    DESCRIPTION
        "An index of pm types."
    ::= { pmThresholdEntry 1 }

pmThreshold15mValue         OBJECT-TYPE
    SYNTAX          OCTET STRING
    MAX-ACCESS      read-write
    STATUS          current
    DESCRIPTION
        "Threshold for 15min period."
    ::= { pmThresholdEntry 2 }

pmThreshold1hValue         OBJECT-TYPE
    SYNTAX          OCTET STRING
    MAX-ACCESS      read-write
    STATUS          current
    DESCRIPTION
        "Threshold for 1hour period."
    ::= { pmThresholdEntry 3 }

pmThreshold1dValue         OBJECT-TYPE
    SYNTAX          OCTET STRING
    MAX-ACCESS      read-write
    STATUS          current
    DESCRIPTION
        "Threshold for 1day period."
    ::= { pmThresholdEntry 4 }

pmUnitTempr        OBJECT IDENTIFIER ::= { pm 100 }

pmUnitTemprCurr15mTable     OBJECT-TYPE
    SYNTAX          SEQUENCE OF PMUnitTemprCurr15mEntry
    MAX-ACCESS      not-accessible
    STATUS          current
    DESCRIPTION
        "A table that contains temperature information of all units."
    ::= { pmUnitTempr 1 }

pmUnitTemprCurr15mEntry     OBJECT-TYPE
    SYNTAX          PMUnitTemprCurr15mEntry
    MAX-ACCESS      not-accessible
    STATUS          current
    DESCRIPTION
        "A list of temperature information of all units."
    INDEX     { pmUnitTemprCurr15mIndex  }
    ::= { pmUnitTemprCurr15mTable 1 }

PMUnitTemprCurr15mEntry    ::=
    SEQUENCE
    {
       pmUnitTemprCurr15mIndex     Integer32,
       pmUnitTemprCurr15mId       OCTET STRING,
       pmUnitTemprCurr15mUnitType  INTEGER,
       pmUnitTemprCurr15mAverage  Counter64,
       pmUnitTemprCurr15mMin    Counter64,
       pmUnitTemprCurr15mMax    Counter64,
       pmUnitTemprCurr15mStartTime  DateAndTime,
       pmUnitTemprCurr15mStopTime  DateAndTime
    }

pmUnitTemprCurr15mIndex         OBJECT-TYPE
    SYNTAX          Integer32
    MAX-ACCESS      not-accessible
    STATUS          current
    DESCRIPTION
        "An index of units."
    ::= { pmUnitTemprCurr15mEntry 1 }

pmUnitTemprCurr15mId         OBJECT-TYPE
    SYNTAX          OCTET STRING
    MAX-ACCESS      read-only
    STATUS          current
    DESCRIPTION
        "Unit sensor name."
    ::= { pmUnitTemprCurr15mEntry 2 }

pmUnitTemprCurr15mUnitType         OBJECT-TYPE
    SYNTAX          INTEGER
    {
       mcu(0)
    }
    MAX-ACCESS      read-only
    STATUS          current
    DESCRIPTION
        "Unit type."
    ::= { pmUnitTemprCurr15mEntry 3 }

pmUnitTemprCurr15mAverage         OBJECT-TYPE
    SYNTAX          Counter64
    MAX-ACCESS      read-only
    STATUS          current
    DESCRIPTION
        "Current 15min counter of average unit temperature."
    ::= { pmUnitTemprCurr15mEntry 4 }

pmUnitTemprCurr15mMin         OBJECT-TYPE
    SYNTAX          Counter64
    MAX-ACCESS      read-only
    STATUS          current
    DESCRIPTION
        "Current 15min counter of minimum unit temperature."
    ::= { pmUnitTemprCurr15mEntry 5 }

pmUnitTemprCurr15mMax         OBJECT-TYPE
    SYNTAX          Counter64
    MAX-ACCESS      read-only
    STATUS          current
    DESCRIPTION
        "Current 15min counter of maximum unit temperature."
    ::= { pmUnitTemprCurr15mEntry 6 }

pmUnitTemprCurr15mStartTime         OBJECT-TYPE
    SYNTAX          DateAndTime
    MAX-ACCESS      read-only
    STATUS          current
    DESCRIPTION
        "Current 15min start time."
    ::= { pmUnitTemprCurr15mEntry 100 }

pmUnitTemprCurr15mStopTime         OBJECT-TYPE
    SYNTAX          DateAndTime
    MAX-ACCESS      read-only
    STATUS          current
    DESCRIPTION
        "Current 15min stop time."
    ::= { pmUnitTemprCurr15mEntry 101 }

pmUnitTemprPrev15mTable     OBJECT-TYPE
    SYNTAX          SEQUENCE OF PMUnitTemprPrev15mEntry
    MAX-ACCESS      not-accessible
    STATUS          current
    DESCRIPTION
        "A table that contains temperature information of all units."
    ::= { pmUnitTempr 2 }

pmUnitTemprPrev15mEntry     OBJECT-TYPE
    SYNTAX          PMUnitTemprPrev15mEntry
    MAX-ACCESS      not-accessible
    STATUS          current
    DESCRIPTION
        "A list of temperature information of all units."
    INDEX     { pmUnitTemprPrev15mIndex  }
    ::= { pmUnitTemprPrev15mTable 1 }

PMUnitTemprPrev15mEntry    ::=
    SEQUENCE
    {
       pmUnitTemprPrev15mIndex     Integer32,
       pmUnitTemprPrev15mId      OCTET STRING,
       pmUnitTemprPrev15mUnitType  INTEGER,
       pmUnitTemprPrev15mAverage  Counter64,
       pmUnitTemprPrev15mMin    Counter64,
       pmUnitTemprPrev15mMax    Counter64,
       pmUnitTemprPrev15mStartTime  DateAndTime,
       pmUnitTemprPrev15mStopTime  DateAndTime
    }

pmUnitTemprPrev15mIndex         OBJECT-TYPE
    SYNTAX          Integer32
    MAX-ACCESS      not-accessible
    STATUS          current
    DESCRIPTION
        "An index of units."
    ::= { pmUnitTemprPrev15mEntry 1 }

pmUnitTemprPrev15mId         OBJECT-TYPE
    SYNTAX          OCTET STRING
    MAX-ACCESS      read-only
    STATUS          current
    DESCRIPTION
        "Sensor name."
    ::= { pmUnitTemprPrev15mEntry 2 }

pmUnitTemprPrev15mUnitType         OBJECT-TYPE
    SYNTAX          INTEGER
    {
       mcu(0)
    }
    MAX-ACCESS      read-only
    STATUS          current
    DESCRIPTION
        "Unit type."
    ::= { pmUnitTemprPrev15mEntry 3 }

pmUnitTemprPrev15mAverage         OBJECT-TYPE
    SYNTAX          Counter64
    MAX-ACCESS      read-only
    STATUS          current
    DESCRIPTION
        "Previous 15min counter of average unit temperature."
    ::= { pmUnitTemprPrev15mEntry 4 }

pmUnitTemprPrev15mMin         OBJECT-TYPE
    SYNTAX          Counter64
    MAX-ACCESS      read-only
    STATUS          current
    DESCRIPTION
        "Previous 15min counter of minimum unit temperature."
    ::= { pmUnitTemprPrev15mEntry 5 }

pmUnitTemprPrev15mMax         OBJECT-TYPE
    SYNTAX          Counter64
    MAX-ACCESS      read-only
    STATUS          current
    DESCRIPTION
        "Previous 15min counter of maximum unit temperature."
    ::= { pmUnitTemprPrev15mEntry 6 }

pmUnitTemprPrev15mStartTime         OBJECT-TYPE
    SYNTAX          DateAndTime
    MAX-ACCESS      read-only
    STATUS          current
    DESCRIPTION
        "Previous 15min start time."
    ::= { pmUnitTemprPrev15mEntry 100 }

pmUnitTemprPrev15mStopTime         OBJECT-TYPE
    SYNTAX          DateAndTime
    MAX-ACCESS      read-only
    STATUS          current
    DESCRIPTION
        "Previous 15min stop time."
    ::= { pmUnitTemprPrev15mEntry 101 }


pmUnitTemprCurr1hTable     OBJECT-TYPE
    SYNTAX          SEQUENCE OF PMUnitTemprCurr1hEntry
    MAX-ACCESS      not-accessible
    STATUS          current
    DESCRIPTION
        "A table that contains temperature information of all units."
    ::= { pmUnitTempr 3 }

pmUnitTemprCurr1hEntry     OBJECT-TYPE
    SYNTAX          PMUnitTemprCurr1hEntry
    MAX-ACCESS      not-accessible
    STATUS          current
    DESCRIPTION
        "A list of temperature information of all units."
    INDEX     { pmUnitTemprCurr1hIndex  }
    ::= { pmUnitTemprCurr1hTable 1 }

PMUnitTemprCurr1hEntry    ::=
    SEQUENCE
    {
       pmUnitTemprCurr1hIndex     Integer32,
       pmUnitTemprCurr1hId       OCTET STRING,
       pmUnitTemprCurr1hUnitType  INTEGER,
       pmUnitTemprCurr1hAverage  Counter64,
       pmUnitTemprCurr1hMin    Counter64,
       pmUnitTemprCurr1hMax    Counter64,
       pmUnitTemprCurr1hStartTime  DateAndTime,
       pmUnitTemprCurr1hStopTime  DateAndTime
    }

pmUnitTemprCurr1hIndex         OBJECT-TYPE
    SYNTAX          Integer32
    MAX-ACCESS      not-accessible
    STATUS          current
    DESCRIPTION
        "An index of units."
    ::= { pmUnitTemprCurr1hEntry 1 }

pmUnitTemprCurr1hId         OBJECT-TYPE
    SYNTAX          OCTET STRING
    MAX-ACCESS      read-only
    STATUS          current
    DESCRIPTION
        "Unit sensor name."
    ::= { pmUnitTemprCurr1hEntry 2 }

pmUnitTemprCurr1hUnitType         OBJECT-TYPE
    SYNTAX          INTEGER
    {
       mcu(0)
    }
    MAX-ACCESS      read-only
    STATUS          current
    DESCRIPTION
        "Unit type."
    ::= { pmUnitTemprCurr1hEntry 3 }

pmUnitTemprCurr1hAverage         OBJECT-TYPE
    SYNTAX          Counter64
    MAX-ACCESS      read-only
    STATUS          current
    DESCRIPTION
        "Current 1hour counter of average unit temperature."
    ::= { pmUnitTemprCurr1hEntry 4 }

pmUnitTemprCurr1hMin         OBJECT-TYPE
    SYNTAX          Counter64
    MAX-ACCESS      read-only
    STATUS          current
    DESCRIPTION
        "Current 1hour counter of minimum unit temperature."
    ::= { pmUnitTemprCurr1hEntry 5 }

pmUnitTemprCurr1hMax         OBJECT-TYPE
    SYNTAX          Counter64
    MAX-ACCESS      read-only
    STATUS          current
    DESCRIPTION
        "Current 1hour counter of maximum unit temperature."
    ::= { pmUnitTemprCurr1hEntry 6 }

pmUnitTemprCurr1hStartTime         OBJECT-TYPE
    SYNTAX          DateAndTime
    MAX-ACCESS      read-only
    STATUS          current
    DESCRIPTION
        "Current 1hour start time."
    ::= { pmUnitTemprCurr1hEntry 100 }

pmUnitTemprCurr1hStopTime         OBJECT-TYPE
    SYNTAX          DateAndTime
    MAX-ACCESS      read-only
    STATUS          current
    DESCRIPTION
        "Current 1hour stop time."
    ::= { pmUnitTemprCurr1hEntry 101 }

pmUnitTemprPrev1hTable     OBJECT-TYPE
    SYNTAX          SEQUENCE OF PMUnitTemprPrev1hEntry
    MAX-ACCESS      not-accessible
    STATUS          current
    DESCRIPTION
        "A table that contains temperature information of all units."
    ::= { pmUnitTempr 4 }

pmUnitTemprPrev1hEntry     OBJECT-TYPE
    SYNTAX          PMUnitTemprPrev1hEntry
    MAX-ACCESS      not-accessible
    STATUS          current
    DESCRIPTION
        "A list of temperature information of all units."
    INDEX     { pmUnitTemprPrev1hIndex  }
    ::= { pmUnitTemprPrev1hTable 1 }

PMUnitTemprPrev1hEntry    ::=
    SEQUENCE
    {
       pmUnitTemprPrev1hIndex     Integer32,
       pmUnitTemprPrev1hId      OCTET STRING,
       pmUnitTemprPrev1hUnitType  INTEGER,
       pmUnitTemprPrev1hAverage  Counter64,
       pmUnitTemprPrev1hMin    Counter64,
       pmUnitTemprPrev1hMax    Counter64,
       pmUnitTemprPrev1hStartTime  DateAndTime,
       pmUnitTemprPrev1hStopTime  DateAndTime
    }

pmUnitTemprPrev1hIndex         OBJECT-TYPE
    SYNTAX          Integer32
    MAX-ACCESS      not-accessible
    STATUS          current
    DESCRIPTION
        "An index of units."
    ::= { pmUnitTemprPrev1hEntry 1 }

pmUnitTemprPrev1hId         OBJECT-TYPE
    SYNTAX          OCTET STRING
    MAX-ACCESS      read-only
    STATUS          current
    DESCRIPTION
        "Sensor name."
    ::= { pmUnitTemprPrev1hEntry 2 }

pmUnitTemprPrev1hUnitType         OBJECT-TYPE
    SYNTAX          INTEGER
    {
       mcu(0)
    }
    MAX-ACCESS      read-only
    STATUS          current
    DESCRIPTION
        "Unit type."
    ::= { pmUnitTemprPrev1hEntry 3 }

pmUnitTemprPrev1hAverage         OBJECT-TYPE
    SYNTAX          Counter64
    MAX-ACCESS      read-only
    STATUS          current
    DESCRIPTION
        "Previous 1hour counter of average unit temperature."
    ::= { pmUnitTemprPrev1hEntry 4 }

pmUnitTemprPrev1hMin         OBJECT-TYPE
    SYNTAX          Counter64
    MAX-ACCESS      read-only
    STATUS          current
    DESCRIPTION
        "Previous 1hour counter of minimum unit temperature."
    ::= { pmUnitTemprPrev1hEntry 5 }

pmUnitTemprPrev1hMax         OBJECT-TYPE
    SYNTAX          Counter64
    MAX-ACCESS      read-only
    STATUS          current
    DESCRIPTION
        "Previous 1hour counter of maximum unit temperature."
    ::= { pmUnitTemprPrev1hEntry 6 }

pmUnitTemprPrev1hStartTime         OBJECT-TYPE
    SYNTAX          DateAndTime
    MAX-ACCESS      read-only
    STATUS          current
    DESCRIPTION
        "Previous 1hour start time."
    ::= { pmUnitTemprPrev1hEntry 100 }

pmUnitTemprPrev1hStopTime         OBJECT-TYPE
    SYNTAX          DateAndTime
    MAX-ACCESS      read-only
    STATUS          current
    DESCRIPTION
        "Previous 1hour stop time."
    ::= { pmUnitTemprPrev1hEntry 101 }

pmUnitTemprCurr1dTable     OBJECT-TYPE
    SYNTAX          SEQUENCE OF PMUnitTemprCurr1dEntry
    MAX-ACCESS      not-accessible
    STATUS          current
    DESCRIPTION
        "A table that contains temperature information of all units."
    ::= { pmUnitTempr 5 }

pmUnitTemprCurr1dEntry     OBJECT-TYPE
    SYNTAX          PMUnitTemprCurr1dEntry
    MAX-ACCESS      not-accessible
    STATUS          current
    DESCRIPTION
        "A list of temperature information of all units."
    INDEX     { pmUnitTemprCurr1dIndex  }
    ::= { pmUnitTemprCurr1dTable 1 }

PMUnitTemprCurr1dEntry    ::=
    SEQUENCE
    {
       pmUnitTemprCurr1dIndex      Integer32,
       pmUnitTemprCurr1dId       OCTET STRING,
       pmUnitTemprCurr1dUnitType  INTEGER,
       pmUnitTemprCurr1dAverage   Counter64,
       pmUnitTemprCurr1dMin     Counter64,
       pmUnitTemprCurr1dMax     Counter64,
       pmUnitTemprCurr1dStartTime   DateAndTime,
       pmUnitTemprCurr1dStopTime  DateAndTime
    }

pmUnitTemprCurr1dIndex         OBJECT-TYPE
    SYNTAX          Integer32
    MAX-ACCESS      not-accessible
    STATUS          current
    DESCRIPTION
        "An index of units."
    ::= { pmUnitTemprCurr1dEntry 1 }

pmUnitTemprCurr1dId         OBJECT-TYPE
    SYNTAX          OCTET STRING
    MAX-ACCESS      read-only
    STATUS          current
    DESCRIPTION
        "Sensor name."
    ::= { pmUnitTemprCurr1dEntry 2 }

pmUnitTemprCurr1dUnitType         OBJECT-TYPE
    SYNTAX          INTEGER
    {
       mcu(0)
    }
    MAX-ACCESS      read-only
    STATUS          current
    DESCRIPTION
        "Unit type."
    ::= { pmUnitTemprCurr1dEntry 3 }

pmUnitTemprCurr1dAverage         OBJECT-TYPE
    SYNTAX          Counter64
    MAX-ACCESS      read-only
    STATUS          current
    DESCRIPTION
        "Current 1day counter of average unit temperature."
    ::= { pmUnitTemprCurr1dEntry 4 }

pmUnitTemprCurr1dMin         OBJECT-TYPE
    SYNTAX          Counter64
    MAX-ACCESS      read-only
    STATUS          current
    DESCRIPTION
        "Current 1day counter of minimum unit temperature."
    ::= { pmUnitTemprCurr1dEntry 5 }

pmUnitTemprCurr1dMax         OBJECT-TYPE
    SYNTAX          Counter64
    MAX-ACCESS      read-only
    STATUS          current
    DESCRIPTION
        "Current 1day counter of maximum unit temperature."
    ::= { pmUnitTemprCurr1dEntry 6 }

pmUnitTemprCurr1dStartTime         OBJECT-TYPE
    SYNTAX          DateAndTime
    MAX-ACCESS      read-only
    STATUS          current
    DESCRIPTION
        "Current 1day start time."
    ::= { pmUnitTemprCurr1dEntry 100 }

pmUnitTemprCurr1dStopTime         OBJECT-TYPE
    SYNTAX          DateAndTime
    MAX-ACCESS      read-only
    STATUS          current
    DESCRIPTION
        "Current 1day stop time."
    ::= { pmUnitTemprCurr1dEntry 101 }

pmUnitTemprPrev1dTable     OBJECT-TYPE
    SYNTAX          SEQUENCE OF PMUnitTemprPrev1dEntry
    MAX-ACCESS      not-accessible
    STATUS          current
    DESCRIPTION
        "A table that contains temperature information of all units."
    ::= { pmUnitTempr 6 }

pmUnitTemprPrev1dEntry     OBJECT-TYPE
    SYNTAX          PMUnitTemprPrev1dEntry
    MAX-ACCESS      not-accessible
    STATUS          current
    DESCRIPTION
        "A list of temperature information of all units."
    INDEX     { pmUnitTemprPrev1dIndex  }
    ::= { pmUnitTemprPrev1dTable 1 }

PMUnitTemprPrev1dEntry    ::=
    SEQUENCE
    {
       pmUnitTemprPrev1dIndex      Integer32,
       pmUnitTemprPrev1dId       OCTET STRING,
       pmUnitTemprPrev1dUnitType  INTEGER,
       pmUnitTemprPrev1dAverage   Counter64,
       pmUnitTemprPrev1dMin     Counter64,
       pmUnitTemprPrev1dMax     Counter64,
       pmUnitTemprPrev1dStartTime   DateAndTime,
       pmUnitTemprPrev1dStopTime  DateAndTime
    }

pmUnitTemprPrev1dIndex         OBJECT-TYPE
    SYNTAX          Integer32
    MAX-ACCESS      not-accessible
    STATUS          current
    DESCRIPTION
        "An index of units."
    ::= { pmUnitTemprPrev1dEntry 1 }

pmUnitTemprPrev1dId         OBJECT-TYPE
    SYNTAX          OCTET STRING
    MAX-ACCESS      read-only
    STATUS          current
    DESCRIPTION
        "Unit name."
    ::= { pmUnitTemprPrev1dEntry 2 }

pmUnitTemprPrev1dUnitType         OBJECT-TYPE
    SYNTAX          INTEGER
    {
       mcu(0)
    }
    MAX-ACCESS      read-only
    STATUS          current
    DESCRIPTION
        "Unit type."
    ::= { pmUnitTemprPrev1dEntry 3 }

pmUnitTemprPrev1dAverage         OBJECT-TYPE
    SYNTAX          Counter64
    MAX-ACCESS      read-only
    STATUS          current
    DESCRIPTION
        "Previous 1day counter of average unit temperature."
    ::= { pmUnitTemprPrev1dEntry 4 }

pmUnitTemprPrev1dMin         OBJECT-TYPE
    SYNTAX          Counter64
    MAX-ACCESS      read-only
    STATUS          current
    DESCRIPTION
        "Previous 1day counter of minimu unit temperature."
    ::= { pmUnitTemprPrev1dEntry 5 }

pmUnitTemprPrev1dMax         OBJECT-TYPE
    SYNTAX          Counter64
    MAX-ACCESS      read-only
    STATUS          current
    DESCRIPTION
        "Previous 1day counter of maximum unit temperature."
    ::= { pmUnitTemprPrev1dEntry 6 }

pmUnitTemprPrev1dStartTime         OBJECT-TYPE
    SYNTAX          DateAndTime
    MAX-ACCESS      read-only
    STATUS          current
    DESCRIPTION
        "Previous 1day start time."
    ::= { pmUnitTemprPrev1dEntry 100 }

pmUnitTemprPrev1dStopTime         OBJECT-TYPE
    SYNTAX          DateAndTime
    MAX-ACCESS      read-only
    STATUS          current
    DESCRIPTION
        "Previous 1day stop time."
    ::= { pmUnitTemprPrev1dEntry 101 }

pmTcaUnitTemprMin15mTable     OBJECT-TYPE
    SYNTAX          SEQUENCE OF PMTcaUnitTemprMin15mEntry
    MAX-ACCESS      not-accessible
    STATUS          current
    DESCRIPTION
        "A table that contains temperature information of all units."
    ::= { pmUnitTempr 7 }

pmTcaUnitTemprMin15mEntry     OBJECT-TYPE
    SYNTAX          PMTcaUnitTemprMin15mEntry
    MAX-ACCESS      not-accessible
    STATUS          current
    DESCRIPTION
        "A list of temperature information of all units."
    INDEX     { pmTcaUnitTemprMin15mIndex  }
    ::= { pmTcaUnitTemprMin15mTable 1 }

PMTcaUnitTemprMin15mEntry    ::=
    SEQUENCE
    {
       pmTcaUnitTemprMin15mIndex      Integer32,
       pmTcaUnitTemprMin15mId       OCTET STRING,
       pmTcaUnitTemprMin15mUnitType   INTEGER,
       pmTcaUnitTemprMin15mCnt     Counter64,
       pmTcaUnitTemprMin15mThreshold   Counter64,
       pmTcaUnitTemprMin15mOccurTime   DateAndTime
    }

pmTcaUnitTemprMin15mIndex         OBJECT-TYPE
    SYNTAX          Integer32
    MAX-ACCESS      not-accessible
    STATUS          current
    DESCRIPTION
        "An index of units."
    ::= { pmTcaUnitTemprMin15mEntry 1 }

pmTcaUnitTemprMin15mId         OBJECT-TYPE
    SYNTAX          OCTET STRING
    MAX-ACCESS      read-only
    STATUS          current
    DESCRIPTION
        "Sensor name."
    ::= { pmTcaUnitTemprMin15mEntry 2 }

pmTcaUnitTemprMin15mUnitType         OBJECT-TYPE
    SYNTAX          INTEGER
    {
       mcu(0)
    }
    MAX-ACCESS      read-only
    STATUS          current
    DESCRIPTION
        "Unit type."
    ::= { pmTcaUnitTemprMin15mEntry 3 }

pmTcaUnitTemprMin15mCnt         OBJECT-TYPE
    SYNTAX          Counter64
    MAX-ACCESS      read-only
    STATUS          current
    DESCRIPTION
        "15min counter of unit temperature."
    ::= { pmTcaUnitTemprMin15mEntry 4 }

pmTcaUnitTemprMin15mThreshold         OBJECT-TYPE
    SYNTAX          Counter64
    MAX-ACCESS      read-only
    STATUS          current
    DESCRIPTION
        "15min threshold of unit temperature."
    ::= { pmTcaUnitTemprMin15mEntry 5 }

pmTcaUnitTemprMin15mOccurTime         OBJECT-TYPE
    SYNTAX          DateAndTime
    MAX-ACCESS      read-only
    STATUS          current
    DESCRIPTION
        "Time of the occurrence of the tca."
    ::= { pmTcaUnitTemprMin15mEntry 6 }

pmTcaUnitTemprMin1hTable     OBJECT-TYPE
    SYNTAX          SEQUENCE OF PMTcaUnitTemprMin1hEntry
    MAX-ACCESS      not-accessible
    STATUS          current
    DESCRIPTION
        "A table that contains temperature information of all units."
    ::= { pmUnitTempr 8 }

pmTcaUnitTemprMin1hEntry     OBJECT-TYPE
    SYNTAX          PMTcaUnitTemprMin1hEntry
    MAX-ACCESS      not-accessible
    STATUS          current
    DESCRIPTION
        "A list of temperature information of all units."
    INDEX     { pmTcaUnitTemprMin1hIndex  }
    ::= { pmTcaUnitTemprMin1hTable 1 }

PMTcaUnitTemprMin1hEntry    ::=
    SEQUENCE
    {
       pmTcaUnitTemprMin1hIndex      Integer32,
       pmTcaUnitTemprMin1hId       OCTET STRING,
       pmTcaUnitTemprMin1hUnitType   INTEGER,
       pmTcaUnitTemprMin1hCnt     Counter64,
       pmTcaUnitTemprMin1hThreshold   Counter64,
       pmTcaUnitTemprMin1hOccurTime   DateAndTime
    }

pmTcaUnitTemprMin1hIndex         OBJECT-TYPE
    SYNTAX          Integer32
    MAX-ACCESS      not-accessible
    STATUS          current
    DESCRIPTION
        "An index of units."
    ::= { pmTcaUnitTemprMin1hEntry 1 }

pmTcaUnitTemprMin1hId         OBJECT-TYPE
    SYNTAX          OCTET STRING
    MAX-ACCESS      read-only
    STATUS          current
    DESCRIPTION
        "Sensor name."
    ::= { pmTcaUnitTemprMin1hEntry 2 }

pmTcaUnitTemprMin1hUnitType         OBJECT-TYPE
    SYNTAX          INTEGER
    {
       mcu(0)
    }
    MAX-ACCESS      read-only
    STATUS          current
    DESCRIPTION
        "Unit type."
    ::= { pmTcaUnitTemprMin1hEntry 3 }

pmTcaUnitTemprMin1hCnt         OBJECT-TYPE
    SYNTAX          Counter64
    MAX-ACCESS      read-only
    STATUS          current
    DESCRIPTION
        "1hour counter of unit temperature."
    ::= { pmTcaUnitTemprMin1hEntry 4 }

pmTcaUnitTemprMin1hThreshold         OBJECT-TYPE
    SYNTAX          Counter64
    MAX-ACCESS      read-only
    STATUS          current
    DESCRIPTION
        "1hour threshold of unit temperature."
    ::= { pmTcaUnitTemprMin1hEntry 5 }

pmTcaUnitTemprMin1hOccurTime         OBJECT-TYPE
    SYNTAX          DateAndTime
    MAX-ACCESS      read-only
    STATUS          current
    DESCRIPTION
        "Time of the occurrence of the tca."
    ::= { pmTcaUnitTemprMin1hEntry 6 }

pmTcaUnitTemprMin1dTable     OBJECT-TYPE
    SYNTAX          SEQUENCE OF PMTcaUnitTemprMin1dEntry
    MAX-ACCESS      not-accessible
    STATUS          current
    DESCRIPTION
        "A table that contains temperature information of all units."
    ::= { pmUnitTempr 9 }

pmTcaUnitTemprMin1dEntry     OBJECT-TYPE
    SYNTAX          PMTcaUnitTemprMin1dEntry
    MAX-ACCESS      not-accessible
    STATUS          current
    DESCRIPTION
        "A list of temperature information of all units."
    INDEX     { pmTcaUnitTemprMin1dIndex  }
    ::= { pmTcaUnitTemprMin1dTable 1 }

PMTcaUnitTemprMin1dEntry    ::=
    SEQUENCE
    {
       pmTcaUnitTemprMin1dIndex      Integer32,
       pmTcaUnitTemprMin1dId       OCTET STRING,
       pmTcaUnitTemprMin1dUnitType  INTEGER,
       pmTcaUnitTemprMin1dCnt     Counter64,
       pmTcaUnitTemprMin1dThreshold   Counter64,
       pmTcaUnitTemprMin1dOccurTime   DateAndTime
    }

pmTcaUnitTemprMin1dIndex         OBJECT-TYPE
    SYNTAX          Integer32
    MAX-ACCESS      not-accessible
    STATUS          current
    DESCRIPTION
        "An index of units."
    ::= { pmTcaUnitTemprMin1dEntry 1 }

pmTcaUnitTemprMin1dId         OBJECT-TYPE
    SYNTAX          OCTET STRING
    MAX-ACCESS      read-only
    STATUS          current
    DESCRIPTION
        "Sensor name."
    ::= { pmTcaUnitTemprMin1dEntry 2 }

pmTcaUnitTemprMin1dUnitType         OBJECT-TYPE
    SYNTAX          INTEGER
    {
       mcu(0)
    }
    MAX-ACCESS      read-only
    STATUS          current
    DESCRIPTION
        "Unit type."
    ::= { pmTcaUnitTemprMin1dEntry 3 }

pmTcaUnitTemprMin1dCnt         OBJECT-TYPE
    SYNTAX          Counter64
    MAX-ACCESS      read-only
    STATUS          current
    DESCRIPTION
        "1day counter of unit temperature."
    ::= { pmTcaUnitTemprMin1dEntry 4 }

pmTcaUnitTemprMin1dThreshold         OBJECT-TYPE
    SYNTAX          Counter64
    MAX-ACCESS      read-only
    STATUS          current
    DESCRIPTION
        "1day threshold of unit temperature."
    ::= { pmTcaUnitTemprMin1dEntry 5 }

pmTcaUnitTemprMin1dOccurTime         OBJECT-TYPE
    SYNTAX          DateAndTime
    MAX-ACCESS      read-only
    STATUS          current
    DESCRIPTION
        "Time of the occurrence of the tca."
    ::= { pmTcaUnitTemprMin1dEntry 6 }

pmTcaUnitTemprMax15mTable     OBJECT-TYPE
    SYNTAX          SEQUENCE OF PMTcaUnitTemprMax15mEntry
    MAX-ACCESS      not-accessible
    STATUS          current
    DESCRIPTION
        "A table that contains temperature information of all units."
    ::= { pmUnitTempr 10 }

pmTcaUnitTemprMax15mEntry     OBJECT-TYPE
    SYNTAX          PMTcaUnitTemprMax15mEntry
    MAX-ACCESS      not-accessible
    STATUS          current
    DESCRIPTION
        "A list of temperature information of all units."
    INDEX     { pmTcaUnitTemprMax15mIndex  }
    ::= { pmTcaUnitTemprMax15mTable 1 }

PMTcaUnitTemprMax15mEntry    ::=
    SEQUENCE
    {
       pmTcaUnitTemprMax15mIndex      Integer32,
       pmTcaUnitTemprMax15mId        OCTET STRING,
       pmTcaUnitTemprMax15mUnitType   INTEGER,
       pmTcaUnitTemprMax15mCnt     Counter64,
       pmTcaUnitTemprMax15mThreshold   Counter64,
       pmTcaUnitTemprMax15mOccurTime   DateAndTime
    }

pmTcaUnitTemprMax15mIndex         OBJECT-TYPE
    SYNTAX          Integer32
    MAX-ACCESS      not-accessible
    STATUS          current
    DESCRIPTION
        "An index of units."
    ::= { pmTcaUnitTemprMax15mEntry 1 }

pmTcaUnitTemprMax15mId         OBJECT-TYPE
    SYNTAX          OCTET STRING
    MAX-ACCESS      read-only
    STATUS          current
    DESCRIPTION
        "Sensor name."
    ::= { pmTcaUnitTemprMax15mEntry 2 }

pmTcaUnitTemprMax15mUnitType         OBJECT-TYPE
    SYNTAX          INTEGER
    {
       mcu(0)
    }
    MAX-ACCESS      read-only
    STATUS          current
    DESCRIPTION
        "Unit type."
    ::= { pmTcaUnitTemprMax15mEntry 3 }

pmTcaUnitTemprMax15mCnt         OBJECT-TYPE
    SYNTAX          Counter64
    MAX-ACCESS      read-only
    STATUS          current
    DESCRIPTION
        "15min counter of unit temperature."
    ::= { pmTcaUnitTemprMax15mEntry 4 }

pmTcaUnitTemprMax15mThreshold         OBJECT-TYPE
    SYNTAX          Counter64
    MAX-ACCESS      read-only
    STATUS          current
    DESCRIPTION
        "15min threshold of unit temperature."
    ::= { pmTcaUnitTemprMax15mEntry 5 }

pmTcaUnitTemprMax15mOccurTime         OBJECT-TYPE
    SYNTAX          DateAndTime
    MAX-ACCESS      read-only
    STATUS          current
    DESCRIPTION
        "Time of the occurrence of the tca."
    ::= { pmTcaUnitTemprMax15mEntry 6 }

pmTcaUnitTemprMax1hTable     OBJECT-TYPE
    SYNTAX          SEQUENCE OF PMTcaUnitTemprMax1hEntry
    MAX-ACCESS      not-accessible
    STATUS          current
    DESCRIPTION
        "A table that contains temperature information of all units."
    ::= { pmUnitTempr 11 }

pmTcaUnitTemprMax1hEntry     OBJECT-TYPE
    SYNTAX          PMTcaUnitTemprMax1hEntry
    MAX-ACCESS      not-accessible
    STATUS          current
    DESCRIPTION
        "A list of temperature information of all units."
    INDEX     { pmTcaUnitTemprMax1hIndex  }
    ::= { pmTcaUnitTemprMax1hTable 1 }

PMTcaUnitTemprMax1hEntry    ::=
    SEQUENCE
    {
       pmTcaUnitTemprMax1hIndex      Integer32,
       pmTcaUnitTemprMax1hId        OCTET STRING,
       pmTcaUnitTemprMax1hUnitType   INTEGER,
       pmTcaUnitTemprMax1hCnt     Counter64,
       pmTcaUnitTemprMax1hThreshold   Counter64,
       pmTcaUnitTemprMax1hOccurTime   DateAndTime
    }

pmTcaUnitTemprMax1hIndex         OBJECT-TYPE
    SYNTAX          Integer32
    MAX-ACCESS      not-accessible
    STATUS          current
    DESCRIPTION
        "An index of units."
    ::= { pmTcaUnitTemprMax1hEntry 1 }

pmTcaUnitTemprMax1hId         OBJECT-TYPE
    SYNTAX          OCTET STRING
    MAX-ACCESS      read-only
    STATUS          current
    DESCRIPTION
        "Sensor name."
    ::= { pmTcaUnitTemprMax1hEntry 2 }

pmTcaUnitTemprMax1hUnitType         OBJECT-TYPE
    SYNTAX          INTEGER
    {
       mcu(0)
    }
    MAX-ACCESS      read-only
    STATUS          current
    DESCRIPTION
        "Unit type."
    ::= { pmTcaUnitTemprMax1hEntry 3 }

pmTcaUnitTemprMax1hCnt         OBJECT-TYPE
    SYNTAX          Counter64
    MAX-ACCESS      read-only
    STATUS          current
    DESCRIPTION
        "1hour counter of unit temperature."
    ::= { pmTcaUnitTemprMax1hEntry 4 }

pmTcaUnitTemprMax1hThreshold         OBJECT-TYPE
    SYNTAX          Counter64
    MAX-ACCESS      read-only
    STATUS          current
    DESCRIPTION
        "1hour threshold of unit temperature."
    ::= { pmTcaUnitTemprMax1hEntry 5 }

pmTcaUnitTemprMax1hOccurTime         OBJECT-TYPE
    SYNTAX          DateAndTime
    MAX-ACCESS      read-only
    STATUS          current
    DESCRIPTION
        "Time of the occurrence of the tca."
    ::= { pmTcaUnitTemprMax1hEntry 6 }

pmTcaUnitTemprMax1dTable     OBJECT-TYPE
    SYNTAX          SEQUENCE OF PMTcaUnitTemprMax1dEntry
    MAX-ACCESS      not-accessible
    STATUS          current
    DESCRIPTION
        "A table that contains temperature information of all units."
    ::= { pmUnitTempr 12 }

pmTcaUnitTemprMax1dEntry     OBJECT-TYPE
    SYNTAX          PMTcaUnitTemprMax1dEntry
    MAX-ACCESS      not-accessible
    STATUS          current
    DESCRIPTION
        "A list of temperature information of all units."
    INDEX     { pmTcaUnitTemprMax1dIndex  }
    ::= { pmTcaUnitTemprMax1dTable 1 }

PMTcaUnitTemprMax1dEntry    ::=
    SEQUENCE
    {
       pmTcaUnitTemprMax1dIndex      Integer32,
       pmTcaUnitTemprMax1dId       OCTET STRING,
       pmTcaUnitTemprMax1dUnitType  INTEGER,
       pmTcaUnitTemprMax1dCnt     Counter64,
       pmTcaUnitTemprMax1dThreshold   Counter64,
       pmTcaUnitTemprMax1dOccurTime   DateAndTime
    }

pmTcaUnitTemprMax1dIndex         OBJECT-TYPE
    SYNTAX          Integer32
    MAX-ACCESS      not-accessible
    STATUS          current
    DESCRIPTION
        "An index of units."
    ::= { pmTcaUnitTemprMax1dEntry 1 }

pmTcaUnitTemprMax1dId         OBJECT-TYPE
    SYNTAX          OCTET STRING
    MAX-ACCESS      read-only
    STATUS          current
    DESCRIPTION
        "Unit name."
    ::= { pmTcaUnitTemprMax1dEntry 2 }

pmTcaUnitTemprMax1dUnitType         OBJECT-TYPE
    SYNTAX          INTEGER
    {
       mcu(0)
    }
    MAX-ACCESS      read-only
    STATUS          current
    DESCRIPTION
        "Unit type."
    ::= { pmTcaUnitTemprMax1dEntry 3 }

pmTcaUnitTemprMax1dCnt         OBJECT-TYPE
    SYNTAX          Counter64
    MAX-ACCESS      read-only
    STATUS          current
    DESCRIPTION
        "1day counter of unit temperature."
    ::= { pmTcaUnitTemprMax1dEntry 4 }

pmTcaUnitTemprMax1dThreshold         OBJECT-TYPE
    SYNTAX          Counter64
    MAX-ACCESS      read-only
    STATUS          current
    DESCRIPTION
        "1day threshold of unit temperature."
    ::= { pmTcaUnitTemprMax1dEntry 5 }

pmTcaUnitTemprMax1dOccurTime         OBJECT-TYPE
    SYNTAX          DateAndTime
    MAX-ACCESS      read-only
    STATUS          current
    DESCRIPTION
        "Time of the occurrence of the tca."
    ::= { pmTcaUnitTemprMax1dEntry 6 }

pmSFPPower        OBJECT IDENTIFIER ::= { pm 101 }

pmSFPPowerCurr15mTable     OBJECT-TYPE
    SYNTAX          SEQUENCE OF PMSFPPowerCurr15mEntry
    MAX-ACCESS      not-accessible
    STATUS          current
    DESCRIPTION
        "A table that contains temperature information of all units."
    ::= { pmSFPPower 1 }

pmSFPPowerCurr15mEntry     OBJECT-TYPE
    SYNTAX          PMSFPPowerCurr15mEntry
    MAX-ACCESS      not-accessible
    STATUS          current
    DESCRIPTION
        "A list of temperature information of all units."
    INDEX     { pmSFPPowerCurr15mIndex  }
    ::= { pmSFPPowerCurr15mTable 1 }

PMSFPPowerCurr15mEntry    ::=
    SEQUENCE
    {
       pmSFPPowerCurr15mIndex      Integer32,
       pmSFPPowerCurr15mId       OCTET STRING,
       pmSFPPowerCurr15mUnitType   INTEGER,
       pmSFPPowerCurr15mRxAverage  Counter64,
       pmSFPPowerCurr15mRxMin    Counter64,
       pmSFPPowerCurr15mRxMax    Counter64,
       pmSFPPowerCurr15mTxAverage  Counter64,
       pmSFPPowerCurr15mTxMin    Counter64,
       pmSFPPowerCurr15mTxMax    Counter64,
       pmSFPPowerCurr15mStartTime    DateAndTime,
       pmSFPPowerCurr15mStopTime   DateAndTime
    }

pmSFPPowerCurr15mIndex         OBJECT-TYPE
    SYNTAX          Integer32
    MAX-ACCESS      not-accessible
    STATUS          current
    DESCRIPTION
        "An index of units."
    ::= { pmSFPPowerCurr15mEntry 1 }

pmSFPPowerCurr15mId         OBJECT-TYPE
    SYNTAX          OCTET STRING
    MAX-ACCESS      read-only
    STATUS          current
    DESCRIPTION
        "SFP name."
    ::= { pmSFPPowerCurr15mEntry 2 }

pmSFPPowerCurr15mUnitType         OBJECT-TYPE
    SYNTAX          INTEGER
    {
       mcu(0)
    }
    MAX-ACCESS      read-only
    STATUS          current
    DESCRIPTION
        "Unit type."
    ::= { pmSFPPowerCurr15mEntry 3 }

pmSFPPowerCurr15mRxAverage         OBJECT-TYPE
    SYNTAX          Counter64
    MAX-ACCESS      read-only
    STATUS          current
    DESCRIPTION
        "Current 15min counter of average sfp rx power."
    ::= { pmSFPPowerCurr15mEntry 4 }

pmSFPPowerCurr15mRxMin         OBJECT-TYPE
    SYNTAX          Counter64
    MAX-ACCESS      read-only
    STATUS          current
    DESCRIPTION
        "Current 15min counter of minimum sfp rx power."
    ::= { pmSFPPowerCurr15mEntry 5 }

pmSFPPowerCurr15mRxMax         OBJECT-TYPE
    SYNTAX          Counter64
    MAX-ACCESS      read-only
    STATUS          current
    DESCRIPTION
        "Current 15min counter of maximum sfp rx power."
    ::= { pmSFPPowerCurr15mEntry 6 }

pmSFPPowerCurr15mTxAverage         OBJECT-TYPE
    SYNTAX          Counter64
    MAX-ACCESS      read-only
    STATUS          current
    DESCRIPTION
        "Current 15min counter of average sfp tx power."
    ::= { pmSFPPowerCurr15mEntry 7 }

pmSFPPowerCurr15mTxMin         OBJECT-TYPE
    SYNTAX          Counter64
    MAX-ACCESS      read-only
    STATUS          current
    DESCRIPTION
        "Current 15min counter of minimum sfp tx power."
    ::= { pmSFPPowerCurr15mEntry 8 }

pmSFPPowerCurr15mTxMax         OBJECT-TYPE
    SYNTAX          Counter64
    MAX-ACCESS      read-only
    STATUS          current
    DESCRIPTION
        "Current 15min counter of maximum sfp tx power."
    ::= { pmSFPPowerCurr15mEntry 9 }

pmSFPPowerCurr15mStartTime         OBJECT-TYPE
    SYNTAX          DateAndTime
    MAX-ACCESS      read-only
    STATUS          current
    DESCRIPTION
        "Current 15min start time."
    ::= { pmSFPPowerCurr15mEntry 100 }

pmSFPPowerCurr15mStopTime         OBJECT-TYPE
    SYNTAX          DateAndTime
    MAX-ACCESS      read-only
    STATUS          current
    DESCRIPTION
        "Current 15min stop time."
    ::= { pmSFPPowerCurr15mEntry 101 }

pmSFPPowerPrev15mTable     OBJECT-TYPE
    SYNTAX          SEQUENCE OF PMSFPPowerPrev15mEntry
    MAX-ACCESS      not-accessible
    STATUS          current
    DESCRIPTION
        "A table that contains temperature information of all units."
    ::= { pmSFPPower 2 }

pmSFPPowerPrev15mEntry     OBJECT-TYPE
    SYNTAX          PMSFPPowerPrev15mEntry
    MAX-ACCESS      not-accessible
    STATUS          current
    DESCRIPTION
        "A list of temperature information of all units."
    INDEX     { pmSFPPowerPrev15mIndex  }
    ::= { pmSFPPowerPrev15mTable 1 }

PMSFPPowerPrev15mEntry    ::=
    SEQUENCE
    {
       pmSFPPowerPrev15mIndex      Integer32,
       pmSFPPowerPrev15mId       OCTET STRING,
       pmSFPPowerPrev15mUnitType   INTEGER,
       pmSFPPowerPrev15mRxAverage  Counter64,
       pmSFPPowerPrev15mRxMin    Counter64,
       pmSFPPowerPrev15mRxMax    Counter64,
       pmSFPPowerPrev15mTxAverage  Counter64,
       pmSFPPowerPrev15mTxMin    Counter64,
       pmSFPPowerPrev15mTxMax    Counter64,
       pmSFPPowerPrev15mStartTime    DateAndTime,
       pmSFPPowerPrev15mStopTime   DateAndTime
    }

pmSFPPowerPrev15mIndex         OBJECT-TYPE
    SYNTAX          Integer32
    MAX-ACCESS      not-accessible
    STATUS          current
    DESCRIPTION
        "An index of units."
    ::= { pmSFPPowerPrev15mEntry 1 }

pmSFPPowerPrev15mId         OBJECT-TYPE
    SYNTAX          OCTET STRING
    MAX-ACCESS      read-only
    STATUS          current
    DESCRIPTION
        "SFP name."
    ::= { pmSFPPowerPrev15mEntry 2 }

pmSFPPowerPrev15mUnitType         OBJECT-TYPE
    SYNTAX          INTEGER
    {
       mcu(0)
    }
    MAX-ACCESS      read-only
    STATUS          current
    DESCRIPTION
        "Unit type."
    ::= { pmSFPPowerPrev15mEntry 3 }

pmSFPPowerPrev15mRxAverage         OBJECT-TYPE
    SYNTAX          Counter64
    MAX-ACCESS      read-only
    STATUS          current
    DESCRIPTION
        "Previous 15min counter of average sfp rx power."
    ::= { pmSFPPowerPrev15mEntry 4 }

pmSFPPowerPrev15mRxMin         OBJECT-TYPE
    SYNTAX          Counter64
    MAX-ACCESS      read-only
    STATUS          current
    DESCRIPTION
        "Previous 15min counter of minimum sfp rx power."
    ::= { pmSFPPowerPrev15mEntry 5 }

pmSFPPowerPrev15mRxMax         OBJECT-TYPE
    SYNTAX          Counter64
    MAX-ACCESS      read-only
    STATUS          current
    DESCRIPTION
        "Previous 15min counter of maximum sfp rx power."
    ::= { pmSFPPowerPrev15mEntry 6 }

pmSFPPowerPrev15mTxAverage         OBJECT-TYPE
    SYNTAX          Counter64
    MAX-ACCESS      read-only
    STATUS          current
    DESCRIPTION
        "Previous 15min counter of average sfp tx power."
    ::= { pmSFPPowerPrev15mEntry 7 }

pmSFPPowerPrev15mTxMin         OBJECT-TYPE
    SYNTAX          Counter64
    MAX-ACCESS      read-only
    STATUS          current
    DESCRIPTION
        "Previous 15min counter of minimum sfp tx power."
    ::= { pmSFPPowerPrev15mEntry 8 }

pmSFPPowerPrev15mTxMax         OBJECT-TYPE
    SYNTAX          Counter64
    MAX-ACCESS      read-only
    STATUS          current
    DESCRIPTION
        "Previous 15min counter of maximum sfp tx power."
    ::= { pmSFPPowerPrev15mEntry 9 }

pmSFPPowerPrev15mStartTime         OBJECT-TYPE
    SYNTAX          DateAndTime
    MAX-ACCESS      read-only
    STATUS          current
    DESCRIPTION
        "Previous 15min start time."
    ::= { pmSFPPowerPrev15mEntry 100 }

pmSFPPowerPrev15mStopTime         OBJECT-TYPE
    SYNTAX          DateAndTime
    MAX-ACCESS      read-only
    STATUS          current
    DESCRIPTION
        "Previous 15min stop time."
    ::= { pmSFPPowerPrev15mEntry 101 }

pmSFPPowerCurr1hTable     OBJECT-TYPE
    SYNTAX          SEQUENCE OF PMSFPPowerCurr1hEntry
    MAX-ACCESS      not-accessible
    STATUS          current
    DESCRIPTION
        "A table that contains temperature information of all units."
    ::= { pmSFPPower 3 }

pmSFPPowerCurr1hEntry     OBJECT-TYPE
    SYNTAX          PMSFPPowerCurr1hEntry
    MAX-ACCESS      not-accessible
    STATUS          current
    DESCRIPTION
        "A list of temperature information of all units."
    INDEX     { pmSFPPowerCurr1hIndex  }
    ::= { pmSFPPowerCurr1hTable 1 }

PMSFPPowerCurr1hEntry    ::=
    SEQUENCE
    {
       pmSFPPowerCurr1hIndex      Integer32,
       pmSFPPowerCurr1hId       OCTET STRING,
       pmSFPPowerCurr1hUnitType   INTEGER,
       pmSFPPowerCurr1hRxAverage  Counter64,
       pmSFPPowerCurr1hRxMin    Counter64,
       pmSFPPowerCurr1hRxMax    Counter64,
       pmSFPPowerCurr1hTxAverage  Counter64,
       pmSFPPowerCurr1hTxMin    Counter64,
       pmSFPPowerCurr1hTxMax    Counter64,
       pmSFPPowerCurr1hStartTime    DateAndTime,
       pmSFPPowerCurr1hStopTime   DateAndTime
    }

pmSFPPowerCurr1hIndex         OBJECT-TYPE
    SYNTAX          Integer32
    MAX-ACCESS      not-accessible
    STATUS          current
    DESCRIPTION
        "An index of units."
    ::= { pmSFPPowerCurr1hEntry 1 }

pmSFPPowerCurr1hId         OBJECT-TYPE
    SYNTAX          OCTET STRING
    MAX-ACCESS      read-only
    STATUS          current
    DESCRIPTION
        "SFP name."
    ::= { pmSFPPowerCurr1hEntry 2 }

pmSFPPowerCurr1hUnitType         OBJECT-TYPE
    SYNTAX          INTEGER
    {
       mcu(0)
    }
    MAX-ACCESS      read-only
    STATUS          current
    DESCRIPTION
        "Unit type."
    ::= { pmSFPPowerCurr1hEntry 3 }

pmSFPPowerCurr1hRxAverage         OBJECT-TYPE
    SYNTAX          Counter64
    MAX-ACCESS      read-only
    STATUS          current
    DESCRIPTION
        "Current 1hour counter of average sfp rx power."
    ::= { pmSFPPowerCurr1hEntry 4 }

pmSFPPowerCurr1hRxMin         OBJECT-TYPE
    SYNTAX          Counter64
    MAX-ACCESS      read-only
    STATUS          current
    DESCRIPTION
        "Current 1hour counter of minimum sfp rx power."
    ::= { pmSFPPowerCurr1hEntry 5 }

pmSFPPowerCurr1hRxMax         OBJECT-TYPE
    SYNTAX          Counter64
    MAX-ACCESS      read-only
    STATUS          current
    DESCRIPTION
        "Current 1hour counter of maximum sfp rx power."
    ::= { pmSFPPowerCurr1hEntry 6 }

pmSFPPowerCurr1hTxAverage         OBJECT-TYPE
    SYNTAX          Counter64
    MAX-ACCESS      read-only
    STATUS          current
    DESCRIPTION
        "Current 1hour counter of average sfp tx power."
    ::= { pmSFPPowerCurr1hEntry 7 }

pmSFPPowerCurr1hTxMin         OBJECT-TYPE
    SYNTAX          Counter64
    MAX-ACCESS      read-only
    STATUS          current
    DESCRIPTION
        "Current 1hour counter of minimum sfp tx power."
    ::= { pmSFPPowerCurr1hEntry 8 }

pmSFPPowerCurr1hTxMax         OBJECT-TYPE
    SYNTAX          Counter64
    MAX-ACCESS      read-only
    STATUS          current
    DESCRIPTION
        "Current 1hour counter of maximum sfp tx power."
    ::= { pmSFPPowerCurr1hEntry 9 }

pmSFPPowerCurr1hStartTime         OBJECT-TYPE
    SYNTAX          DateAndTime
    MAX-ACCESS      read-only
    STATUS          current
    DESCRIPTION
        "Current 1hour start time."
    ::= { pmSFPPowerCurr1hEntry 100 }

pmSFPPowerCurr1hStopTime         OBJECT-TYPE
    SYNTAX          DateAndTime
    MAX-ACCESS      read-only
    STATUS          current
    DESCRIPTION
        "Current 1hour stop time."
    ::= { pmSFPPowerCurr1hEntry 101 }

pmSFPPowerPrev1hTable     OBJECT-TYPE
    SYNTAX          SEQUENCE OF PMSFPPowerPrev1hEntry
    MAX-ACCESS      not-accessible
    STATUS          current
    DESCRIPTION
        "A table that contains temperature information of all units."
    ::= { pmSFPPower 4 }

pmSFPPowerPrev1hEntry     OBJECT-TYPE
    SYNTAX          PMSFPPowerPrev1hEntry
    MAX-ACCESS      not-accessible
    STATUS          current
    DESCRIPTION
        "A list of temperature information of all units."
    INDEX     { pmSFPPowerPrev1hIndex  }
    ::= { pmSFPPowerPrev1hTable 1 }

PMSFPPowerPrev1hEntry    ::=
    SEQUENCE
    {
       pmSFPPowerPrev1hIndex      Integer32,
       pmSFPPowerPrev1hId       OCTET STRING,
       pmSFPPowerPrev1hUnitType   INTEGER,
       pmSFPPowerPrev1hRxAverage  Counter64,
       pmSFPPowerPrev1hRxMin    Counter64,
       pmSFPPowerPrev1hRxMax    Counter64,
       pmSFPPowerPrev1hTxAverage  Counter64,
       pmSFPPowerPrev1hTxMin    Counter64,
       pmSFPPowerPrev1hTxMax    Counter64,
       pmSFPPowerPrev1hStartTime    DateAndTime,
       pmSFPPowerPrev1hStopTime   DateAndTime
    }

pmSFPPowerPrev1hIndex         OBJECT-TYPE
    SYNTAX          Integer32
    MAX-ACCESS      not-accessible
    STATUS          current
    DESCRIPTION
        "An index of units."
    ::= { pmSFPPowerPrev1hEntry 1 }

pmSFPPowerPrev1hId         OBJECT-TYPE
    SYNTAX          OCTET STRING
    MAX-ACCESS      read-only
    STATUS          current
    DESCRIPTION
        "SFP name."
    ::= { pmSFPPowerPrev1hEntry 2 }

pmSFPPowerPrev1hUnitType         OBJECT-TYPE
    SYNTAX          INTEGER
    {
       mcu(0)
    }
    MAX-ACCESS      read-only
    STATUS          current
    DESCRIPTION
        "Unit type."
    ::= { pmSFPPowerPrev1hEntry 3 }

pmSFPPowerPrev1hRxAverage         OBJECT-TYPE
    SYNTAX          Counter64
    MAX-ACCESS      read-only
    STATUS          current
    DESCRIPTION
        "Previous 1hour counter of average sfp rx power."
    ::= { pmSFPPowerPrev1hEntry 4 }

pmSFPPowerPrev1hRxMin         OBJECT-TYPE
    SYNTAX          Counter64
    MAX-ACCESS      read-only
    STATUS          current
    DESCRIPTION
        "Previous 1hour counter of minimum sfp rx power."
    ::= { pmSFPPowerPrev1hEntry 5 }

pmSFPPowerPrev1hRxMax         OBJECT-TYPE
    SYNTAX          Counter64
    MAX-ACCESS      read-only
    STATUS          current
    DESCRIPTION
        "Previous 1hour counter of maximum sfp rx power."
    ::= { pmSFPPowerPrev1hEntry 6 }

pmSFPPowerPrev1hTxAverage         OBJECT-TYPE
    SYNTAX          Counter64
    MAX-ACCESS      read-only
    STATUS          current
    DESCRIPTION
        "Previous 1hour counter of average sfp tx power."
    ::= { pmSFPPowerPrev1hEntry 7 }

pmSFPPowerPrev1hTxMin         OBJECT-TYPE
    SYNTAX          Counter64
    MAX-ACCESS      read-only
    STATUS          current
    DESCRIPTION
        "Previous 1hour counter of minimum sfp tx power."
    ::= { pmSFPPowerPrev1hEntry 8 }

pmSFPPowerPrev1hTxMax         OBJECT-TYPE
    SYNTAX          Counter64
    MAX-ACCESS      read-only
    STATUS          current
    DESCRIPTION
        "Previous 1hour counter of maximum sfp tx power."
    ::= { pmSFPPowerPrev1hEntry 9 }

pmSFPPowerPrev1hStartTime         OBJECT-TYPE
    SYNTAX          DateAndTime
    MAX-ACCESS      read-only
    STATUS          current
    DESCRIPTION
        "Previous 1hour start time."
    ::= { pmSFPPowerPrev1hEntry 100 }

pmSFPPowerPrev1hStopTime         OBJECT-TYPE
    SYNTAX          DateAndTime
    MAX-ACCESS      read-only
    STATUS          current
    DESCRIPTION
        "Previous 1hour stop time."
    ::= { pmSFPPowerPrev1hEntry 101 }

pmSFPPowerCurr1dTable     OBJECT-TYPE
    SYNTAX          SEQUENCE OF PMSFPPowerCurr1dEntry
    MAX-ACCESS      not-accessible
    STATUS          current
    DESCRIPTION
        "A table that contains temperature information of all units."
    ::= { pmSFPPower 5 }

pmSFPPowerCurr1dEntry     OBJECT-TYPE
    SYNTAX          PMSFPPowerCurr1dEntry
    MAX-ACCESS      not-accessible
    STATUS          current
    DESCRIPTION
        "A list of temperature information of all units."
    INDEX     { pmSFPPowerCurr1dIndex  }
    ::= { pmSFPPowerCurr1dTable 1 }

PMSFPPowerCurr1dEntry    ::=
    SEQUENCE
    {
       pmSFPPowerCurr1dIndex      Integer32,
       pmSFPPowerCurr1dId       OCTET STRING,
       pmSFPPowerCurr1dUnitType   INTEGER,
       pmSFPPowerCurr1dRxAverage  Counter64,
       pmSFPPowerCurr1dRxMin    Counter64,
       pmSFPPowerCurr1dRxMax    Counter64,
       pmSFPPowerCurr1dTxAverage  Counter64,
       pmSFPPowerCurr1dTxMin    Counter64,
       pmSFPPowerCurr1dTxMax    Counter64,
       pmSFPPowerCurr1dStartTime    DateAndTime,
       pmSFPPowerCurr1dStopTime   DateAndTime
    }

pmSFPPowerCurr1dIndex         OBJECT-TYPE
    SYNTAX          Integer32
    MAX-ACCESS      not-accessible
    STATUS          current
    DESCRIPTION
        "An index of units."
    ::= { pmSFPPowerCurr1dEntry 1 }

pmSFPPowerCurr1dId         OBJECT-TYPE
    SYNTAX          OCTET STRING
    MAX-ACCESS      read-only
    STATUS          current
    DESCRIPTION
        "SFP name."
    ::= { pmSFPPowerCurr1dEntry 2 }

pmSFPPowerCurr1dUnitType         OBJECT-TYPE
    SYNTAX          INTEGER
    {
       mcu(0)
    }
    MAX-ACCESS      read-only
    STATUS          current
    DESCRIPTION
        "Unit type."
    ::= { pmSFPPowerCurr1dEntry 3 }

pmSFPPowerCurr1dRxAverage         OBJECT-TYPE
    SYNTAX          Counter64
    MAX-ACCESS      read-only
    STATUS          current
    DESCRIPTION
        "Current 1day counter of average sfp rx power."
    ::= { pmSFPPowerCurr1dEntry 4 }

pmSFPPowerCurr1dRxMin         OBJECT-TYPE
    SYNTAX          Counter64
    MAX-ACCESS      read-only
    STATUS          current
    DESCRIPTION
        "Current 1day counter of minimum sfp rx power."
    ::= { pmSFPPowerCurr1dEntry 5 }

pmSFPPowerCurr1dRxMax         OBJECT-TYPE
    SYNTAX          Counter64
    MAX-ACCESS      read-only
    STATUS          current
    DESCRIPTION
        "Current 1day counter of maximum sfp rx power."
    ::= { pmSFPPowerCurr1dEntry 6 }

pmSFPPowerCurr1dTxAverage         OBJECT-TYPE
    SYNTAX          Counter64
    MAX-ACCESS      read-only
    STATUS          current
    DESCRIPTION
        "Current 1day counter of average sfp tx power."
    ::= { pmSFPPowerCurr1dEntry 7 }

pmSFPPowerCurr1dTxMin         OBJECT-TYPE
    SYNTAX          Counter64
    MAX-ACCESS      read-only
    STATUS          current
    DESCRIPTION
        "Current 1day counter of minimum sfp tx power."
    ::= { pmSFPPowerCurr1dEntry 8 }

pmSFPPowerCurr1dTxMax         OBJECT-TYPE
    SYNTAX          Counter64
    MAX-ACCESS      read-only
    STATUS          current
    DESCRIPTION
        "Current 1day counter of maximum sfp tx power."
    ::= { pmSFPPowerCurr1dEntry 9 }

pmSFPPowerCurr1dStartTime         OBJECT-TYPE
    SYNTAX          DateAndTime
    MAX-ACCESS      read-only
    STATUS          current
    DESCRIPTION
        "Current 1day start time."
    ::= { pmSFPPowerCurr1dEntry 100 }

pmSFPPowerCurr1dStopTime         OBJECT-TYPE
    SYNTAX          DateAndTime
    MAX-ACCESS      read-only
    STATUS          current
    DESCRIPTION
        "Current 1day stop time."
    ::= { pmSFPPowerCurr1dEntry 101 }

pmSFPPowerPrev1dTable     OBJECT-TYPE
    SYNTAX          SEQUENCE OF PMSFPPowerPrev1dEntry
    MAX-ACCESS      not-accessible
    STATUS          current
    DESCRIPTION
        "A table that contains temperature information of all units."
    ::= { pmSFPPower 6 }

pmSFPPowerPrev1dEntry     OBJECT-TYPE
    SYNTAX          PMSFPPowerPrev1dEntry
    MAX-ACCESS      not-accessible
    STATUS          current
    DESCRIPTION
        "A list of temperature information of all units."
    INDEX     { pmSFPPowerPrev1dIndex  }
    ::= { pmSFPPowerPrev1dTable 1 }

PMSFPPowerPrev1dEntry    ::=
    SEQUENCE
    {
       pmSFPPowerPrev1dIndex      Integer32,
       pmSFPPowerPrev1dId       OCTET STRING,
       pmSFPPowerPrev1dUnitType   INTEGER,
       pmSFPPowerPrev1dRxAverage  Counter64,
       pmSFPPowerPrev1dRxMin    Counter64,
       pmSFPPowerPrev1dRxMax    Counter64,
       pmSFPPowerPrev1dTxAverage  Counter64,
       pmSFPPowerPrev1dTxMin    Counter64,
       pmSFPPowerPrev1dTxMax    Counter64,
       pmSFPPowerPrev1dStartTime    DateAndTime,
       pmSFPPowerPrev1dStopTime   DateAndTime
    }

pmSFPPowerPrev1dIndex         OBJECT-TYPE
    SYNTAX          Integer32
    MAX-ACCESS      not-accessible
    STATUS          current
    DESCRIPTION
        "An index of units."
    ::= { pmSFPPowerPrev1dEntry 1 }

pmSFPPowerPrev1dId         OBJECT-TYPE
    SYNTAX          OCTET STRING
    MAX-ACCESS      read-only
    STATUS          current
    DESCRIPTION
        "SFP name."
    ::= { pmSFPPowerPrev1dEntry 2 }

pmSFPPowerPrev1dUnitType         OBJECT-TYPE
    SYNTAX          INTEGER
    {
       mcu(0)
    }
    MAX-ACCESS      read-only
    STATUS          current
    DESCRIPTION
        "Unit type."
    ::= { pmSFPPowerPrev1dEntry 3 }

pmSFPPowerPrev1dRxAverage         OBJECT-TYPE
    SYNTAX          Counter64
    MAX-ACCESS      read-only
    STATUS          current
    DESCRIPTION
        "Previous 1day counter of average sfp rx power."
    ::= { pmSFPPowerPrev1dEntry 4 }

pmSFPPowerPrev1dRxMin         OBJECT-TYPE
    SYNTAX          Counter64
    MAX-ACCESS      read-only
    STATUS          current
    DESCRIPTION
        "Previous 1day counter of minimum sfp rx power."
    ::= { pmSFPPowerPrev1dEntry 5 }

pmSFPPowerPrev1dRxMax         OBJECT-TYPE
    SYNTAX          Counter64
    MAX-ACCESS      read-only
    STATUS          current
    DESCRIPTION
        "Previous 1day counter of maximum sfp rx power."
    ::= { pmSFPPowerPrev1dEntry 6 }

pmSFPPowerPrev1dTxAverage         OBJECT-TYPE
    SYNTAX          Counter64
    MAX-ACCESS      read-only
    STATUS          current
    DESCRIPTION
        "Previous 1day counter of average sfp tx power."
    ::= { pmSFPPowerPrev1dEntry 7 }

pmSFPPowerPrev1dTxMin         OBJECT-TYPE
    SYNTAX          Counter64
    MAX-ACCESS      read-only
    STATUS          current
    DESCRIPTION
        "Previous 1day counter of minimum sfp tx power."
    ::= { pmSFPPowerPrev1dEntry 8 }

pmSFPPowerPrev1dTxMax         OBJECT-TYPE
    SYNTAX          Counter64
    MAX-ACCESS      read-only
    STATUS          current
    DESCRIPTION
        "Previous 1day counter of maximum sfp tx power."
    ::= { pmSFPPowerPrev1dEntry 9 }

pmSFPPowerPrev1dStartTime         OBJECT-TYPE
    SYNTAX          DateAndTime
    MAX-ACCESS      read-only
    STATUS          current
    DESCRIPTION
        "Previous 1day start time."
    ::= { pmSFPPowerPrev1dEntry 100 }

pmSFPPowerPrev1dStopTime         OBJECT-TYPE
    SYNTAX          DateAndTime
    MAX-ACCESS      read-only
    STATUS          current
    DESCRIPTION
        "Previous 1day stop time."
    ::= { pmSFPPowerPrev1dEntry 101 }

pmTcaSFPRxPowerMin15mTable     OBJECT-TYPE
    SYNTAX          SEQUENCE OF PMTcaSFPRxPowerMin15mEntry
    MAX-ACCESS      not-accessible
    STATUS          current
    DESCRIPTION
        "A table that contains temperature information of all units."
    ::= { pmSFPPower 7 }

pmTcaSFPRxPowerMin15mEntry     OBJECT-TYPE
    SYNTAX          PMTcaSFPRxPowerMin15mEntry
    MAX-ACCESS      not-accessible
    STATUS          current
    DESCRIPTION
        "A list of temperature information of all units."
    INDEX     { pmTcaSFPRxPowerMin15mIndex  }
    ::= { pmTcaSFPRxPowerMin15mTable 1 }

PMTcaSFPRxPowerMin15mEntry    ::=
    SEQUENCE
    {
       pmTcaSFPRxPowerMin15mIndex      Integer32,
       pmTcaSFPRxPowerMin15mId       OCTET STRING,
       pmTcaSFPRxPowerMin15mUnitType   INTEGER,
       pmTcaSFPRxPowerMin15mCnt     Counter64,
       pmTcaSFPRxPowerMin15mThreshold   Counter64,
       pmTcaSFPRxPowerMin15mOccurTime   DateAndTime
    }

pmTcaSFPRxPowerMin15mIndex         OBJECT-TYPE
    SYNTAX          Integer32
    MAX-ACCESS      not-accessible
    STATUS          current
    DESCRIPTION
        "An index of units."
    ::= { pmTcaSFPRxPowerMin15mEntry 1 }

pmTcaSFPRxPowerMin15mId         OBJECT-TYPE
    SYNTAX          OCTET STRING
    MAX-ACCESS      read-only
    STATUS          current
    DESCRIPTION
        "Unit name."
    ::= { pmTcaSFPRxPowerMin15mEntry 2 }

pmTcaSFPRxPowerMin15mUnitType         OBJECT-TYPE
    SYNTAX          INTEGER
    {
       mcu(0)
    }
    MAX-ACCESS      read-only
    STATUS          current
    DESCRIPTION
        "Unit type."
    ::= { pmTcaSFPRxPowerMin15mEntry 3 }

pmTcaSFPRxPowerMin15mCnt         OBJECT-TYPE
    SYNTAX          Counter64
    MAX-ACCESS      read-only
    STATUS          current
    DESCRIPTION
        "15min counter of unit temperature."
    ::= { pmTcaSFPRxPowerMin15mEntry 4 }

pmTcaSFPRxPowerMin15mThreshold         OBJECT-TYPE
    SYNTAX          Counter64
    MAX-ACCESS      read-only
    STATUS          current
    DESCRIPTION
        "15min threshold of unit temperature."
    ::= { pmTcaSFPRxPowerMin15mEntry 5 }

pmTcaSFPRxPowerMin15mOccurTime         OBJECT-TYPE
    SYNTAX          DateAndTime
    MAX-ACCESS      read-only
    STATUS          current
    DESCRIPTION
        "Time of the occurrence of the tca."
    ::= { pmTcaSFPRxPowerMin15mEntry 6 }

pmTcaSFPRxPowerMin1hTable     OBJECT-TYPE
    SYNTAX          SEQUENCE OF PMTcaSFPRxPowerMin1hEntry
    MAX-ACCESS      not-accessible
    STATUS          current
    DESCRIPTION
        "A table that contains temperature information of all units."
    ::= { pmSFPPower 8 }

pmTcaSFPRxPowerMin1hEntry     OBJECT-TYPE
    SYNTAX          PMTcaSFPRxPowerMin1hEntry
    MAX-ACCESS      not-accessible
    STATUS          current
    DESCRIPTION
        "A list of temperature information of all units."
    INDEX     { pmTcaSFPRxPowerMin1hIndex  }
    ::= { pmTcaSFPRxPowerMin1hTable 1 }

PMTcaSFPRxPowerMin1hEntry    ::=
    SEQUENCE
    {
       pmTcaSFPRxPowerMin1hIndex      Integer32,
       pmTcaSFPRxPowerMin1hId       OCTET STRING,
       pmTcaSFPRxPowerMin1hUnitType   INTEGER,
       pmTcaSFPRxPowerMin1hCnt     Counter64,
       pmTcaSFPRxPowerMin1hThreshold   Counter64,
       pmTcaSFPRxPowerMin1hOccurTime   DateAndTime
    }

pmTcaSFPRxPowerMin1hIndex         OBJECT-TYPE
    SYNTAX          Integer32
    MAX-ACCESS      not-accessible
    STATUS          current
    DESCRIPTION
        "An index of units."
    ::= { pmTcaSFPRxPowerMin1hEntry 1 }

pmTcaSFPRxPowerMin1hId         OBJECT-TYPE
    SYNTAX          OCTET STRING
    MAX-ACCESS      read-only
    STATUS          current
    DESCRIPTION
        "Unit name."
    ::= { pmTcaSFPRxPowerMin1hEntry 2 }

pmTcaSFPRxPowerMin1hUnitType         OBJECT-TYPE
    SYNTAX          INTEGER
    {
       mcu(0)
    }
    MAX-ACCESS      read-only
    STATUS          current
    DESCRIPTION
        "Unit type."
    ::= { pmTcaSFPRxPowerMin1hEntry 3 }

pmTcaSFPRxPowerMin1hCnt         OBJECT-TYPE
    SYNTAX          Counter64
    MAX-ACCESS      read-only
    STATUS          current
    DESCRIPTION
        "1hour counter of unit temperature."
    ::= { pmTcaSFPRxPowerMin1hEntry 4 }

pmTcaSFPRxPowerMin1hThreshold         OBJECT-TYPE
    SYNTAX          Counter64
    MAX-ACCESS      read-only
    STATUS          current
    DESCRIPTION
        "1hour threshold of unit temperature."
    ::= { pmTcaSFPRxPowerMin1hEntry 5 }

pmTcaSFPRxPowerMin1hOccurTime         OBJECT-TYPE
    SYNTAX          DateAndTime
    MAX-ACCESS      read-only
    STATUS          current
    DESCRIPTION
        "Time of the occurrence of the tca."
    ::= { pmTcaSFPRxPowerMin1hEntry 6 }

pmTcaSFPRxPowerMin1dTable     OBJECT-TYPE
    SYNTAX          SEQUENCE OF PMTcaSFPRxPowerMin1dEntry
    MAX-ACCESS      not-accessible
    STATUS          current
    DESCRIPTION
        "A table that contains temperature information of all units."
    ::= { pmSFPPower 9 }

pmTcaSFPRxPowerMin1dEntry     OBJECT-TYPE
    SYNTAX          PMTcaSFPRxPowerMin1dEntry
    MAX-ACCESS      not-accessible
    STATUS          current
    DESCRIPTION
        "A list of temperature information of all units."
    INDEX     { pmTcaSFPRxPowerMin1dIndex  }
    ::= { pmTcaSFPRxPowerMin1dTable 1 }

PMTcaSFPRxPowerMin1dEntry    ::=
    SEQUENCE
    {
       pmTcaSFPRxPowerMin1dIndex      Integer32,
       pmTcaSFPRxPowerMin1dId        OCTET STRING,
       pmTcaSFPRxPowerMin1dUnitType   INTEGER,
       pmTcaSFPRxPowerMin1dCnt     Counter64,
       pmTcaSFPRxPowerMin1dThreshold   Counter64,
       pmTcaSFPRxPowerMin1dOccurTime   DateAndTime
    }

pmTcaSFPRxPowerMin1dIndex         OBJECT-TYPE
    SYNTAX          Integer32
    MAX-ACCESS      not-accessible
    STATUS          current
    DESCRIPTION
        "An index of units."
    ::= { pmTcaSFPRxPowerMin1dEntry 1 }

pmTcaSFPRxPowerMin1dId         OBJECT-TYPE
    SYNTAX          OCTET STRING
    MAX-ACCESS      read-only
    STATUS          current
    DESCRIPTION
        "Unit name."
    ::= { pmTcaSFPRxPowerMin1dEntry 2 }

pmTcaSFPRxPowerMin1dUnitType         OBJECT-TYPE
    SYNTAX          INTEGER
    {
       mcu(0)
    }
    MAX-ACCESS      read-only
    STATUS          current
    DESCRIPTION
        "Unit type."
    ::= { pmTcaSFPRxPowerMin1dEntry 3 }

pmTcaSFPRxPowerMin1dCnt         OBJECT-TYPE
    SYNTAX          Counter64
    MAX-ACCESS      read-only
    STATUS          current
    DESCRIPTION
        "1day counter of unit temperature."
    ::= { pmTcaSFPRxPowerMin1dEntry 4 }

pmTcaSFPRxPowerMin1dThreshold         OBJECT-TYPE
    SYNTAX          Counter64
    MAX-ACCESS      read-only
    STATUS          current
    DESCRIPTION
        "1day threshold of unit temperature."
    ::= { pmTcaSFPRxPowerMin1dEntry 5 }

pmTcaSFPRxPowerMin1dOccurTime         OBJECT-TYPE
    SYNTAX          DateAndTime
    MAX-ACCESS      read-only
    STATUS          current
    DESCRIPTION
        "Time of the occurrence of the tca."
    ::= { pmTcaSFPRxPowerMin1dEntry 6 }

pmTcaSFPRxPowerMax15mTable     OBJECT-TYPE
    SYNTAX          SEQUENCE OF PMTcaSFPRxPowerMax15mEntry
    MAX-ACCESS      not-accessible
    STATUS          current
    DESCRIPTION
        "A table that contains temperature information of all units."
    ::= { pmSFPPower 10 }

pmTcaSFPRxPowerMax15mEntry     OBJECT-TYPE
    SYNTAX          PMTcaSFPRxPowerMax15mEntry
    MAX-ACCESS      not-accessible
    STATUS          current
    DESCRIPTION
        "A list of temperature information of all units."
    INDEX     { pmTcaSFPRxPowerMax15mIndex  }
    ::= { pmTcaSFPRxPowerMax15mTable 1 }

PMTcaSFPRxPowerMax15mEntry    ::=
    SEQUENCE
    {
       pmTcaSFPRxPowerMax15mIndex      Integer32,
       pmTcaSFPRxPowerMax15mId     OCTET STRING,
       pmTcaSFPRxPowerMax15mUnitType   INTEGER,
       pmTcaSFPRxPowerMax15mCnt     Counter64,
       pmTcaSFPRxPowerMax15mThreshold   Counter64,
       pmTcaSFPRxPowerMax15mOccurTime   DateAndTime
    }

pmTcaSFPRxPowerMax15mIndex         OBJECT-TYPE
    SYNTAX          Integer32
    MAX-ACCESS      not-accessible
    STATUS          current
    DESCRIPTION
        "An index of units."
    ::= { pmTcaSFPRxPowerMax15mEntry 1 }

pmTcaSFPRxPowerMax15mId         OBJECT-TYPE
    SYNTAX          OCTET STRING
    MAX-ACCESS      read-only
    STATUS          current
    DESCRIPTION
        "Unit name."
    ::= { pmTcaSFPRxPowerMax15mEntry 2 }

pmTcaSFPRxPowerMax15mUnitType         OBJECT-TYPE
    SYNTAX          INTEGER
    {
       mcu(0)
    }
    MAX-ACCESS      read-only
    STATUS          current
    DESCRIPTION
        "Unit type."
    ::= { pmTcaSFPRxPowerMax15mEntry 3 }

pmTcaSFPRxPowerMax15mCnt         OBJECT-TYPE
    SYNTAX          Counter64
    MAX-ACCESS      read-only
    STATUS          current
    DESCRIPTION
        "15min counter of unit temperature."
    ::= { pmTcaSFPRxPowerMax15mEntry 4 }

pmTcaSFPRxPowerMax15mThreshold         OBJECT-TYPE
    SYNTAX          Counter64
    MAX-ACCESS      read-only
    STATUS          current
    DESCRIPTION
        "15min threshold of unit temperature."
    ::= { pmTcaSFPRxPowerMax15mEntry 5 }

pmTcaSFPRxPowerMax15mOccurTime         OBJECT-TYPE
    SYNTAX          DateAndTime
    MAX-ACCESS      read-only
    STATUS          current
    DESCRIPTION
        "Time of the occurrence of the tca."
    ::= { pmTcaSFPRxPowerMax15mEntry 6 }

pmTcaSFPRxPowerMax1hTable     OBJECT-TYPE
    SYNTAX          SEQUENCE OF PMTcaSFPRxPowerMax1hEntry
    MAX-ACCESS      not-accessible
    STATUS          current
    DESCRIPTION
        "A table that contains temperature information of all units."
    ::= { pmSFPPower 11 }

pmTcaSFPRxPowerMax1hEntry     OBJECT-TYPE
    SYNTAX          PMTcaSFPRxPowerMax1hEntry
    MAX-ACCESS      not-accessible
    STATUS          current
    DESCRIPTION
        "A list of temperature information of all units."
    INDEX     { pmTcaSFPRxPowerMax1hIndex  }
    ::= { pmTcaSFPRxPowerMax1hTable 1 }

PMTcaSFPRxPowerMax1hEntry    ::=
    SEQUENCE
    {
       pmTcaSFPRxPowerMax1hIndex      Integer32,
       pmTcaSFPRxPowerMax1hId     OCTET STRING,
       pmTcaSFPRxPowerMax1hUnitType   INTEGER,
       pmTcaSFPRxPowerMax1hCnt     Counter64,
       pmTcaSFPRxPowerMax1hThreshold   Counter64,
       pmTcaSFPRxPowerMax1hOccurTime   DateAndTime
    }

pmTcaSFPRxPowerMax1hIndex         OBJECT-TYPE
    SYNTAX          Integer32
    MAX-ACCESS      not-accessible
    STATUS          current
    DESCRIPTION
        "An index of units."
    ::= { pmTcaSFPRxPowerMax1hEntry 1 }

pmTcaSFPRxPowerMax1hId         OBJECT-TYPE
    SYNTAX          OCTET STRING
    MAX-ACCESS      read-only
    STATUS          current
    DESCRIPTION
        "Unit name."
    ::= { pmTcaSFPRxPowerMax1hEntry 2 }

pmTcaSFPRxPowerMax1hUnitType         OBJECT-TYPE
    SYNTAX          INTEGER
    {
       mcu(0)
    }
    MAX-ACCESS      read-only
    STATUS          current
    DESCRIPTION
        "Unit type."
    ::= { pmTcaSFPRxPowerMax1hEntry 3 }

pmTcaSFPRxPowerMax1hCnt         OBJECT-TYPE
    SYNTAX          Counter64
    MAX-ACCESS      read-only
    STATUS          current
    DESCRIPTION
        "1hour counter of unit temperature."
    ::= { pmTcaSFPRxPowerMax1hEntry 4 }

pmTcaSFPRxPowerMax1hThreshold         OBJECT-TYPE
    SYNTAX          Counter64
    MAX-ACCESS      read-only
    STATUS          current
    DESCRIPTION
        "1hour threshold of unit temperature."
    ::= { pmTcaSFPRxPowerMax1hEntry 5 }

pmTcaSFPRxPowerMax1hOccurTime         OBJECT-TYPE
    SYNTAX          DateAndTime
    MAX-ACCESS      read-only
    STATUS          current
    DESCRIPTION
        "Time of the occurrence of the tca."
    ::= { pmTcaSFPRxPowerMax1hEntry 6 }

pmTcaSFPRxPowerMax1dTable     OBJECT-TYPE
    SYNTAX          SEQUENCE OF PMTcaSFPRxPowerMax1dEntry
    MAX-ACCESS      not-accessible
    STATUS          current
    DESCRIPTION
        "A table that contains temperature information of all units."
    ::= { pmSFPPower 12 }

pmTcaSFPRxPowerMax1dEntry     OBJECT-TYPE
    SYNTAX          PMTcaSFPRxPowerMax1dEntry
    MAX-ACCESS      not-accessible
    STATUS          current
    DESCRIPTION
        "A list of temperature information of all units."
    INDEX     { pmTcaSFPRxPowerMax1dIndex  }
    ::= { pmTcaSFPRxPowerMax1dTable 1 }

PMTcaSFPRxPowerMax1dEntry    ::=
    SEQUENCE
    {
       pmTcaSFPRxPowerMax1dIndex      Integer32,
       pmTcaSFPRxPowerMax1dId       OCTET STRING,
       pmTcaSFPRxPowerMax1dUnitType   INTEGER,
       pmTcaSFPRxPowerMax1dCnt     Counter64,
       pmTcaSFPRxPowerMax1dThreshold   Counter64,
       pmTcaSFPRxPowerMax1dOccurTime   DateAndTime
    }

pmTcaSFPRxPowerMax1dIndex         OBJECT-TYPE
    SYNTAX          Integer32
    MAX-ACCESS      not-accessible
    STATUS          current
    DESCRIPTION
        "An index of units."
    ::= { pmTcaSFPRxPowerMax1dEntry 1 }

pmTcaSFPRxPowerMax1dId         OBJECT-TYPE
    SYNTAX          OCTET STRING
    MAX-ACCESS      read-only
    STATUS          current
    DESCRIPTION
        "Unit name."
    ::= { pmTcaSFPRxPowerMax1dEntry 2 }

pmTcaSFPRxPowerMax1dUnitType         OBJECT-TYPE
    SYNTAX          INTEGER
    {
       mcu(0)
    }
    MAX-ACCESS      read-only
    STATUS          current
    DESCRIPTION
        "Unit type."
    ::= { pmTcaSFPRxPowerMax1dEntry 3 }

pmTcaSFPRxPowerMax1dCnt         OBJECT-TYPE
    SYNTAX          Counter64
    MAX-ACCESS      read-only
    STATUS          current
    DESCRIPTION
        "1day counter of unit temperature."
    ::= { pmTcaSFPRxPowerMax1dEntry 4 }

pmTcaSFPRxPowerMax1dThreshold         OBJECT-TYPE
    SYNTAX          Counter64
    MAX-ACCESS      read-only
    STATUS          current
    DESCRIPTION
        "1day threshold of unit temperature."
    ::= { pmTcaSFPRxPowerMax1dEntry 5 }

pmTcaSFPRxPowerMax1dOccurTime         OBJECT-TYPE
    SYNTAX          DateAndTime
    MAX-ACCESS      read-only
    STATUS          current
    DESCRIPTION
        "Time of the occurrence of the tca."
    ::= { pmTcaSFPRxPowerMax1dEntry 6 }

pmTcaSFPTxPowerMin15mTable     OBJECT-TYPE
    SYNTAX          SEQUENCE OF PMTcaSFPTxPowerMin15mEntry
    MAX-ACCESS      not-accessible
    STATUS          current
    DESCRIPTION
        "A table that contains temperature information of all units."
    ::= { pmSFPPower 13 }

pmTcaSFPTxPowerMin15mEntry     OBJECT-TYPE
    SYNTAX          PMTcaSFPTxPowerMin15mEntry
    MAX-ACCESS      not-accessible
    STATUS          current
    DESCRIPTION
        "A list of temperature information of all units."
    INDEX     { pmTcaSFPTxPowerMin15mIndex  }
    ::= { pmTcaSFPTxPowerMin15mTable 1 }

PMTcaSFPTxPowerMin15mEntry    ::=
    SEQUENCE
    {
       pmTcaSFPTxPowerMin15mIndex      Integer32,
       pmTcaSFPTxPowerMin15mId       OCTET STRING,
       pmTcaSFPTxPowerMin15mUnitType   INTEGER,
       pmTcaSFPTxPowerMin15mCnt     Counter64,
       pmTcaSFPTxPowerMin15mThreshold   Counter64,
       pmTcaSFPTxPowerMin15mOccurTime   DateAndTime
    }

pmTcaSFPTxPowerMin15mIndex         OBJECT-TYPE
    SYNTAX          Integer32
    MAX-ACCESS      not-accessible
    STATUS          current
    DESCRIPTION
        "An index of units."
    ::= { pmTcaSFPTxPowerMin15mEntry 1 }

pmTcaSFPTxPowerMin15mId         OBJECT-TYPE
    SYNTAX          OCTET STRING
    MAX-ACCESS      read-only
    STATUS          current
    DESCRIPTION
        "Unit name."
    ::= { pmTcaSFPTxPowerMin15mEntry 2 }

pmTcaSFPTxPowerMin15mUnitType         OBJECT-TYPE
    SYNTAX          INTEGER
    {
       mcu(0)
    }
    MAX-ACCESS      read-only
    STATUS          current
    DESCRIPTION
        "Unit type."
    ::= { pmTcaSFPTxPowerMin15mEntry 3 }

pmTcaSFPTxPowerMin15mCnt         OBJECT-TYPE
    SYNTAX          Counter64
    MAX-ACCESS      read-only
    STATUS          current
    DESCRIPTION
        "15min counter of unit temperature."
    ::= { pmTcaSFPTxPowerMin15mEntry 4 }

pmTcaSFPTxPowerMin15mThreshold         OBJECT-TYPE
    SYNTAX          Counter64
    MAX-ACCESS      read-only
    STATUS          current
    DESCRIPTION
        "15min threshold of unit temperature."
    ::= { pmTcaSFPTxPowerMin15mEntry 5 }

pmTcaSFPTxPowerMin15mOccurTime         OBJECT-TYPE
    SYNTAX          DateAndTime
    MAX-ACCESS      read-only
    STATUS          current
    DESCRIPTION
        "Time of the occurrence of the tca."
    ::= { pmTcaSFPTxPowerMin15mEntry 6 }

pmTcaSFPTxPowerMin1hTable     OBJECT-TYPE
    SYNTAX          SEQUENCE OF PMTcaSFPTxPowerMin1hEntry
    MAX-ACCESS      not-accessible
    STATUS          current
    DESCRIPTION
        "A table that contains temperature information of all units."
    ::= { pmSFPPower 14 }

pmTcaSFPTxPowerMin1hEntry     OBJECT-TYPE
    SYNTAX          PMTcaSFPTxPowerMin1hEntry
    MAX-ACCESS      not-accessible
    STATUS          current
    DESCRIPTION
        "A list of temperature information of all units."
    INDEX     { pmTcaSFPTxPowerMin1hIndex  }
    ::= { pmTcaSFPTxPowerMin1hTable 1 }

PMTcaSFPTxPowerMin1hEntry    ::=
    SEQUENCE
    {
       pmTcaSFPTxPowerMin1hIndex      Integer32,
       pmTcaSFPTxPowerMin1hId       OCTET STRING,
       pmTcaSFPTxPowerMin1hUnitType   INTEGER,
       pmTcaSFPTxPowerMin1hCnt     Counter64,
       pmTcaSFPTxPowerMin1hThreshold   Counter64,
       pmTcaSFPTxPowerMin1hOccurTime   DateAndTime
    }

pmTcaSFPTxPowerMin1hIndex         OBJECT-TYPE
    SYNTAX          Integer32
    MAX-ACCESS      not-accessible
    STATUS          current
    DESCRIPTION
        "An index of units."
    ::= { pmTcaSFPTxPowerMin1hEntry 1 }

pmTcaSFPTxPowerMin1hId         OBJECT-TYPE
    SYNTAX          OCTET STRING
    MAX-ACCESS      read-only
    STATUS          current
    DESCRIPTION
        "Unit name."
    ::= { pmTcaSFPTxPowerMin1hEntry 2 }

pmTcaSFPTxPowerMin1hUnitType         OBJECT-TYPE
    SYNTAX          INTEGER
    {
       mcu(0)
    }
    MAX-ACCESS      read-only
    STATUS          current
    DESCRIPTION
        "Unit type."
    ::= { pmTcaSFPTxPowerMin1hEntry 3 }

pmTcaSFPTxPowerMin1hCnt         OBJECT-TYPE
    SYNTAX          Counter64
    MAX-ACCESS      read-only
    STATUS          current
    DESCRIPTION
        "1hour counter of unit temperature."
    ::= { pmTcaSFPTxPowerMin1hEntry 4 }

pmTcaSFPTxPowerMin1hThreshold         OBJECT-TYPE
    SYNTAX          Counter64
    MAX-ACCESS      read-only
    STATUS          current
    DESCRIPTION
        "1hour threshold of unit temperature."
    ::= { pmTcaSFPTxPowerMin1hEntry 5 }

pmTcaSFPTxPowerMin1hOccurTime         OBJECT-TYPE
    SYNTAX          DateAndTime
    MAX-ACCESS      read-only
    STATUS          current
    DESCRIPTION
        "Time of the occurrence of the tca."
    ::= { pmTcaSFPTxPowerMin1hEntry 6 }

pmTcaSFPTxPowerMin1dTable     OBJECT-TYPE
    SYNTAX          SEQUENCE OF PMTcaSFPTxPowerMin1dEntry
    MAX-ACCESS      not-accessible
    STATUS          current
    DESCRIPTION
        "A table that contains temperature information of all units."
    ::= { pmSFPPower 15 }

pmTcaSFPTxPowerMin1dEntry     OBJECT-TYPE
    SYNTAX          PMTcaSFPTxPowerMin1dEntry
    MAX-ACCESS      not-accessible
    STATUS          current
    DESCRIPTION
        "A list of temperature information of all units."
    INDEX     { pmTcaSFPTxPowerMin1dIndex  }
    ::= { pmTcaSFPTxPowerMin1dTable 1 }

PMTcaSFPTxPowerMin1dEntry    ::=
    SEQUENCE
    {
       pmTcaSFPTxPowerMin1dIndex      Integer32,
       pmTcaSFPTxPowerMin1dId        OCTET STRING,
       pmTcaSFPTxPowerMin1dUnitType   INTEGER,
       pmTcaSFPTxPowerMin1dCnt     Counter64,
       pmTcaSFPTxPowerMin1dThreshold   Counter64,
       pmTcaSFPTxPowerMin1dOccurTime   DateAndTime
    }

pmTcaSFPTxPowerMin1dIndex         OBJECT-TYPE
    SYNTAX          Integer32
    MAX-ACCESS      not-accessible
    STATUS          current
    DESCRIPTION
        "An index of units."
    ::= { pmTcaSFPTxPowerMin1dEntry 1 }

pmTcaSFPTxPowerMin1dId         OBJECT-TYPE
    SYNTAX          OCTET STRING
    MAX-ACCESS      read-only
    STATUS          current
    DESCRIPTION
        "Unit name."
    ::= { pmTcaSFPTxPowerMin1dEntry 2 }

pmTcaSFPTxPowerMin1dUnitType         OBJECT-TYPE
    SYNTAX          INTEGER
    {
       mcu(0)
    }
    MAX-ACCESS      read-only
    STATUS          current
    DESCRIPTION
        "Unit type."
    ::= { pmTcaSFPTxPowerMin1dEntry 3 }

pmTcaSFPTxPowerMin1dCnt         OBJECT-TYPE
    SYNTAX          Counter64
    MAX-ACCESS      read-only
    STATUS          current
    DESCRIPTION
        "1day counter of unit temperature."
    ::= { pmTcaSFPTxPowerMin1dEntry 4 }

pmTcaSFPTxPowerMin1dThreshold         OBJECT-TYPE
    SYNTAX          Counter64
    MAX-ACCESS      read-only
    STATUS          current
    DESCRIPTION
        "1day threshold of unit temperature."
    ::= { pmTcaSFPTxPowerMin1dEntry 5 }

pmTcaSFPTxPowerMin1dOccurTime         OBJECT-TYPE
    SYNTAX          DateAndTime
    MAX-ACCESS      read-only
    STATUS          current
    DESCRIPTION
        "Time of the occurrence of the tca."
    ::= { pmTcaSFPTxPowerMin1dEntry 6 }

pmTcaSFPTxPowerMax15mTable     OBJECT-TYPE
    SYNTAX          SEQUENCE OF PMTcaSFPTxPowerMax15mEntry
    MAX-ACCESS      not-accessible
    STATUS          current
    DESCRIPTION
        "A table that contains temperature information of all units."
    ::= { pmSFPPower 16 }

pmTcaSFPTxPowerMax15mEntry     OBJECT-TYPE
    SYNTAX          PMTcaSFPTxPowerMax15mEntry
    MAX-ACCESS      not-accessible
    STATUS          current
    DESCRIPTION
        "A list of temperature information of all units."
    INDEX     { pmTcaSFPTxPowerMax15mIndex  }
    ::= { pmTcaSFPTxPowerMax15mTable 1 }

PMTcaSFPTxPowerMax15mEntry    ::=
    SEQUENCE
    {
       pmTcaSFPTxPowerMax15mIndex      Integer32,
       pmTcaSFPTxPowerMax15mId       OCTET STRING,
       pmTcaSFPTxPowerMax15mUnitType  INTEGER,
       pmTcaSFPTxPowerMax15mCnt     Counter64,
       pmTcaSFPTxPowerMax15mThreshold   Counter64,
       pmTcaSFPTxPowerMax15mOccurTime   DateAndTime
    }

pmTcaSFPTxPowerMax15mIndex         OBJECT-TYPE
    SYNTAX          Integer32
    MAX-ACCESS      not-accessible
    STATUS          current
    DESCRIPTION
        "An index of units."
    ::= { pmTcaSFPTxPowerMax15mEntry 1 }

pmTcaSFPTxPowerMax15mId         OBJECT-TYPE
    SYNTAX          OCTET STRING
    MAX-ACCESS      read-only
    STATUS          current
    DESCRIPTION
        "Unit name."
    ::= { pmTcaSFPTxPowerMax15mEntry 2 }

pmTcaSFPTxPowerMax15mUnitType         OBJECT-TYPE
    SYNTAX          INTEGER
    {
       mcu(0)
    }
    MAX-ACCESS      read-only
    STATUS          current
    DESCRIPTION
        "Unit type."
    ::= { pmTcaSFPTxPowerMax15mEntry 3 }

pmTcaSFPTxPowerMax15mCnt         OBJECT-TYPE
    SYNTAX          Counter64
    MAX-ACCESS      read-only
    STATUS          current
    DESCRIPTION
        "15min counter of unit temperature."
    ::= { pmTcaSFPTxPowerMax15mEntry 4 }

pmTcaSFPTxPowerMax15mThreshold         OBJECT-TYPE
    SYNTAX          Counter64
    MAX-ACCESS      read-only
    STATUS          current
    DESCRIPTION
        "15min threshold of unit temperature."
    ::= { pmTcaSFPTxPowerMax15mEntry 5 }

pmTcaSFPTxPowerMax15mOccurTime         OBJECT-TYPE
    SYNTAX          DateAndTime
    MAX-ACCESS      read-only
    STATUS          current
    DESCRIPTION
        "Time of the occurrence of the tca."
    ::= { pmTcaSFPTxPowerMax15mEntry 6 }

pmTcaSFPTxPowerMax1hTable     OBJECT-TYPE
    SYNTAX          SEQUENCE OF PMTcaSFPTxPowerMax1hEntry
    MAX-ACCESS      not-accessible
    STATUS          current
    DESCRIPTION
        "A table that contains temperature information of all units."
    ::= { pmSFPPower 17 }

pmTcaSFPTxPowerMax1hEntry     OBJECT-TYPE
    SYNTAX          PMTcaSFPTxPowerMax1hEntry
    MAX-ACCESS      not-accessible
    STATUS          current
    DESCRIPTION
        "A list of temperature information of all units."
    INDEX     { pmTcaSFPTxPowerMax1hIndex  }
    ::= { pmTcaSFPTxPowerMax1hTable 1 }

PMTcaSFPTxPowerMax1hEntry    ::=
    SEQUENCE
    {
       pmTcaSFPTxPowerMax1hIndex      Integer32,
       pmTcaSFPTxPowerMax1hId       OCTET STRING,
       pmTcaSFPTxPowerMax1hUnitType  INTEGER,
       pmTcaSFPTxPowerMax1hCnt     Counter64,
       pmTcaSFPTxPowerMax1hThreshold   Counter64,
       pmTcaSFPTxPowerMax1hOccurTime   DateAndTime
    }

pmTcaSFPTxPowerMax1hIndex         OBJECT-TYPE
    SYNTAX          Integer32
    MAX-ACCESS      not-accessible
    STATUS          current
    DESCRIPTION
        "An index of units."
    ::= { pmTcaSFPTxPowerMax1hEntry 1 }

pmTcaSFPTxPowerMax1hId         OBJECT-TYPE
    SYNTAX          OCTET STRING
    MAX-ACCESS      read-only
    STATUS          current
    DESCRIPTION
        "Unit name."
    ::= { pmTcaSFPTxPowerMax1hEntry 2 }

pmTcaSFPTxPowerMax1hUnitType         OBJECT-TYPE
    SYNTAX          INTEGER
    {
       mcu(0)
    }
    MAX-ACCESS      read-only
    STATUS          current
    DESCRIPTION
        "Unit type."
    ::= { pmTcaSFPTxPowerMax1hEntry 3 }

pmTcaSFPTxPowerMax1hCnt         OBJECT-TYPE
    SYNTAX          Counter64
    MAX-ACCESS      read-only
    STATUS          current
    DESCRIPTION
        "1hour counter of unit temperature."
    ::= { pmTcaSFPTxPowerMax1hEntry 4 }

pmTcaSFPTxPowerMax1hThreshold         OBJECT-TYPE
    SYNTAX          Counter64
    MAX-ACCESS      read-only
    STATUS          current
    DESCRIPTION
        "1hour threshold of unit temperature."
    ::= { pmTcaSFPTxPowerMax1hEntry 5 }

pmTcaSFPTxPowerMax1hOccurTime         OBJECT-TYPE
    SYNTAX          DateAndTime
    MAX-ACCESS      read-only
    STATUS          current
    DESCRIPTION
        "Time of the occurrence of the tca."
    ::= { pmTcaSFPTxPowerMax1hEntry 6 }

pmTcaSFPTxPowerMax1dTable     OBJECT-TYPE
    SYNTAX          SEQUENCE OF PMTcaSFPTxPowerMax1dEntry
    MAX-ACCESS      not-accessible
    STATUS          current
    DESCRIPTION
        "A table that contains temperature information of all units."
    ::= { pmSFPPower 18 }

pmTcaSFPTxPowerMax1dEntry     OBJECT-TYPE
    SYNTAX          PMTcaSFPTxPowerMax1dEntry
    MAX-ACCESS      not-accessible
    STATUS          current
    DESCRIPTION
        "A list of temperature information of all units."
    INDEX     { pmTcaSFPTxPowerMax1dIndex  }
    ::= { pmTcaSFPTxPowerMax1dTable 1 }

PMTcaSFPTxPowerMax1dEntry    ::=
    SEQUENCE
    {
       pmTcaSFPTxPowerMax1dIndex      Integer32,
       pmTcaSFPTxPowerMax1dId        OCTET STRING,
       pmTcaSFPTxPowerMax1dUnitType   INTEGER,
       pmTcaSFPTxPowerMax1dCnt     Counter64,
       pmTcaSFPTxPowerMax1dThreshold   Counter64,
       pmTcaSFPTxPowerMax1dOccurTime   DateAndTime
    }

pmTcaSFPTxPowerMax1dIndex         OBJECT-TYPE
    SYNTAX          Integer32
    MAX-ACCESS      not-accessible
    STATUS          current
    DESCRIPTION
        "An index of units."
    ::= { pmTcaSFPTxPowerMax1dEntry 1 }

pmTcaSFPTxPowerMax1dId         OBJECT-TYPE
    SYNTAX          OCTET STRING
    MAX-ACCESS      read-only
    STATUS          current
    DESCRIPTION
        "Unit name."
    ::= { pmTcaSFPTxPowerMax1dEntry 2 }

pmTcaSFPTxPowerMax1dUnitType         OBJECT-TYPE
    SYNTAX          INTEGER
    {
       mcu(0)
    }
    MAX-ACCESS      read-only
    STATUS          current
    DESCRIPTION
        "Unit type."
    ::= { pmTcaSFPTxPowerMax1dEntry 3 }

pmTcaSFPTxPowerMax1dCnt         OBJECT-TYPE
    SYNTAX          Counter64
    MAX-ACCESS      read-only
    STATUS          current
    DESCRIPTION
        "1day counter of unit temperature."
    ::= { pmTcaSFPTxPowerMax1dEntry 4 }

pmTcaSFPTxPowerMax1dThreshold         OBJECT-TYPE
    SYNTAX          Counter64
    MAX-ACCESS      read-only
    STATUS          current
    DESCRIPTION
        "1day threshold of unit temperature."
    ::= { pmTcaSFPTxPowerMax1dEntry 5 }

pmTcaSFPTxPowerMax1dOccurTime         OBJECT-TYPE
    SYNTAX          DateAndTime
    MAX-ACCESS      read-only
    STATUS          current
    DESCRIPTION
        "Time of the occurrence of the tca."
    ::= { pmTcaSFPTxPowerMax1dEntry 6 }

pmIfStatistics        OBJECT IDENTIFIER ::= { pm 102 }


pmIfStatCurr15mTable     OBJECT-TYPE
    SYNTAX          SEQUENCE OF PMIfStatCurr15mEntry
    MAX-ACCESS      not-accessible
    STATUS          current
    DESCRIPTION
        "A table that contains interface statistics information of all units."
    ::= { pmIfStatistics 1 }

pmIfStatCurr15mEntry     OBJECT-TYPE
    SYNTAX          PMIfStatCurr15mEntry
    MAX-ACCESS      not-accessible
    STATUS          current
    DESCRIPTION
        "A list of interface statistics information of all units."
    INDEX     { pmIfStatCurr15mIndex  }
    ::= { pmIfStatCurr15mTable 1 }

PMIfStatCurr15mEntry    ::=
    SEQUENCE
    {
       pmIfStatCurr15mIndex       Integer32,
       pmIfStatCurr15mId      OCTET STRING,
       pmIfStatCurr15mUnitType   INTEGER,
       pmIfStatCurr15mDropped    Counter64,
       pmIfStatCurr15mInputPkts   Counter64,
       pmIfStatCurr15mInputbytes  Counter64,
       pmIfStatCurr15mInputBrdCst  Counter64,
       pmIfStatCurr15mInputMltCst  Counter64,
       pmIfStatCurr15mCrcErrors   Counter64,
       pmIfStatCurr15mCollision   Counter64,
       pmIfStatCurr15mUndersized  Counter64,
       pmIfStatCurr15mOversized   Counter64,
       pmIfStatCurr15mFragments   Counter64,
       pmIfStatCurr15mJabbers    Counter64,
       pmIfStatCurr15mPkt64     Counter64,
       pmIfStatCurr15mPkt65To127  Counter64,
       pmIfStatCurr15mPkt128To255  Counter64,
       pmIfStatCurr15mPkt256To511  Counter64,
       pmIfStatCurr15mPkt512To1023 Counter64,
       pmIfStatCurr15mPkt1024    Counter64,
       pmIfStatCurr15mOutputPkts  Counter64,
       pmIfStatCurr15mOutputBytes  Counter64,
       pmIfStatCurr15mStartTime    DateAndTime,
       pmIfStatCurr15mStopTime   DateAndTime
    }

pmIfStatCurr15mIndex         OBJECT-TYPE
    SYNTAX          Integer32
    MAX-ACCESS      not-accessible
    STATUS          current
    DESCRIPTION
        "An index of units."
    ::= { pmIfStatCurr15mEntry 1 }

pmIfStatCurr15mId         OBJECT-TYPE
    SYNTAX          OCTET STRING
    MAX-ACCESS      read-only
    STATUS          current
    DESCRIPTION
        "Interface name."
    ::= { pmIfStatCurr15mEntry 2 }

pmIfStatCurr15mUnitType         OBJECT-TYPE
    SYNTAX          INTEGER
    {
       mcu(0)
    }
    MAX-ACCESS      read-only
    STATUS          current
    DESCRIPTION
        "Unit type."
    ::= { pmIfStatCurr15mEntry 3 }

pmIfStatCurr15mDropped         OBJECT-TYPE
    SYNTAX          Counter64
    MAX-ACCESS      read-only
    STATUS          current
    DESCRIPTION
        "Current 15min counter of dropped events."
    ::= { pmIfStatCurr15mEntry 4 }

pmIfStatCurr15mInputPkts         OBJECT-TYPE
    SYNTAX          Counter64
    MAX-ACCESS      read-only
    STATUS          current
    DESCRIPTION
        "Current 15min counter of input packets."
    ::= { pmIfStatCurr15mEntry 5 }

pmIfStatCurr15mInputbytes         OBJECT-TYPE
    SYNTAX          Counter64
    MAX-ACCESS      read-only
    STATUS          current
    DESCRIPTION
        "Current 15min counter of input bytes."
    ::= { pmIfStatCurr15mEntry 6 }

pmIfStatCurr15mCrcErrors         OBJECT-TYPE
    SYNTAX          Counter64
    MAX-ACCESS      read-only
    STATUS          current
    DESCRIPTION
        "Current 15min counter of packets with CRC error."
    ::= { pmIfStatCurr15mEntry 7 }

pmIfStatCurr15mInputBrdCst         OBJECT-TYPE
    SYNTAX          Counter64
    MAX-ACCESS      read-only
    STATUS          current
    DESCRIPTION
        "Current 15min counter of broadcast packets."
    ::= { pmIfStatCurr15mEntry 8 }

pmIfStatCurr15mInputMltCst         OBJECT-TYPE
    SYNTAX          Counter64
    MAX-ACCESS      read-only
    STATUS          current
    DESCRIPTION
        "Current 15min counter of multicast packets."
    ::= { pmIfStatCurr15mEntry 9 }

pmIfStatCurr15mCollision         OBJECT-TYPE
    SYNTAX          Counter64
    MAX-ACCESS      read-only
    STATUS          current
    DESCRIPTION
        "Current 15min counter of collisions."
    ::= { pmIfStatCurr15mEntry 10 }

pmIfStatCurr15mUndersized         OBJECT-TYPE
    SYNTAX          Counter64
    MAX-ACCESS      read-only
    STATUS          current
    DESCRIPTION
        "Current 15min counter of undersized packets."
    ::= { pmIfStatCurr15mEntry 11 }

pmIfStatCurr15mOversized         OBJECT-TYPE
    SYNTAX          Counter64
    MAX-ACCESS      read-only
    STATUS          current
    DESCRIPTION
        "Current 15min counter of oversized packets."
    ::= { pmIfStatCurr15mEntry 12 }

pmIfStatCurr15mFragments         OBJECT-TYPE
    SYNTAX          Counter64
    MAX-ACCESS      read-only
    STATUS          current
    DESCRIPTION
        "Current 15min counter of frament packets."
    ::= { pmIfStatCurr15mEntry 13 }

pmIfStatCurr15mJabbers         OBJECT-TYPE
    SYNTAX          Counter64
    MAX-ACCESS      read-only
    STATUS          current
    DESCRIPTION
        "Current 15min counter of jabber packets."
    ::= { pmIfStatCurr15mEntry 14 }

pmIfStatCurr15mPkt64         OBJECT-TYPE
    SYNTAX          Counter64
    MAX-ACCESS      read-only
    STATUS          current
    DESCRIPTION
        "Current 15min counter of packets with size under 64."
    ::= { pmIfStatCurr15mEntry 15 }

pmIfStatCurr15mPkt65To127         OBJECT-TYPE
    SYNTAX          Counter64
    MAX-ACCESS      read-only
    STATUS          current
    DESCRIPTION
        "Current 15min counter of packets with size between 65 to 127."
    ::= { pmIfStatCurr15mEntry 16 }

pmIfStatCurr15mPkt128To255         OBJECT-TYPE
    SYNTAX          Counter64
    MAX-ACCESS      read-only
    STATUS          current
    DESCRIPTION
        "Current 15min counter of packets with size between 128 to 255."
    ::= { pmIfStatCurr15mEntry 17 }

pmIfStatCurr15mPkt256To511         OBJECT-TYPE
    SYNTAX          Counter64
    MAX-ACCESS      read-only
    STATUS          current
    DESCRIPTION
        "Current 15min counter of packets with size between 256 to 511."
    ::= { pmIfStatCurr15mEntry 18 }

pmIfStatCurr15mPkt512To1023         OBJECT-TYPE
    SYNTAX          Counter64
    MAX-ACCESS      read-only
    STATUS          current
    DESCRIPTION
        "Current 15min counter of packets with size between 512 to 1023."
    ::= { pmIfStatCurr15mEntry 19 }

pmIfStatCurr15mPkt1024         OBJECT-TYPE
    SYNTAX          Counter64
    MAX-ACCESS      read-only
    STATUS          current
    DESCRIPTION
        "Current 15min counter of packets with size over 1024."
    ::= { pmIfStatCurr15mEntry 20 }

pmIfStatCurr15mOutputPkts         OBJECT-TYPE
    SYNTAX          Counter64
    MAX-ACCESS      read-only
    STATUS          current
    DESCRIPTION
        "Current 15min counter of interface output packets."
    ::= { pmIfStatCurr15mEntry 21 }

pmIfStatCurr15mOutputBytes         OBJECT-TYPE
    SYNTAX          Counter64
    MAX-ACCESS      read-only
    STATUS          current
    DESCRIPTION
        "Current 15min counter of interface output bytes."
    ::= { pmIfStatCurr15mEntry 22 }

pmIfStatCurr15mStartTime         OBJECT-TYPE
    SYNTAX          DateAndTime
    MAX-ACCESS      read-only
    STATUS          current
    DESCRIPTION
        "Current 15min start time."
    ::= { pmIfStatCurr15mEntry 100 }

pmIfStatCurr15mStopTime         OBJECT-TYPE
    SYNTAX          DateAndTime
    MAX-ACCESS      read-only
    STATUS          current
    DESCRIPTION
        "Current 15min stop time."
    ::= { pmIfStatCurr15mEntry 101 }


pmIfStatPrev15mTable     OBJECT-TYPE
    SYNTAX          SEQUENCE OF PMIfStatPrev15mEntry
    MAX-ACCESS      not-accessible
    STATUS          current
    DESCRIPTION
        "A table that contains interface statistics information of all units."
    ::= { pmIfStatistics 2 }

pmIfStatPrev15mEntry     OBJECT-TYPE
    SYNTAX          PMIfStatPrev15mEntry
    MAX-ACCESS      not-accessible
    STATUS          current
    DESCRIPTION
        "A list of interface statistics information of all units."
    INDEX     { pmIfStatPrev15mIndex  }
    ::= { pmIfStatPrev15mTable 1 }

PMIfStatPrev15mEntry    ::=
    SEQUENCE
    {
       pmIfStatPrev15mIndex       Integer32,
       pmIfStatPrev15mId      OCTET STRING,
       pmIfStatPrev15mUnitType   INTEGER,
       pmIfStatPrev15mDropped    Counter64,
       pmIfStatPrev15mInputPkts   Counter64,
       pmIfStatPrev15mInputbytes  Counter64,
       pmIfStatPrev15mInputBrdCst  Counter64,
       pmIfStatPrev15mInputMltCst  Counter64,
       pmIfStatPrev15mCrcErrors   Counter64,
       pmIfStatPrev15mCollision   Counter64,
       pmIfStatPrev15mUndersized  Counter64,
       pmIfStatPrev15mOversized   Counter64,
       pmIfStatPrev15mFragments   Counter64,
       pmIfStatPrev15mJabbers    Counter64,
       pmIfStatPrev15mPkt64     Counter64,
       pmIfStatPrev15mPkt65To127  Counter64,
       pmIfStatPrev15mPkt128To255  Counter64,
       pmIfStatPrev15mPkt256To511  Counter64,
       pmIfStatPrev15mPkt512To1023 Counter64,
       pmIfStatPrev15mPkt1024    Counter64,
       pmIfStatPrev15mOutputPkts  Counter64,
       pmIfStatPrev15mOutputBytes  Counter64,
       pmIfStatPrev15mStartTime    DateAndTime,
       pmIfStatPrev15mStopTime   DateAndTime
    }

pmIfStatPrev15mIndex         OBJECT-TYPE
    SYNTAX          Integer32
    MAX-ACCESS      not-accessible
    STATUS          current
    DESCRIPTION
        "An index of units."
    ::= { pmIfStatPrev15mEntry 1 }

pmIfStatPrev15mId         OBJECT-TYPE
    SYNTAX          OCTET STRING
    MAX-ACCESS      read-only
    STATUS          current
    DESCRIPTION
        "Interface name."
    ::= { pmIfStatPrev15mEntry 2 }

pmIfStatPrev15mUnitType         OBJECT-TYPE
    SYNTAX          INTEGER
    {
       mcu(0)
    }
    MAX-ACCESS      read-only
    STATUS          current
    DESCRIPTION
        "Unit type."
    ::= { pmIfStatPrev15mEntry 3 }

pmIfStatPrev15mDropped         OBJECT-TYPE
    SYNTAX          Counter64
    MAX-ACCESS      read-only
    STATUS          current
    DESCRIPTION
        "Previous 15min counter of dropped events."
    ::= { pmIfStatPrev15mEntry 4 }

pmIfStatPrev15mInputPkts         OBJECT-TYPE
    SYNTAX          Counter64
    MAX-ACCESS      read-only
    STATUS          current
    DESCRIPTION
        "Previous 15min counter of input packets."
    ::= { pmIfStatPrev15mEntry 5 }

pmIfStatPrev15mInputbytes         OBJECT-TYPE
    SYNTAX          Counter64
    MAX-ACCESS      read-only
    STATUS          current
    DESCRIPTION
        "Previous 15min counter of input bytes."
    ::= { pmIfStatPrev15mEntry 6 }

pmIfStatPrev15mCrcErrors         OBJECT-TYPE
    SYNTAX          Counter64
    MAX-ACCESS      read-only
    STATUS          current
    DESCRIPTION
        "Previous 15min counter of packets with CRC error."
    ::= { pmIfStatPrev15mEntry 7 }

pmIfStatPrev15mInputBrdCst         OBJECT-TYPE
    SYNTAX          Counter64
    MAX-ACCESS      read-only
    STATUS          current
    DESCRIPTION
        "Previous 15min counter of broadcast packets."
    ::= { pmIfStatPrev15mEntry 8 }

pmIfStatPrev15mInputMltCst         OBJECT-TYPE
    SYNTAX          Counter64
    MAX-ACCESS      read-only
    STATUS          current
    DESCRIPTION
        "Previous 15min counter of multicast packets."
    ::= { pmIfStatPrev15mEntry 9 }

pmIfStatPrev15mCollision         OBJECT-TYPE
    SYNTAX          Counter64
    MAX-ACCESS      read-only
    STATUS          current
    DESCRIPTION
        "Previous 15min counter of collisions."
    ::= { pmIfStatPrev15mEntry 10 }

pmIfStatPrev15mUndersized         OBJECT-TYPE
    SYNTAX          Counter64
    MAX-ACCESS      read-only
    STATUS          current
    DESCRIPTION
        "Previous 15min counter of undersized packets."
    ::= { pmIfStatPrev15mEntry 11 }

pmIfStatPrev15mOversized         OBJECT-TYPE
    SYNTAX          Counter64
    MAX-ACCESS      read-only
    STATUS          current
    DESCRIPTION
        "Previous 15min counter of oversized packets."
    ::= { pmIfStatPrev15mEntry 12 }

pmIfStatPrev15mFragments         OBJECT-TYPE
    SYNTAX          Counter64
    MAX-ACCESS      read-only
    STATUS          current
    DESCRIPTION
        "Previous 15min counter of frament packets."
    ::= { pmIfStatPrev15mEntry 13 }

pmIfStatPrev15mJabbers         OBJECT-TYPE
    SYNTAX          Counter64
    MAX-ACCESS      read-only
    STATUS          current
    DESCRIPTION
        "Previous 15min counter of jabber packets."
    ::= { pmIfStatPrev15mEntry 14 }

pmIfStatPrev15mPkt64         OBJECT-TYPE
    SYNTAX          Counter64
    MAX-ACCESS      read-only
    STATUS          current
    DESCRIPTION
        "Previous 15min counter of packets with size under 64."
    ::= { pmIfStatPrev15mEntry 15 }

pmIfStatPrev15mPkt65To127         OBJECT-TYPE
    SYNTAX          Counter64
    MAX-ACCESS      read-only
    STATUS          current
    DESCRIPTION
        "Previous 15min counter of packets with size between 65 to 127."
    ::= { pmIfStatPrev15mEntry 16 }

pmIfStatPrev15mPkt128To255         OBJECT-TYPE
    SYNTAX          Counter64
    MAX-ACCESS      read-only
    STATUS          current
    DESCRIPTION
        "Previous 15min counter of packets with size between 128 to 255."
    ::= { pmIfStatPrev15mEntry 17 }

pmIfStatPrev15mPkt256To511         OBJECT-TYPE
    SYNTAX          Counter64
    MAX-ACCESS      read-only
    STATUS          current
    DESCRIPTION
        "Previous 15min counter of packets with size between 256 to 511."
    ::= { pmIfStatPrev15mEntry 18 }

pmIfStatPrev15mPkt512To1023         OBJECT-TYPE
    SYNTAX          Counter64
    MAX-ACCESS      read-only
    STATUS          current
    DESCRIPTION
        "Previous 15min counter of packets with size between 512 to 1023."
    ::= { pmIfStatPrev15mEntry 19 }

pmIfStatPrev15mPkt1024         OBJECT-TYPE
    SYNTAX          Counter64
    MAX-ACCESS      read-only
    STATUS          current
    DESCRIPTION
        "Previous 15min counter of packets with size over 1024."
    ::= { pmIfStatPrev15mEntry 20 }

pmIfStatPrev15mOutputPkts         OBJECT-TYPE
    SYNTAX          Counter64
    MAX-ACCESS      read-only
    STATUS          current
    DESCRIPTION
        "Previous 15min counter of interface output packets."
    ::= { pmIfStatPrev15mEntry 21 }

pmIfStatPrev15mOutputBytes         OBJECT-TYPE
    SYNTAX          Counter64
    MAX-ACCESS      read-only
    STATUS          current
    DESCRIPTION
        "Previous 15min counter of interface output bytes."
    ::= { pmIfStatPrev15mEntry 22 }

pmIfStatPrev15mStartTime         OBJECT-TYPE
    SYNTAX          DateAndTime
    MAX-ACCESS      read-only
    STATUS          current
    DESCRIPTION
        "Previous 15min start time."
    ::= { pmIfStatPrev15mEntry 100 }

pmIfStatPrev15mStopTime         OBJECT-TYPE
    SYNTAX          DateAndTime
    MAX-ACCESS      read-only
    STATUS          current
    DESCRIPTION
        "Previous 15min stop time."
    ::= { pmIfStatPrev15mEntry 101 }

pmIfStatCurr1hTable     OBJECT-TYPE
    SYNTAX          SEQUENCE OF PMIfStatCurr1hEntry
    MAX-ACCESS      not-accessible
    STATUS          current
    DESCRIPTION
        "A table that contains interface statistics information of all units."
    ::= { pmIfStatistics 3 }

pmIfStatCurr1hEntry     OBJECT-TYPE
    SYNTAX          PMIfStatCurr1hEntry
    MAX-ACCESS      not-accessible
    STATUS          current
    DESCRIPTION
        "A list of interface statistics information of all units."
    INDEX     { pmIfStatCurr1hIndex  }
    ::= { pmIfStatCurr1hTable 1 }

PMIfStatCurr1hEntry    ::=
    SEQUENCE
    {
       pmIfStatCurr1hIndex       Integer32,
       pmIfStatCurr1hId      OCTET STRING,
       pmIfStatCurr1hUnitType   INTEGER,
       pmIfStatCurr1hDropped    Counter64,
       pmIfStatCurr1hInputPkts   Counter64,
       pmIfStatCurr1hInputbytes  Counter64,
       pmIfStatCurr1hInputBrdCst  Counter64,
       pmIfStatCurr1hInputMltCst  Counter64,
       pmIfStatCurr1hCrcErrors   Counter64,
       pmIfStatCurr1hCollision   Counter64,
       pmIfStatCurr1hUndersized  Counter64,
       pmIfStatCurr1hOversized   Counter64,
       pmIfStatCurr1hFragments   Counter64,
       pmIfStatCurr1hJabbers    Counter64,
       pmIfStatCurr1hPkt64     Counter64,
       pmIfStatCurr1hPkt65To127  Counter64,
       pmIfStatCurr1hPkt128To255  Counter64,
       pmIfStatCurr1hPkt256To511  Counter64,
       pmIfStatCurr1hPkt512To1023 Counter64,
       pmIfStatCurr1hPkt1024    Counter64,
       pmIfStatCurr1hOutputPkts  Counter64,
       pmIfStatCurr1hOutputBytes  Counter64,
       pmIfStatCurr1hStartTime    DateAndTime,
       pmIfStatCurr1hStopTime   DateAndTime
    }

pmIfStatCurr1hIndex         OBJECT-TYPE
    SYNTAX          Integer32
    MAX-ACCESS      not-accessible
    STATUS          current
    DESCRIPTION
        "An index of units."
    ::= { pmIfStatCurr1hEntry 1 }

pmIfStatCurr1hId         OBJECT-TYPE
    SYNTAX          OCTET STRING
    MAX-ACCESS      read-only
    STATUS          current
    DESCRIPTION
        "Interface name."
    ::= { pmIfStatCurr1hEntry 2 }

pmIfStatCurr1hUnitType         OBJECT-TYPE
    SYNTAX          INTEGER
    {
       mcu(0)
    }
    MAX-ACCESS      read-only
    STATUS          current
    DESCRIPTION
        "Unit type."
    ::= { pmIfStatCurr1hEntry 3 }

pmIfStatCurr1hDropped         OBJECT-TYPE
    SYNTAX          Counter64
    MAX-ACCESS      read-only
    STATUS          current
    DESCRIPTION
        "Current 1hour counter of dropped events."
    ::= { pmIfStatCurr1hEntry 4 }

pmIfStatCurr1hInputPkts         OBJECT-TYPE
    SYNTAX          Counter64
    MAX-ACCESS      read-only
    STATUS          current
    DESCRIPTION
        "Current 1hour counter of input packets."
    ::= { pmIfStatCurr1hEntry 5 }

pmIfStatCurr1hInputbytes         OBJECT-TYPE
    SYNTAX          Counter64
    MAX-ACCESS      read-only
    STATUS          current
    DESCRIPTION
        "Current 1hour counter of input bytes."
    ::= { pmIfStatCurr1hEntry 6 }

pmIfStatCurr1hCrcErrors         OBJECT-TYPE
    SYNTAX          Counter64
    MAX-ACCESS      read-only
    STATUS          current
    DESCRIPTION
        "Current 1hour counter of packets with CRC error."
    ::= { pmIfStatCurr1hEntry 7 }

pmIfStatCurr1hInputBrdCst         OBJECT-TYPE
    SYNTAX          Counter64
    MAX-ACCESS      read-only
    STATUS          current
    DESCRIPTION
        "Current 1hour counter of broadcast packets."
    ::= { pmIfStatCurr1hEntry 8 }

pmIfStatCurr1hInputMltCst         OBJECT-TYPE
    SYNTAX          Counter64
    MAX-ACCESS      read-only
    STATUS          current
    DESCRIPTION
        "Current 1hour counter of multicast packets."
    ::= { pmIfStatCurr1hEntry 9 }

pmIfStatCurr1hCollision         OBJECT-TYPE
    SYNTAX          Counter64
    MAX-ACCESS      read-only
    STATUS          current
    DESCRIPTION
        "Current 1hour counter of collisions."
    ::= { pmIfStatCurr1hEntry 10 }

pmIfStatCurr1hUndersized         OBJECT-TYPE
    SYNTAX          Counter64
    MAX-ACCESS      read-only
    STATUS          current
    DESCRIPTION
        "Current 1hour counter of undersized packets."
    ::= { pmIfStatCurr1hEntry 11 }

pmIfStatCurr1hOversized         OBJECT-TYPE
    SYNTAX          Counter64
    MAX-ACCESS      read-only
    STATUS          current
    DESCRIPTION
        "Current 1hour counter of oversized packets."
    ::= { pmIfStatCurr1hEntry 12 }

pmIfStatCurr1hFragments         OBJECT-TYPE
    SYNTAX          Counter64
    MAX-ACCESS      read-only
    STATUS          current
    DESCRIPTION
        "Current 1hour counter of frament packets."
    ::= { pmIfStatCurr1hEntry 13 }

pmIfStatCurr1hJabbers         OBJECT-TYPE
    SYNTAX          Counter64
    MAX-ACCESS      read-only
    STATUS          current
    DESCRIPTION
        "Current 1hour counter of jabber packets."
    ::= { pmIfStatCurr1hEntry 14 }

pmIfStatCurr1hPkt64         OBJECT-TYPE
    SYNTAX          Counter64
    MAX-ACCESS      read-only
    STATUS          current
    DESCRIPTION
        "Current 1hour counter of packets with size under 64."
    ::= { pmIfStatCurr1hEntry 15 }

pmIfStatCurr1hPkt65To127         OBJECT-TYPE
    SYNTAX          Counter64
    MAX-ACCESS      read-only
    STATUS          current
    DESCRIPTION
        "Current 1hour counter of packets with size between 65 to 127."
    ::= { pmIfStatCurr1hEntry 16 }

pmIfStatCurr1hPkt128To255         OBJECT-TYPE
    SYNTAX          Counter64
    MAX-ACCESS      read-only
    STATUS          current
    DESCRIPTION
        "Current 1hour counter of packets with size between 128 to 255."
    ::= { pmIfStatCurr1hEntry 17 }

pmIfStatCurr1hPkt256To511         OBJECT-TYPE
    SYNTAX          Counter64
    MAX-ACCESS      read-only
    STATUS          current
    DESCRIPTION
        "Current 1hour counter of packets with size between 256 to 511."
    ::= { pmIfStatCurr1hEntry 18 }

pmIfStatCurr1hPkt512To1023         OBJECT-TYPE
    SYNTAX          Counter64
    MAX-ACCESS      read-only
    STATUS          current
    DESCRIPTION
        "Current 1hour counter of packets with size between 512 to 1023."
    ::= { pmIfStatCurr1hEntry 19 }

pmIfStatCurr1hPkt1024         OBJECT-TYPE
    SYNTAX          Counter64
    MAX-ACCESS      read-only
    STATUS          current
    DESCRIPTION
        "Current 1hour counter of packets with size over 1024."
    ::= { pmIfStatCurr1hEntry 20 }

pmIfStatCurr1hOutputPkts         OBJECT-TYPE
    SYNTAX          Counter64
    MAX-ACCESS      read-only
    STATUS          current
    DESCRIPTION
        "Current 1hour counter of interface output packets."
    ::= { pmIfStatCurr1hEntry 21 }

pmIfStatCurr1hOutputBytes         OBJECT-TYPE
    SYNTAX          Counter64
    MAX-ACCESS      read-only
    STATUS          current
    DESCRIPTION
        "Current 1hour counter of interface output bytes."
    ::= { pmIfStatCurr1hEntry 22 }

pmIfStatCurr1hStartTime         OBJECT-TYPE
    SYNTAX          DateAndTime
    MAX-ACCESS      read-only
    STATUS          current
    DESCRIPTION
        "Current 1hour start time."
    ::= { pmIfStatCurr1hEntry 100 }

pmIfStatCurr1hStopTime         OBJECT-TYPE
    SYNTAX          DateAndTime
    MAX-ACCESS      read-only
    STATUS          current
    DESCRIPTION
        "Current 1hour stop time."
    ::= { pmIfStatCurr1hEntry 101 }


pmIfStatPrev1hTable     OBJECT-TYPE
    SYNTAX          SEQUENCE OF PMIfStatPrev1hEntry
    MAX-ACCESS      not-accessible
    STATUS          current
    DESCRIPTION
        "A table that contains interface statistics information of all units."
    ::= { pmIfStatistics 4 }

pmIfStatPrev1hEntry     OBJECT-TYPE
    SYNTAX          PMIfStatPrev1hEntry
    MAX-ACCESS      not-accessible
    STATUS          current
    DESCRIPTION
        "A list of interface statistics information of all units."
    INDEX     { pmIfStatPrev1hIndex  }
    ::= { pmIfStatPrev1hTable 1 }

PMIfStatPrev1hEntry    ::=
    SEQUENCE
    {
       pmIfStatPrev1hIndex       Integer32,
       pmIfStatPrev1hId      OCTET STRING,
       pmIfStatPrev1hUnitType   INTEGER,
       pmIfStatPrev1hDropped    Counter64,
       pmIfStatPrev1hInputPkts   Counter64,
       pmIfStatPrev1hInputbytes  Counter64,
       pmIfStatPrev1hInputBrdCst  Counter64,
       pmIfStatPrev1hInputMltCst  Counter64,
       pmIfStatPrev1hCrcErrors   Counter64,
       pmIfStatPrev1hCollision   Counter64,
       pmIfStatPrev1hUndersized  Counter64,
       pmIfStatPrev1hOversized   Counter64,
       pmIfStatPrev1hFragments   Counter64,
       pmIfStatPrev1hJabbers    Counter64,
       pmIfStatPrev1hPkt64     Counter64,
       pmIfStatPrev1hPkt65To127  Counter64,
       pmIfStatPrev1hPkt128To255  Counter64,
       pmIfStatPrev1hPkt256To511  Counter64,
       pmIfStatPrev1hPkt512To1023 Counter64,
       pmIfStatPrev1hPkt1024    Counter64,
       pmIfStatPrev1hOutputPkts  Counter64,
       pmIfStatPrev1hOutputBytes  Counter64,
       pmIfStatPrev1hStartTime    DateAndTime,
       pmIfStatPrev1hStopTime   DateAndTime
    }

pmIfStatPrev1hIndex         OBJECT-TYPE
    SYNTAX          Integer32
    MAX-ACCESS      not-accessible
    STATUS          current
    DESCRIPTION
        "An index of units."
    ::= { pmIfStatPrev1hEntry 1 }

pmIfStatPrev1hId         OBJECT-TYPE
    SYNTAX          OCTET STRING
    MAX-ACCESS      read-only
    STATUS          current
    DESCRIPTION
        "Interface name."
    ::= { pmIfStatPrev1hEntry 2 }

pmIfStatPrev1hUnitType         OBJECT-TYPE
    SYNTAX          INTEGER
    {
       mcu(0)
    }
    MAX-ACCESS      read-only
    STATUS          current
    DESCRIPTION
        "Unit type."
    ::= { pmIfStatPrev1hEntry 3 }

pmIfStatPrev1hDropped         OBJECT-TYPE
    SYNTAX          Counter64
    MAX-ACCESS      read-only
    STATUS          current
    DESCRIPTION
        "Previous 1hour counter of dropped events."
    ::= { pmIfStatPrev1hEntry 4 }

pmIfStatPrev1hInputPkts         OBJECT-TYPE
    SYNTAX          Counter64
    MAX-ACCESS      read-only
    STATUS          current
    DESCRIPTION
        "Previous 1hour counter of input packets."
    ::= { pmIfStatPrev1hEntry 5 }

pmIfStatPrev1hInputbytes         OBJECT-TYPE
    SYNTAX          Counter64
    MAX-ACCESS      read-only
    STATUS          current
    DESCRIPTION
        "Previous 1hour counter of input bytes."
    ::= { pmIfStatPrev1hEntry 6 }

pmIfStatPrev1hCrcErrors         OBJECT-TYPE
    SYNTAX          Counter64
    MAX-ACCESS      read-only
    STATUS          current
    DESCRIPTION
        "Previous 1hour counter of packets with CRC error."
    ::= { pmIfStatPrev1hEntry 7 }

pmIfStatPrev1hInputBrdCst         OBJECT-TYPE
    SYNTAX          Counter64
    MAX-ACCESS      read-only
    STATUS          current
    DESCRIPTION
        "Previous 1hour counter of broadcast packets."
    ::= { pmIfStatPrev1hEntry 8 }

pmIfStatPrev1hInputMltCst         OBJECT-TYPE
    SYNTAX          Counter64
    MAX-ACCESS      read-only
    STATUS          current
    DESCRIPTION
        "Previous 1hour counter of multicast packets."
    ::= { pmIfStatPrev1hEntry 9 }

pmIfStatPrev1hCollision         OBJECT-TYPE
    SYNTAX          Counter64
    MAX-ACCESS      read-only
    STATUS          current
    DESCRIPTION
        "Previous 1hour counter of collisions."
    ::= { pmIfStatPrev1hEntry 10 }

pmIfStatPrev1hUndersized         OBJECT-TYPE
    SYNTAX          Counter64
    MAX-ACCESS      read-only
    STATUS          current
    DESCRIPTION
        "Previous 1hour counter of undersized packets."
    ::= { pmIfStatPrev1hEntry 11 }

pmIfStatPrev1hOversized         OBJECT-TYPE
    SYNTAX          Counter64
    MAX-ACCESS      read-only
    STATUS          current
    DESCRIPTION
        "Previous 1hour counter of oversized packets."
    ::= { pmIfStatPrev1hEntry 12 }

pmIfStatPrev1hFragments         OBJECT-TYPE
    SYNTAX          Counter64
    MAX-ACCESS      read-only
    STATUS          current
    DESCRIPTION
        "Previous 1hour counter of frament packets."
    ::= { pmIfStatPrev1hEntry 13 }

pmIfStatPrev1hJabbers         OBJECT-TYPE
    SYNTAX          Counter64
    MAX-ACCESS      read-only
    STATUS          current
    DESCRIPTION
        "Previous 1hour counter of jabber packets."
    ::= { pmIfStatPrev1hEntry 14 }

pmIfStatPrev1hPkt64         OBJECT-TYPE
    SYNTAX          Counter64
    MAX-ACCESS      read-only
    STATUS          current
    DESCRIPTION
        "Previous 1hour counter of packets with size under 64."
    ::= { pmIfStatPrev1hEntry 15 }

pmIfStatPrev1hPkt65To127         OBJECT-TYPE
    SYNTAX          Counter64
    MAX-ACCESS      read-only
    STATUS          current
    DESCRIPTION
        "Previous 1hour counter of packets with size between 65 to 127."
    ::= { pmIfStatPrev1hEntry 16 }

pmIfStatPrev1hPkt128To255         OBJECT-TYPE
    SYNTAX          Counter64
    MAX-ACCESS      read-only
    STATUS          current
    DESCRIPTION
        "Previous 1hour counter of packets with size between 128 to 255."
    ::= { pmIfStatPrev1hEntry 17 }

pmIfStatPrev1hPkt256To511         OBJECT-TYPE
    SYNTAX          Counter64
    MAX-ACCESS      read-only
    STATUS          current
    DESCRIPTION
        "Previous 1hour counter of packets with size between 256 to 511."
    ::= { pmIfStatPrev1hEntry 18 }

pmIfStatPrev1hPkt512To1023         OBJECT-TYPE
    SYNTAX          Counter64
    MAX-ACCESS      read-only
    STATUS          current
    DESCRIPTION
        "Previous 1hour counter of packets with size between 512 to 1023."
    ::= { pmIfStatPrev1hEntry 19 }

pmIfStatPrev1hPkt1024         OBJECT-TYPE
    SYNTAX          Counter64
    MAX-ACCESS      read-only
    STATUS          current
    DESCRIPTION
        "Previous 1hour counter of packets with size over 1024."
    ::= { pmIfStatPrev1hEntry 20 }

pmIfStatPrev1hOutputPkts         OBJECT-TYPE
    SYNTAX          Counter64
    MAX-ACCESS      read-only
    STATUS          current
    DESCRIPTION
        "Previous 1hour counter of interface output packets."
    ::= { pmIfStatPrev1hEntry 21 }

pmIfStatPrev1hOutputBytes         OBJECT-TYPE
    SYNTAX          Counter64
    MAX-ACCESS      read-only
    STATUS          current
    DESCRIPTION
        "Previous 1hour counter of interface output bytes."
    ::= { pmIfStatPrev1hEntry 22 }

pmIfStatPrev1hStartTime         OBJECT-TYPE
    SYNTAX          DateAndTime
    MAX-ACCESS      read-only
    STATUS          current
    DESCRIPTION
        "Previous 1hour start time."
    ::= { pmIfStatPrev1hEntry 100 }

pmIfStatPrev1hStopTime         OBJECT-TYPE
    SYNTAX          DateAndTime
    MAX-ACCESS      read-only
    STATUS          current
    DESCRIPTION
        "Previous 1hour stop time."
    ::= { pmIfStatPrev1hEntry 101 }

pmIfStatCurr1dTable     OBJECT-TYPE
    SYNTAX          SEQUENCE OF PMIfStatCurr1dEntry
    MAX-ACCESS      not-accessible
    STATUS          current
    DESCRIPTION
        "A table that contains interface statistics information of all units."
    ::= { pmIfStatistics 5 }

pmIfStatCurr1dEntry     OBJECT-TYPE
    SYNTAX          PMIfStatCurr1dEntry
    MAX-ACCESS      not-accessible
    STATUS          current
    DESCRIPTION
        "A list of interface statistics information of all units."
    INDEX     { pmIfStatCurr1dIndex  }
    ::= { pmIfStatCurr1dTable 1 }

PMIfStatCurr1dEntry    ::=
    SEQUENCE
    {
       pmIfStatCurr1dIndex       Integer32,
       pmIfStatCurr1dId      OCTET STRING,
       pmIfStatCurr1dUnitType   INTEGER,
       pmIfStatCurr1dDropped    Counter64,
       pmIfStatCurr1dInputPkts   Counter64,
       pmIfStatCurr1dInputbytes  Counter64,
       pmIfStatCurr1dInputBrdCst  Counter64,
       pmIfStatCurr1dInputMltCst  Counter64,
       pmIfStatCurr1dCrcErrors   Counter64,
       pmIfStatCurr1dCollision   Counter64,
       pmIfStatCurr1dUndersized  Counter64,
       pmIfStatCurr1dOversized   Counter64,
       pmIfStatCurr1dFragments   Counter64,
       pmIfStatCurr1dJabbers    Counter64,
       pmIfStatCurr1dPkt64     Counter64,
       pmIfStatCurr1dPkt65To127  Counter64,
       pmIfStatCurr1dPkt128To255  Counter64,
       pmIfStatCurr1dPkt256To511  Counter64,
       pmIfStatCurr1dPkt512To1023 Counter64,
       pmIfStatCurr1dPkt1024    Counter64,
       pmIfStatCurr1dOutputPkts  Counter64,
       pmIfStatCurr1dOutputBytes  Counter64,
       pmIfStatCurr1dStartTime    DateAndTime,
       pmIfStatCurr1dStopTime   DateAndTime
    }

pmIfStatCurr1dIndex         OBJECT-TYPE
    SYNTAX          Integer32
    MAX-ACCESS      not-accessible
    STATUS          current
    DESCRIPTION
        "An index of units."
    ::= { pmIfStatCurr1dEntry 1 }

pmIfStatCurr1dId         OBJECT-TYPE
    SYNTAX          OCTET STRING
    MAX-ACCESS      read-only
    STATUS          current
    DESCRIPTION
        "Interface name."
    ::= { pmIfStatCurr1dEntry 2 }

pmIfStatCurr1dUnitType         OBJECT-TYPE
    SYNTAX          INTEGER
    {
       mcu(0)
    }
    MAX-ACCESS      read-only
    STATUS          current
    DESCRIPTION
        "Unit type."
    ::= { pmIfStatCurr1dEntry 3 }

pmIfStatCurr1dDropped         OBJECT-TYPE
    SYNTAX          Counter64
    MAX-ACCESS      read-only
    STATUS          current
    DESCRIPTION
        "Current 1day counter of dropped events."
    ::= { pmIfStatCurr1dEntry 4 }

pmIfStatCurr1dInputPkts         OBJECT-TYPE
    SYNTAX          Counter64
    MAX-ACCESS      read-only
    STATUS          current
    DESCRIPTION
        "Current 1day counter of input packets."
    ::= { pmIfStatCurr1dEntry 5 }

pmIfStatCurr1dInputbytes         OBJECT-TYPE
    SYNTAX          Counter64
    MAX-ACCESS      read-only
    STATUS          current
    DESCRIPTION
        "Current 1day counter of input bytes."
    ::= { pmIfStatCurr1dEntry 6 }

pmIfStatCurr1dCrcErrors         OBJECT-TYPE
    SYNTAX          Counter64
    MAX-ACCESS      read-only
    STATUS          current
    DESCRIPTION
        "Current 1day counter of packets with CRC error."
    ::= { pmIfStatCurr1dEntry 7 }

pmIfStatCurr1dInputBrdCst         OBJECT-TYPE
    SYNTAX          Counter64
    MAX-ACCESS      read-only
    STATUS          current
    DESCRIPTION
        "Current 1day counter of broadcast packets."
    ::= { pmIfStatCurr1dEntry 8 }

pmIfStatCurr1dInputMltCst         OBJECT-TYPE
    SYNTAX          Counter64
    MAX-ACCESS      read-only
    STATUS          current
    DESCRIPTION
        "Current 1day counter of multicast packets."
    ::= { pmIfStatCurr1dEntry 9 }

pmIfStatCurr1dCollision         OBJECT-TYPE
    SYNTAX          Counter64
    MAX-ACCESS      read-only
    STATUS          current
    DESCRIPTION
        "Current 1day counter of collisions."
    ::= { pmIfStatCurr1dEntry 10 }

pmIfStatCurr1dUndersized         OBJECT-TYPE
    SYNTAX          Counter64
    MAX-ACCESS      read-only
    STATUS          current
    DESCRIPTION
        "Current 1day counter of undersized packets."
    ::= { pmIfStatCurr1dEntry 11 }

pmIfStatCurr1dOversized         OBJECT-TYPE
    SYNTAX          Counter64
    MAX-ACCESS      read-only
    STATUS          current
    DESCRIPTION
        "Current 1day counter of oversized packets."
    ::= { pmIfStatCurr1dEntry 12 }

pmIfStatCurr1dFragments         OBJECT-TYPE
    SYNTAX          Counter64
    MAX-ACCESS      read-only
    STATUS          current
    DESCRIPTION
        "Current 1day counter of frament packets."
    ::= { pmIfStatCurr1dEntry 13 }

pmIfStatCurr1dJabbers         OBJECT-TYPE
    SYNTAX          Counter64
    MAX-ACCESS      read-only
    STATUS          current
    DESCRIPTION
        "Current 1day counter of jabber packets."
    ::= { pmIfStatCurr1dEntry 14 }

pmIfStatCurr1dPkt64         OBJECT-TYPE
    SYNTAX          Counter64
    MAX-ACCESS      read-only
    STATUS          current
    DESCRIPTION
        "Current 1day counter of packets with size under 64."
    ::= { pmIfStatCurr1dEntry 15 }

pmIfStatCurr1dPkt65To127         OBJECT-TYPE
    SYNTAX          Counter64
    MAX-ACCESS      read-only
    STATUS          current
    DESCRIPTION
        "Current 1day counter of packets with size between 65 to 127."
    ::= { pmIfStatCurr1dEntry 16 }

pmIfStatCurr1dPkt128To255         OBJECT-TYPE
    SYNTAX          Counter64
    MAX-ACCESS      read-only
    STATUS          current
    DESCRIPTION
        "Current 1day counter of packets with size between 128 to 255."
    ::= { pmIfStatCurr1dEntry 17 }

pmIfStatCurr1dPkt256To511         OBJECT-TYPE
    SYNTAX          Counter64
    MAX-ACCESS      read-only
    STATUS          current
    DESCRIPTION
        "Current 1day counter of packets with size between 256 to 511."
    ::= { pmIfStatCurr1dEntry 18 }

pmIfStatCurr1dPkt512To1023         OBJECT-TYPE
    SYNTAX          Counter64
    MAX-ACCESS      read-only
    STATUS          current
    DESCRIPTION
        "Current 1day counter of packets with size between 512 to 1023."
    ::= { pmIfStatCurr1dEntry 19 }

pmIfStatCurr1dPkt1024         OBJECT-TYPE
    SYNTAX          Counter64
    MAX-ACCESS      read-only
    STATUS          current
    DESCRIPTION
        "Current 1day counter of packets with size over 1024."
    ::= { pmIfStatCurr1dEntry 20 }

pmIfStatCurr1dOutputPkts         OBJECT-TYPE
    SYNTAX          Counter64
    MAX-ACCESS      read-only
    STATUS          current
    DESCRIPTION
        "Current 1day counter of interface output packets."
    ::= { pmIfStatCurr1dEntry 21 }

pmIfStatCurr1dOutputBytes         OBJECT-TYPE
    SYNTAX          Counter64
    MAX-ACCESS      read-only
    STATUS          current
    DESCRIPTION
        "Current 1day counter of interface output bytes."
    ::= { pmIfStatCurr1dEntry 22 }

pmIfStatCurr1dStartTime         OBJECT-TYPE
    SYNTAX          DateAndTime
    MAX-ACCESS      read-only
    STATUS          current
    DESCRIPTION
        "Current 1day start time."
    ::= { pmIfStatCurr1dEntry 100 }

pmIfStatCurr1dStopTime         OBJECT-TYPE
    SYNTAX          DateAndTime
    MAX-ACCESS      read-only
    STATUS          current
    DESCRIPTION
        "Current 1day stop time."
    ::= { pmIfStatCurr1dEntry 101 }


pmIfStatPrev1dTable     OBJECT-TYPE
    SYNTAX          SEQUENCE OF PMIfStatPrev1dEntry
    MAX-ACCESS      not-accessible
    STATUS          current
    DESCRIPTION
        "A table that contains interface statistics information of all units."
    ::= { pmIfStatistics 6 }

pmIfStatPrev1dEntry     OBJECT-TYPE
    SYNTAX          PMIfStatPrev1dEntry
    MAX-ACCESS      not-accessible
    STATUS          current
    DESCRIPTION
        "A list of interface statistics information of all units."
    INDEX     { pmIfStatPrev1dIndex  }
    ::= { pmIfStatPrev1dTable 1 }

PMIfStatPrev1dEntry    ::=
    SEQUENCE
    {
       pmIfStatPrev1dIndex       Integer32,
       pmIfStatPrev1dId      OCTET STRING,
       pmIfStatPrev1dUnitType   INTEGER,
       pmIfStatPrev1dDropped    Counter64,
       pmIfStatPrev1dInputPkts   Counter64,
       pmIfStatPrev1dInputbytes  Counter64,
       pmIfStatPrev1dInputBrdCst  Counter64,
       pmIfStatPrev1dInputMltCst  Counter64,
       pmIfStatPrev1dCrcErrors   Counter64,
       pmIfStatPrev1dCollision   Counter64,
       pmIfStatPrev1dUndersized  Counter64,
       pmIfStatPrev1dOversized   Counter64,
       pmIfStatPrev1dFragments   Counter64,
       pmIfStatPrev1dJabbers    Counter64,
       pmIfStatPrev1dPkt64     Counter64,
       pmIfStatPrev1dPkt65To127  Counter64,
       pmIfStatPrev1dPkt128To255  Counter64,
       pmIfStatPrev1dPkt256To511  Counter64,
       pmIfStatPrev1dPkt512To1023 Counter64,
       pmIfStatPrev1dPkt1024    Counter64,
       pmIfStatPrev1dOutputPkts  Counter64,
       pmIfStatPrev1dOutputBytes  Counter64,
       pmIfStatPrev1dStartTime    DateAndTime,
       pmIfStatPrev1dStopTime   DateAndTime
    }

pmIfStatPrev1dIndex         OBJECT-TYPE
    SYNTAX          Integer32
    MAX-ACCESS      not-accessible
    STATUS          current
    DESCRIPTION
        "An index of units."
    ::= { pmIfStatPrev1dEntry 1 }

pmIfStatPrev1dId         OBJECT-TYPE
    SYNTAX          OCTET STRING
    MAX-ACCESS      read-only
    STATUS          current
    DESCRIPTION
        "Interface name."
    ::= { pmIfStatPrev1dEntry 2 }

pmIfStatPrev1dUnitType         OBJECT-TYPE
    SYNTAX          INTEGER
    {
       mcu(0)
    }
    MAX-ACCESS      read-only
    STATUS          current
    DESCRIPTION
        "Unit type."
    ::= { pmIfStatPrev1dEntry 3 }

pmIfStatPrev1dDropped         OBJECT-TYPE
    SYNTAX          Counter64
    MAX-ACCESS      read-only
    STATUS          current
    DESCRIPTION
        "Previous 1day counter of dropped events."
    ::= { pmIfStatPrev1dEntry 4 }

pmIfStatPrev1dInputPkts         OBJECT-TYPE
    SYNTAX          Counter64
    MAX-ACCESS      read-only
    STATUS          current
    DESCRIPTION
        "Previous 1day counter of input packets."
    ::= { pmIfStatPrev1dEntry 5 }

pmIfStatPrev1dInputbytes         OBJECT-TYPE
    SYNTAX          Counter64
    MAX-ACCESS      read-only
    STATUS          current
    DESCRIPTION
        "Previous 1day counter of input bytes."
    ::= { pmIfStatPrev1dEntry 6 }

pmIfStatPrev1dCrcErrors         OBJECT-TYPE
    SYNTAX          Counter64
    MAX-ACCESS      read-only
    STATUS          current
    DESCRIPTION
        "Previous 1day counter of packets with CRC error."
    ::= { pmIfStatPrev1dEntry 7 }

pmIfStatPrev1dInputBrdCst         OBJECT-TYPE
    SYNTAX          Counter64
    MAX-ACCESS      read-only
    STATUS          current
    DESCRIPTION
        "Previous 1day counter of broadcast packets."
    ::= { pmIfStatPrev1dEntry 8 }

pmIfStatPrev1dInputMltCst         OBJECT-TYPE
    SYNTAX          Counter64
    MAX-ACCESS      read-only
    STATUS          current
    DESCRIPTION
        "Previous 1day counter of multicast packets."
    ::= { pmIfStatPrev1dEntry 9 }

pmIfStatPrev1dCollision         OBJECT-TYPE
    SYNTAX          Counter64
    MAX-ACCESS      read-only
    STATUS          current
    DESCRIPTION
        "Previous 1day counter of collisions."
    ::= { pmIfStatPrev1dEntry 10 }

pmIfStatPrev1dUndersized         OBJECT-TYPE
    SYNTAX          Counter64
    MAX-ACCESS      read-only
    STATUS          current
    DESCRIPTION
        "Previous 1day counter of undersized packets."
    ::= { pmIfStatPrev1dEntry 11 }

pmIfStatPrev1dOversized         OBJECT-TYPE
    SYNTAX          Counter64
    MAX-ACCESS      read-only
    STATUS          current
    DESCRIPTION
        "Previous 1day counter of oversized packets."
    ::= { pmIfStatPrev1dEntry 12 }

pmIfStatPrev1dFragments         OBJECT-TYPE
    SYNTAX          Counter64
    MAX-ACCESS      read-only
    STATUS          current
    DESCRIPTION
        "Previous 1day counter of frament packets."
    ::= { pmIfStatPrev1dEntry 13 }

pmIfStatPrev1dJabbers         OBJECT-TYPE
    SYNTAX          Counter64
    MAX-ACCESS      read-only
    STATUS          current
    DESCRIPTION
        "Previous 1day counter of jabber packets."
    ::= { pmIfStatPrev1dEntry 14 }

pmIfStatPrev1dPkt64         OBJECT-TYPE
    SYNTAX          Counter64
    MAX-ACCESS      read-only
    STATUS          current
    DESCRIPTION
        "Previous 1day counter of packets with size under 64."
    ::= { pmIfStatPrev1dEntry 15 }

pmIfStatPrev1dPkt65To127         OBJECT-TYPE
    SYNTAX          Counter64
    MAX-ACCESS      read-only
    STATUS          current
    DESCRIPTION
        "Previous 1day counter of packets with size between 65 to 127."
    ::= { pmIfStatPrev1dEntry 16 }

pmIfStatPrev1dPkt128To255         OBJECT-TYPE
    SYNTAX          Counter64
    MAX-ACCESS      read-only
    STATUS          current
    DESCRIPTION
        "Previous 1day counter of packets with size between 128 to 255."
    ::= { pmIfStatPrev1dEntry 17 }

pmIfStatPrev1dPkt256To511         OBJECT-TYPE
    SYNTAX          Counter64
    MAX-ACCESS      read-only
    STATUS          current
    DESCRIPTION
        "Previous 1day counter of packets with size between 256 to 511."
    ::= { pmIfStatPrev1dEntry 18 }

pmIfStatPrev1dPkt512To1023         OBJECT-TYPE
    SYNTAX          Counter64
    MAX-ACCESS      read-only
    STATUS          current
    DESCRIPTION
        "Previous 1day counter of packets with size between 512 to 1023."
    ::= { pmIfStatPrev1dEntry 19 }

pmIfStatPrev1dPkt1024         OBJECT-TYPE
    SYNTAX          Counter64
    MAX-ACCESS      read-only
    STATUS          current
    DESCRIPTION
        "Previous 1day counter of packets with size over 1024."
    ::= { pmIfStatPrev1dEntry 20 }

pmIfStatPrev1dOutputPkts         OBJECT-TYPE
    SYNTAX          Counter64
    MAX-ACCESS      read-only
    STATUS          current
    DESCRIPTION
        "Previous 1day counter of interface output packets."
    ::= { pmIfStatPrev1dEntry 21 }

pmIfStatPrev1dOutputBytes         OBJECT-TYPE
    SYNTAX          Counter64
    MAX-ACCESS      read-only
    STATUS          current
    DESCRIPTION
        "Previous 1day counter of interface output bytes."
    ::= { pmIfStatPrev1dEntry 22 }

pmIfStatPrev1dStartTime         OBJECT-TYPE
    SYNTAX          DateAndTime
    MAX-ACCESS      read-only
    STATUS          current
    DESCRIPTION
        "Previous 1day start time."
    ::= { pmIfStatPrev1dEntry 100 }

pmIfStatPrev1dStopTime         OBJECT-TYPE
    SYNTAX          DateAndTime
    MAX-ACCESS      read-only
    STATUS          current
    DESCRIPTION
        "Previous 1day stop time."
    ::= { pmIfStatPrev1dEntry 101 }


pmTcaIfDropped15mTable     OBJECT-TYPE
    SYNTAX          SEQUENCE OF PMTcaIfDropped15mEntry
    MAX-ACCESS      not-accessible
    STATUS          current
    DESCRIPTION
        "A table that contains interface information of all units."
    ::= { pmIfStatistics 7 }

pmTcaIfDropped15mEntry     OBJECT-TYPE
    SYNTAX          PMTcaIfDropped15mEntry
    MAX-ACCESS      not-accessible
    STATUS          current
    DESCRIPTION
        "A list of temperature information of all units."
    INDEX     { pmTcaIfDropped15mIndex  }
    ::= { pmTcaIfDropped15mTable 1 }

PMTcaIfDropped15mEntry    ::=
    SEQUENCE
    {
       pmTcaIfDropped15mIndex      Integer32,
       pmTcaIfDropped15mId     OCTET STRING,
       pmTcaIfDropped15mUnitType   INTEGER,
       pmTcaIfDropped15mCnt     Counter64,
       pmTcaIfDropped15mThreshold   Counter64,
       pmTcaIfDropped15mOccurTime   DateAndTime
    }

pmTcaIfDropped15mIndex         OBJECT-TYPE
    SYNTAX          Integer32
    MAX-ACCESS      not-accessible
    STATUS          current
    DESCRIPTION
        "An index of units."
    ::= { pmTcaIfDropped15mEntry 1 }

pmTcaIfDropped15mId         OBJECT-TYPE
    SYNTAX          OCTET STRING
    MAX-ACCESS      read-only
    STATUS          current
    DESCRIPTION
        "Interface name."
    ::= { pmTcaIfDropped15mEntry 2 }

pmTcaIfDropped15mUnitType         OBJECT-TYPE
    SYNTAX          INTEGER
    {
       mcu(0)
    }
    MAX-ACCESS      read-only
    STATUS          current
    DESCRIPTION
        "Unit type."
    ::= { pmTcaIfDropped15mEntry 3 }

pmTcaIfDropped15mCnt         OBJECT-TYPE
    SYNTAX          Counter64
    MAX-ACCESS      read-only
    STATUS          current
    DESCRIPTION
        "15min counter of interface dropped events."
    ::= { pmTcaIfDropped15mEntry 4 }

pmTcaIfDropped15mThreshold         OBJECT-TYPE
    SYNTAX          Counter64
    MAX-ACCESS      read-only
    STATUS          current
    DESCRIPTION
        "15min threshold of interface dropped events."
    ::= { pmTcaIfDropped15mEntry 5 }

pmTcaIfDropped15mOccurTime         OBJECT-TYPE
    SYNTAX          DateAndTime
    MAX-ACCESS      read-only
    STATUS          current
    DESCRIPTION
        "Time of the occurrence of the tca."
    ::= { pmTcaIfDropped15mEntry 6 }

pmTcaIfDropped1hTable     OBJECT-TYPE
    SYNTAX          SEQUENCE OF PMTcaIfDropped1hEntry
    MAX-ACCESS      not-accessible
    STATUS          current
    DESCRIPTION
        "A table that contains interface information of all units."
    ::= { pmIfStatistics 8 }

pmTcaIfDropped1hEntry     OBJECT-TYPE
    SYNTAX          PMTcaIfDropped1hEntry
    MAX-ACCESS      not-accessible
    STATUS          current
    DESCRIPTION
        "A list of temperature information of all units."
    INDEX     { pmTcaIfDropped1hIndex  }
    ::= { pmTcaIfDropped1hTable 1 }

PMTcaIfDropped1hEntry    ::=
    SEQUENCE
    {
       pmTcaIfDropped1hIndex      Integer32,
       pmTcaIfDropped1hId     OCTET STRING,
       pmTcaIfDropped1hUnitType   INTEGER,
       pmTcaIfDropped1hCnt     Counter64,
       pmTcaIfDropped1hThreshold   Counter64,
       pmTcaIfDropped1hOccurTime   DateAndTime
    }

pmTcaIfDropped1hIndex         OBJECT-TYPE
    SYNTAX          Integer32
    MAX-ACCESS      not-accessible
    STATUS          current
    DESCRIPTION
        "An index of units."
    ::= { pmTcaIfDropped1hEntry 1 }

pmTcaIfDropped1hId         OBJECT-TYPE
    SYNTAX          OCTET STRING
    MAX-ACCESS      read-only
    STATUS          current
    DESCRIPTION
        "Interface name."
    ::= { pmTcaIfDropped1hEntry 2 }

pmTcaIfDropped1hUnitType         OBJECT-TYPE
    SYNTAX          INTEGER
    {
       mcu(0)
    }
    MAX-ACCESS      read-only
    STATUS          current
    DESCRIPTION
        "Unit type."
    ::= { pmTcaIfDropped1hEntry 3 }

pmTcaIfDropped1hCnt         OBJECT-TYPE
    SYNTAX          Counter64
    MAX-ACCESS      read-only
    STATUS          current
    DESCRIPTION
        "1hour counter of interface dropped events."
    ::= { pmTcaIfDropped1hEntry 4 }

pmTcaIfDropped1hThreshold         OBJECT-TYPE
    SYNTAX          Counter64
    MAX-ACCESS      read-only
    STATUS          current
    DESCRIPTION
        "1hour threshold of interface dropped events."
    ::= { pmTcaIfDropped1hEntry 5 }

pmTcaIfDropped1hOccurTime         OBJECT-TYPE
    SYNTAX          DateAndTime
    MAX-ACCESS      read-only
    STATUS          current
    DESCRIPTION
        "Time of the occurrence of the tca."
    ::= { pmTcaIfDropped1hEntry 6 }

pmTcaIfDropped1dTable     OBJECT-TYPE
    SYNTAX          SEQUENCE OF PMTcaIfDropped1dEntry
    MAX-ACCESS      not-accessible
    STATUS          current
    DESCRIPTION
        "A table that contains temperature information of all units."
    ::= { pmIfStatistics 9 }

pmTcaIfDropped1dEntry     OBJECT-TYPE
    SYNTAX          PMTcaIfDropped1dEntry
    MAX-ACCESS      not-accessible
    STATUS          current
    DESCRIPTION
        "A list of temperature information of all units."
    INDEX     { pmTcaIfDropped1dIndex  }
    ::= { pmTcaIfDropped1dTable 1 }

PMTcaIfDropped1dEntry    ::=
    SEQUENCE
    {
       pmTcaIfDropped1dIndex      Integer32,
       pmTcaIfDropped1dId     OCTET STRING,
       pmTcaIfDropped1dUnitType  INTEGER,
       pmTcaIfDropped1dCnt     Counter64,
       pmTcaIfDropped1dThreshold   Counter64,
       pmTcaIfDropped1dOccurTime   DateAndTime
    }

pmTcaIfDropped1dIndex         OBJECT-TYPE
    SYNTAX          Integer32
    MAX-ACCESS      not-accessible
    STATUS          current
    DESCRIPTION
        "An index of units."
    ::= { pmTcaIfDropped1dEntry 1 }

pmTcaIfDropped1dId         OBJECT-TYPE
    SYNTAX          OCTET STRING
    MAX-ACCESS      read-only
    STATUS          current
    DESCRIPTION
        "Interface name."
    ::= { pmTcaIfDropped1dEntry 2 }

pmTcaIfDropped1dUnitType         OBJECT-TYPE
    SYNTAX          INTEGER
    {
       mcu(0)
    }
    MAX-ACCESS      read-only
    STATUS          current
    DESCRIPTION
        "Unit type."
    ::= { pmTcaIfDropped1dEntry 3 }

pmTcaIfDropped1dCnt         OBJECT-TYPE
    SYNTAX          Counter64
    MAX-ACCESS      read-only
    STATUS          current
    DESCRIPTION
        "1day counter of interface dropped events."
    ::= { pmTcaIfDropped1dEntry 4 }

pmTcaIfDropped1dThreshold         OBJECT-TYPE
    SYNTAX          Counter64
    MAX-ACCESS      read-only
    STATUS          current
    DESCRIPTION
        "1day threshold of interface dropped events."
    ::= { pmTcaIfDropped1dEntry 5 }

pmTcaIfDropped1dOccurTime         OBJECT-TYPE
    SYNTAX          DateAndTime
    MAX-ACCESS      read-only
    STATUS          current
    DESCRIPTION
        "Time of the occurrence of the tca."
    ::= { pmTcaIfDropped1dEntry 6 }


pmTcaIfInPkts15mTable     OBJECT-TYPE
    SYNTAX          SEQUENCE OF PMTcaIfInPkts15mEntry
    MAX-ACCESS      not-accessible
    STATUS          current
    DESCRIPTION
        "A table that contains interface information of all units."
    ::= { pmIfStatistics 10 }

pmTcaIfInPkts15mEntry     OBJECT-TYPE
    SYNTAX          PMTcaIfInPkts15mEntry
    MAX-ACCESS      not-accessible
    STATUS          current
    DESCRIPTION
        "A list of interface information of all units."
    INDEX     { pmTcaIfInPkts15mIndex  }
    ::= { pmTcaIfInPkts15mTable 1 }

PMTcaIfInPkts15mEntry    ::=
    SEQUENCE
    {
       pmTcaIfInPkts15mIndex      Integer32,
       pmTcaIfInPkts15mId     OCTET STRING,
       pmTcaIfInPkts15mUnitType   INTEGER,
       pmTcaIfInPkts15mCnt     Counter64,
       pmTcaIfInPkts15mThreshold   Counter64,
       pmTcaIfInPkts15mOccurTime   DateAndTime
    }

pmTcaIfInPkts15mIndex         OBJECT-TYPE
    SYNTAX          Integer32
    MAX-ACCESS      not-accessible
    STATUS          current
    DESCRIPTION
        "An index of units."
    ::= { pmTcaIfInPkts15mEntry 1 }

pmTcaIfInPkts15mId         OBJECT-TYPE
    SYNTAX          OCTET STRING
    MAX-ACCESS      read-only
    STATUS          current
    DESCRIPTION
        "Interface name."
    ::= { pmTcaIfInPkts15mEntry 2 }

pmTcaIfInPkts15mUnitType         OBJECT-TYPE
    SYNTAX          INTEGER
    {
       mcu(0)
    }
    MAX-ACCESS      read-only
    STATUS          current
    DESCRIPTION
        "Unit type."
    ::= { pmTcaIfInPkts15mEntry 3 }

pmTcaIfInPkts15mCnt         OBJECT-TYPE
    SYNTAX          Counter64
    MAX-ACCESS      read-only
    STATUS          current
    DESCRIPTION
        "15min counter of input packets."
    ::= { pmTcaIfInPkts15mEntry 4 }

pmTcaIfInPkts15mThreshold         OBJECT-TYPE
    SYNTAX          Counter64
    MAX-ACCESS      read-only
    STATUS          current
    DESCRIPTION
        "15min threshold of input packets."
    ::= { pmTcaIfInPkts15mEntry 5 }

pmTcaIfInPkts15mOccurTime         OBJECT-TYPE
    SYNTAX          DateAndTime
    MAX-ACCESS      read-only
    STATUS          current
    DESCRIPTION
        "Time of the occurrence of the tca."
    ::= { pmTcaIfInPkts15mEntry 6 }

pmTcaIfInPkts1hTable     OBJECT-TYPE
    SYNTAX          SEQUENCE OF PMTcaIfInPkts1hEntry
    MAX-ACCESS      not-accessible
    STATUS          current
    DESCRIPTION
        "A table that contains interface information of all units."
    ::= { pmIfStatistics 11 }

pmTcaIfInPkts1hEntry     OBJECT-TYPE
    SYNTAX          PMTcaIfInPkts1hEntry
    MAX-ACCESS      not-accessible
    STATUS          current
    DESCRIPTION
        "A list of interface information of all units."
    INDEX     { pmTcaIfInPkts1hIndex  }
    ::= { pmTcaIfInPkts1hTable 1 }

PMTcaIfInPkts1hEntry    ::=
    SEQUENCE
    {
       pmTcaIfInPkts1hIndex      Integer32,
       pmTcaIfInPkts1hId     OCTET STRING,
       pmTcaIfInPkts1hUnitType   INTEGER,
       pmTcaIfInPkts1hCnt     Counter64,
       pmTcaIfInPkts1hThreshold   Counter64,
       pmTcaIfInPkts1hOccurTime   DateAndTime
    }

pmTcaIfInPkts1hIndex         OBJECT-TYPE
    SYNTAX          Integer32
    MAX-ACCESS      not-accessible
    STATUS          current
    DESCRIPTION
        "An index of units."
    ::= { pmTcaIfInPkts1hEntry 1 }

pmTcaIfInPkts1hId         OBJECT-TYPE
    SYNTAX          OCTET STRING
    MAX-ACCESS      read-only
    STATUS          current
    DESCRIPTION
        "Interface name."
    ::= { pmTcaIfInPkts1hEntry 2 }

pmTcaIfInPkts1hUnitType         OBJECT-TYPE
    SYNTAX          INTEGER
    {
       mcu(0)
    }
    MAX-ACCESS      read-only
    STATUS          current
    DESCRIPTION
        "Unit type."
    ::= { pmTcaIfInPkts1hEntry 3 }

pmTcaIfInPkts1hCnt         OBJECT-TYPE
    SYNTAX          Counter64
    MAX-ACCESS      read-only
    STATUS          current
    DESCRIPTION
        "1hour counter of input packets."
    ::= { pmTcaIfInPkts1hEntry 4 }

pmTcaIfInPkts1hThreshold         OBJECT-TYPE
    SYNTAX          Counter64
    MAX-ACCESS      read-only
    STATUS          current
    DESCRIPTION
        "1hour threshold of input packets."
    ::= { pmTcaIfInPkts1hEntry 5 }

pmTcaIfInPkts1hOccurTime         OBJECT-TYPE
    SYNTAX          DateAndTime
    MAX-ACCESS      read-only
    STATUS          current
    DESCRIPTION
        "Time of the occurrence of the tca."
    ::= { pmTcaIfInPkts1hEntry 6 }

pmTcaIfInPkts1dTable     OBJECT-TYPE
    SYNTAX          SEQUENCE OF PMTcaIfInPkts1dEntry
    MAX-ACCESS      not-accessible
    STATUS          current
    DESCRIPTION
        "A table that contains interface information of all units."
    ::= { pmIfStatistics 12 }

pmTcaIfInPkts1dEntry     OBJECT-TYPE
    SYNTAX          PMTcaIfInPkts1dEntry
    MAX-ACCESS      not-accessible
    STATUS          current
    DESCRIPTION
        "A list of interface information of all units."
    INDEX     { pmTcaIfInPkts1dIndex  }
    ::= { pmTcaIfInPkts1dTable 1 }

PMTcaIfInPkts1dEntry    ::=
    SEQUENCE
    {
       pmTcaIfInPkts1dIndex      Integer32,
       pmTcaIfInPkts1dId     OCTET STRING,
       pmTcaIfInPkts1dUnitType  INTEGER,
       pmTcaIfInPkts1dCnt     Counter64,
       pmTcaIfInPkts1dThreshold   Counter64,
       pmTcaIfInPkts1dOccurTime   DateAndTime
    }

pmTcaIfInPkts1dIndex         OBJECT-TYPE
    SYNTAX          Integer32
    MAX-ACCESS      not-accessible
    STATUS          current
    DESCRIPTION
        "An index of units."
    ::= { pmTcaIfInPkts1dEntry 1 }

pmTcaIfInPkts1dId         OBJECT-TYPE
    SYNTAX          OCTET STRING
    MAX-ACCESS      read-only
    STATUS          current
    DESCRIPTION
        "Interface name."
    ::= { pmTcaIfInPkts1dEntry 2 }

pmTcaIfInPkts1dUnitType         OBJECT-TYPE
    SYNTAX          INTEGER
    {
       mcu(0)
    }
    MAX-ACCESS      read-only
    STATUS          current
    DESCRIPTION
        "Unit type."
    ::= { pmTcaIfInPkts1dEntry 3 }

pmTcaIfInPkts1dCnt         OBJECT-TYPE
    SYNTAX          Counter64
    MAX-ACCESS      read-only
    STATUS          current
    DESCRIPTION
        "1day counter of input packets."
    ::= { pmTcaIfInPkts1dEntry 4 }

pmTcaIfInPkts1dThreshold         OBJECT-TYPE
    SYNTAX          Counter64
    MAX-ACCESS      read-only
    STATUS          current
    DESCRIPTION
        "1day threshold of input packets."
    ::= { pmTcaIfInPkts1dEntry 5 }

pmTcaIfInPkts1dOccurTime         OBJECT-TYPE
    SYNTAX          DateAndTime
    MAX-ACCESS      read-only
    STATUS          current
    DESCRIPTION
        "Time of the occurrence of the tca."
    ::= { pmTcaIfInPkts1dEntry 6 }


pmTcaIfInBytes15mTable     OBJECT-TYPE
    SYNTAX          SEQUENCE OF PMTcaIfInBytes15mEntry
    MAX-ACCESS      not-accessible
    STATUS          current
    DESCRIPTION
        "A table that contains interface information of all units."
    ::= { pmIfStatistics 13 }

pmTcaIfInBytes15mEntry     OBJECT-TYPE
    SYNTAX          PMTcaIfInBytes15mEntry
    MAX-ACCESS      not-accessible
    STATUS          current
    DESCRIPTION
        "A list of interface information of all units."
    INDEX     { pmTcaIfInBytes15mIndex  }
    ::= { pmTcaIfInBytes15mTable 1 }

PMTcaIfInBytes15mEntry    ::=
    SEQUENCE
    {
       pmTcaIfInBytes15mIndex      Integer32,
       pmTcaIfInBytes15mId     OCTET STRING,
       pmTcaIfInBytes15mUnitType   INTEGER,
       pmTcaIfInBytes15mCnt     Counter64,
       pmTcaIfInBytes15mThreshold   Counter64,
       pmTcaIfInBytes15mOccurTime   DateAndTime
    }

pmTcaIfInBytes15mIndex         OBJECT-TYPE
    SYNTAX          Integer32
    MAX-ACCESS      not-accessible
    STATUS          current
    DESCRIPTION
        "An index of units."
    ::= { pmTcaIfInBytes15mEntry 1 }

pmTcaIfInBytes15mId         OBJECT-TYPE
    SYNTAX          OCTET STRING
    MAX-ACCESS      read-only
    STATUS          current
    DESCRIPTION
        "Interface name."
    ::= { pmTcaIfInBytes15mEntry 2 }

pmTcaIfInBytes15mUnitType         OBJECT-TYPE
    SYNTAX          INTEGER
    {
       mcu(0)
    }
    MAX-ACCESS      read-only
    STATUS          current
    DESCRIPTION
        "Unit type."
    ::= { pmTcaIfInBytes15mEntry 3 }

pmTcaIfInBytes15mCnt         OBJECT-TYPE
    SYNTAX          Counter64
    MAX-ACCESS      read-only
    STATUS          current
    DESCRIPTION
        "15min counter of input bytes."
    ::= { pmTcaIfInBytes15mEntry 4 }

pmTcaIfInBytes15mThreshold         OBJECT-TYPE
    SYNTAX          Counter64
    MAX-ACCESS      read-only
    STATUS          current
    DESCRIPTION
        "15min threshold of input bytes."
    ::= { pmTcaIfInBytes15mEntry 5 }

pmTcaIfInBytes15mOccurTime         OBJECT-TYPE
    SYNTAX          DateAndTime
    MAX-ACCESS      read-only
    STATUS          current
    DESCRIPTION
        "Time of the occurrence of the tca."
    ::= { pmTcaIfInBytes15mEntry 6 }

pmTcaIfInBytes1hTable     OBJECT-TYPE
    SYNTAX          SEQUENCE OF PMTcaIfInBytes1hEntry
    MAX-ACCESS      not-accessible
    STATUS          current
    DESCRIPTION
        "A table that contains interface information of all units."
    ::= { pmIfStatistics 14 }

pmTcaIfInBytes1hEntry     OBJECT-TYPE
    SYNTAX          PMTcaIfInBytes1hEntry
    MAX-ACCESS      not-accessible
    STATUS          current
    DESCRIPTION
        "A list of interface information of all units."
    INDEX     { pmTcaIfInBytes1hIndex  }
    ::= { pmTcaIfInBytes1hTable 1 }

PMTcaIfInBytes1hEntry    ::=
    SEQUENCE
    {
       pmTcaIfInBytes1hIndex      Integer32,
       pmTcaIfInBytes1hId     OCTET STRING,
       pmTcaIfInBytes1hUnitType   INTEGER,
       pmTcaIfInBytes1hCnt     Counter64,
       pmTcaIfInBytes1hThreshold   Counter64,
       pmTcaIfInBytes1hOccurTime   DateAndTime
    }

pmTcaIfInBytes1hIndex         OBJECT-TYPE
    SYNTAX          Integer32
    MAX-ACCESS      not-accessible
    STATUS          current
    DESCRIPTION
        "An index of units."
    ::= { pmTcaIfInBytes1hEntry 1 }

pmTcaIfInBytes1hId         OBJECT-TYPE
    SYNTAX          OCTET STRING
    MAX-ACCESS      read-only
    STATUS          current
    DESCRIPTION
        "Interface name."
    ::= { pmTcaIfInBytes1hEntry 2 }

pmTcaIfInBytes1hUnitType         OBJECT-TYPE
    SYNTAX          INTEGER
    {
       mcu(0)
    }
    MAX-ACCESS      read-only
    STATUS          current
    DESCRIPTION
        "Unit type."
    ::= { pmTcaIfInBytes1hEntry 3 }

pmTcaIfInBytes1hCnt         OBJECT-TYPE
    SYNTAX          Counter64
    MAX-ACCESS      read-only
    STATUS          current
    DESCRIPTION
        "1hour counter of input bytes."
    ::= { pmTcaIfInBytes1hEntry 4 }

pmTcaIfInBytes1hThreshold         OBJECT-TYPE
    SYNTAX          Counter64
    MAX-ACCESS      read-only
    STATUS          current
    DESCRIPTION
        "1hour threshold of input bytes."
    ::= { pmTcaIfInBytes1hEntry 5 }

pmTcaIfInBytes1hOccurTime         OBJECT-TYPE
    SYNTAX          DateAndTime
    MAX-ACCESS      read-only
    STATUS          current
    DESCRIPTION
        "Time of the occurrence of the tca."
    ::= { pmTcaIfInBytes1hEntry 6 }

pmTcaIfInBytes1dTable     OBJECT-TYPE
    SYNTAX          SEQUENCE OF PMTcaIfInBytes1dEntry
    MAX-ACCESS      not-accessible
    STATUS          current
    DESCRIPTION
        "A table that contains interface information of all units."
    ::= { pmIfStatistics 15 }

pmTcaIfInBytes1dEntry     OBJECT-TYPE
    SYNTAX          PMTcaIfInBytes1dEntry
    MAX-ACCESS      not-accessible
    STATUS          current
    DESCRIPTION
        "A list of interface information of all units."
    INDEX     { pmTcaIfInBytes1dIndex  }
    ::= { pmTcaIfInBytes1dTable 1 }

PMTcaIfInBytes1dEntry    ::=
    SEQUENCE
    {
       pmTcaIfInBytes1dIndex      Integer32,
       pmTcaIfInBytes1dId     OCTET STRING,
       pmTcaIfInBytes1dUnitType  INTEGER,
       pmTcaIfInBytes1dCnt     Counter64,
       pmTcaIfInBytes1dThreshold   Counter64,
       pmTcaIfInBytes1dOccurTime   DateAndTime
    }

pmTcaIfInBytes1dIndex         OBJECT-TYPE
    SYNTAX          Integer32
    MAX-ACCESS      not-accessible
    STATUS          current
    DESCRIPTION
        "An index of units."
    ::= { pmTcaIfInBytes1dEntry 1 }

pmTcaIfInBytes1dId         OBJECT-TYPE
    SYNTAX          OCTET STRING
    MAX-ACCESS      read-only
    STATUS          current
    DESCRIPTION
        "Interface name."
    ::= { pmTcaIfInBytes1dEntry 2 }

pmTcaIfInBytes1dUnitType         OBJECT-TYPE
    SYNTAX          INTEGER
    {
       mcu(0)
    }
    MAX-ACCESS      read-only
    STATUS          current
    DESCRIPTION
        "Unit type."
    ::= { pmTcaIfInBytes1dEntry 3 }

pmTcaIfInBytes1dCnt         OBJECT-TYPE
    SYNTAX          Counter64
    MAX-ACCESS      read-only
    STATUS          current
    DESCRIPTION
        "1day counter of input bytes."
    ::= { pmTcaIfInBytes1dEntry 4 }

pmTcaIfInBytes1dThreshold         OBJECT-TYPE
    SYNTAX          Counter64
    MAX-ACCESS      read-only
    STATUS          current
    DESCRIPTION
        "1day threshold of input bytes."
    ::= { pmTcaIfInBytes1dEntry 5 }

pmTcaIfInBytes1dOccurTime         OBJECT-TYPE
    SYNTAX          DateAndTime
    MAX-ACCESS      read-only
    STATUS          current
    DESCRIPTION
        "Time of the occurrence of the tca."
    ::= { pmTcaIfInBytes1dEntry 6 }


pmTcaIfInBrdcasts15mTable     OBJECT-TYPE
    SYNTAX          SEQUENCE OF PMTcaIfInBrdcasts15mEntry
    MAX-ACCESS      not-accessible
    STATUS          current
    DESCRIPTION
        "A table that contains interface information of all units."
    ::= { pmIfStatistics 16 }

pmTcaIfInBrdcasts15mEntry     OBJECT-TYPE
    SYNTAX          PMTcaIfInBrdcasts15mEntry
    MAX-ACCESS      not-accessible
    STATUS          current
    DESCRIPTION
        "A list of interface information of all units."
    INDEX     { pmTcaIfInBrdcasts15mIndex  }
    ::= { pmTcaIfInBrdcasts15mTable 1 }

PMTcaIfInBrdcasts15mEntry    ::=
    SEQUENCE
    {
       pmTcaIfInBrdcasts15mIndex      Integer32,
       pmTcaIfInBrdcasts15mId     OCTET STRING,
       pmTcaIfInBrdcasts15mUnitType   INTEGER,
       pmTcaIfInBrdcasts15mCnt     Counter64,
       pmTcaIfInBrdcasts15mThreshold   Counter64,
       pmTcaIfInBrdcasts15mOccurTime   DateAndTime
    }

pmTcaIfInBrdcasts15mIndex         OBJECT-TYPE
    SYNTAX          Integer32
    MAX-ACCESS      not-accessible
    STATUS          current
    DESCRIPTION
        "An index of units."
    ::= { pmTcaIfInBrdcasts15mEntry 1 }

pmTcaIfInBrdcasts15mId         OBJECT-TYPE
    SYNTAX          OCTET STRING
    MAX-ACCESS      read-only
    STATUS          current
    DESCRIPTION
        "Interface name."
    ::= { pmTcaIfInBrdcasts15mEntry 2 }

pmTcaIfInBrdcasts15mUnitType         OBJECT-TYPE
    SYNTAX          INTEGER
    {
       mcu(0)
    }
    MAX-ACCESS      read-only
    STATUS          current
    DESCRIPTION
        "Unit type."
    ::= { pmTcaIfInBrdcasts15mEntry 3 }

pmTcaIfInBrdcasts15mCnt         OBJECT-TYPE
    SYNTAX          Counter64
    MAX-ACCESS      read-only
    STATUS          current
    DESCRIPTION
        "15min counter of input broadcast packets."
    ::= { pmTcaIfInBrdcasts15mEntry 4 }

pmTcaIfInBrdcasts15mThreshold         OBJECT-TYPE
    SYNTAX          Counter64
    MAX-ACCESS      read-only
    STATUS          current
    DESCRIPTION
        "15min threshold of input broadcast packets."
    ::= { pmTcaIfInBrdcasts15mEntry 5 }

pmTcaIfInBrdcasts15mOccurTime         OBJECT-TYPE
    SYNTAX          DateAndTime
    MAX-ACCESS      read-only
    STATUS          current
    DESCRIPTION
        "Time of the occurrence of the tca."
    ::= { pmTcaIfInBrdcasts15mEntry 6 }

pmTcaIfInBrdcasts1hTable     OBJECT-TYPE
    SYNTAX          SEQUENCE OF PMTcaIfInBrdcasts1hEntry
    MAX-ACCESS      not-accessible
    STATUS          current
    DESCRIPTION
        "A table that contains interface information of all units."
    ::= { pmIfStatistics 17 }

pmTcaIfInBrdcasts1hEntry     OBJECT-TYPE
    SYNTAX          PMTcaIfInBrdcasts1hEntry
    MAX-ACCESS      not-accessible
    STATUS          current
    DESCRIPTION
        "A list of interface information of all units."
    INDEX     { pmTcaIfInBrdcasts1hIndex  }
    ::= { pmTcaIfInBrdcasts1hTable 1 }

PMTcaIfInBrdcasts1hEntry    ::=
    SEQUENCE
    {
       pmTcaIfInBrdcasts1hIndex      Integer32,
       pmTcaIfInBrdcasts1hId     OCTET STRING,
       pmTcaIfInBrdcasts1hUnitType   INTEGER,
       pmTcaIfInBrdcasts1hCnt     Counter64,
       pmTcaIfInBrdcasts1hThreshold   Counter64,
       pmTcaIfInBrdcasts1hOccurTime   DateAndTime
    }

pmTcaIfInBrdcasts1hIndex         OBJECT-TYPE
    SYNTAX          Integer32
    MAX-ACCESS      not-accessible
    STATUS          current
    DESCRIPTION
        "An index of units."
    ::= { pmTcaIfInBrdcasts1hEntry 1 }

pmTcaIfInBrdcasts1hId         OBJECT-TYPE
    SYNTAX          OCTET STRING
    MAX-ACCESS      read-only
    STATUS          current
    DESCRIPTION
        "Interface name."
    ::= { pmTcaIfInBrdcasts1hEntry 2 }

pmTcaIfInBrdcasts1hUnitType         OBJECT-TYPE
    SYNTAX          INTEGER
    {
       mcu(0)
    }
    MAX-ACCESS      read-only
    STATUS          current
    DESCRIPTION
        "Unit type."
    ::= { pmTcaIfInBrdcasts1hEntry 3 }

pmTcaIfInBrdcasts1hCnt         OBJECT-TYPE
    SYNTAX          Counter64
    MAX-ACCESS      read-only
    STATUS          current
    DESCRIPTION
        "1hour counter of input broadcast packets."
    ::= { pmTcaIfInBrdcasts1hEntry 4 }

pmTcaIfInBrdcasts1hThreshold         OBJECT-TYPE
    SYNTAX          Counter64
    MAX-ACCESS      read-only
    STATUS          current
    DESCRIPTION
        "1hour threshold of input broadcast packets."
    ::= { pmTcaIfInBrdcasts1hEntry 5 }

pmTcaIfInBrdcasts1hOccurTime         OBJECT-TYPE
    SYNTAX          DateAndTime
    MAX-ACCESS      read-only
    STATUS          current
    DESCRIPTION
        "Time of the occurrence of the tca."
    ::= { pmTcaIfInBrdcasts1hEntry 6 }

pmTcaIfInBrdcasts1dTable     OBJECT-TYPE
    SYNTAX          SEQUENCE OF PMTcaIfInBrdcasts1dEntry
    MAX-ACCESS      not-accessible
    STATUS          current
    DESCRIPTION
        "A table that contains interface information of all units."
    ::= { pmIfStatistics 18 }

pmTcaIfInBrdcasts1dEntry     OBJECT-TYPE
    SYNTAX          PMTcaIfInBrdcasts1dEntry
    MAX-ACCESS      not-accessible
    STATUS          current
    DESCRIPTION
        "A list of interface information of all units."
    INDEX     { pmTcaIfInBrdcasts1dIndex  }
    ::= { pmTcaIfInBrdcasts1dTable 1 }

PMTcaIfInBrdcasts1dEntry    ::=
    SEQUENCE
    {
       pmTcaIfInBrdcasts1dIndex      Integer32,
       pmTcaIfInBrdcasts1dId     OCTET STRING,
       pmTcaIfInBrdcasts1dUnitType  INTEGER,
       pmTcaIfInBrdcasts1dCnt     Counter64,
       pmTcaIfInBrdcasts1dThreshold   Counter64,
       pmTcaIfInBrdcasts1dOccurTime   DateAndTime
    }

pmTcaIfInBrdcasts1dIndex         OBJECT-TYPE
    SYNTAX          Integer32
    MAX-ACCESS      not-accessible
    STATUS          current
    DESCRIPTION
        "An index of units."
    ::= { pmTcaIfInBrdcasts1dEntry 1 }

pmTcaIfInBrdcasts1dId         OBJECT-TYPE
    SYNTAX          OCTET STRING
    MAX-ACCESS      read-only
    STATUS          current
    DESCRIPTION
        "Interface name."
    ::= { pmTcaIfInBrdcasts1dEntry 2 }

pmTcaIfInBrdcasts1dUnitType         OBJECT-TYPE
    SYNTAX          INTEGER
    {
       mcu(0)
    }
    MAX-ACCESS      read-only
    STATUS          current
    DESCRIPTION
        "Unit type."
    ::= { pmTcaIfInBrdcasts1dEntry 3 }

pmTcaIfInBrdcasts1dCnt         OBJECT-TYPE
    SYNTAX          Counter64
    MAX-ACCESS      read-only
    STATUS          current
    DESCRIPTION
        "1day counter of input broadcast packets."
    ::= { pmTcaIfInBrdcasts1dEntry 4 }

pmTcaIfInBrdcasts1dThreshold         OBJECT-TYPE
    SYNTAX          Counter64
    MAX-ACCESS      read-only
    STATUS          current
    DESCRIPTION
        "1day threshold of input broadcast packets."
    ::= { pmTcaIfInBrdcasts1dEntry 5 }

pmTcaIfInBrdcasts1dOccurTime         OBJECT-TYPE
    SYNTAX          DateAndTime
    MAX-ACCESS      read-only
    STATUS          current
    DESCRIPTION
        "Time of the occurrence of the tca."
    ::= { pmTcaIfInBrdcasts1dEntry 6 }


pmTcaIfInMltcasts15mTable     OBJECT-TYPE
    SYNTAX          SEQUENCE OF PMTcaIfInMltcasts15mEntry
    MAX-ACCESS      not-accessible
    STATUS          current
    DESCRIPTION
        "A table that contains interface information of all units."
    ::= { pmIfStatistics 19 }

pmTcaIfInMltcasts15mEntry     OBJECT-TYPE
    SYNTAX          PMTcaIfInMltcasts15mEntry
    MAX-ACCESS      not-accessible
    STATUS          current
    DESCRIPTION
        "A list of interface information of all units."
    INDEX     { pmTcaIfInMltcasts15mIndex  }
    ::= { pmTcaIfInMltcasts15mTable 1 }

PMTcaIfInMltcasts15mEntry    ::=
    SEQUENCE
    {
       pmTcaIfInMltcasts15mIndex      Integer32,
       pmTcaIfInMltcasts15mId     OCTET STRING,
       pmTcaIfInMltcasts15mUnitType   INTEGER,
       pmTcaIfInMltcasts15mCnt     Counter64,
       pmTcaIfInMltcasts15mThreshold   Counter64,
       pmTcaIfInMltcasts15mOccurTime   DateAndTime
    }

pmTcaIfInMltcasts15mIndex         OBJECT-TYPE
    SYNTAX          Integer32
    MAX-ACCESS      not-accessible
    STATUS          current
    DESCRIPTION
        "An index of units."
    ::= { pmTcaIfInMltcasts15mEntry 1 }

pmTcaIfInMltcasts15mId         OBJECT-TYPE
    SYNTAX          OCTET STRING
    MAX-ACCESS      read-only
    STATUS          current
    DESCRIPTION
        "Interface name."
    ::= { pmTcaIfInMltcasts15mEntry 2 }

pmTcaIfInMltcasts15mUnitType         OBJECT-TYPE
    SYNTAX          INTEGER
    {
       mcu(0)
    }
    MAX-ACCESS      read-only
    STATUS          current
    DESCRIPTION
        "Unit type."
    ::= { pmTcaIfInMltcasts15mEntry 3 }

pmTcaIfInMltcasts15mCnt         OBJECT-TYPE
    SYNTAX          Counter64
    MAX-ACCESS      read-only
    STATUS          current
    DESCRIPTION
        "15min counter of input multicast packets."
    ::= { pmTcaIfInMltcasts15mEntry 4 }

pmTcaIfInMltcasts15mThreshold         OBJECT-TYPE
    SYNTAX          Counter64
    MAX-ACCESS      read-only
    STATUS          current
    DESCRIPTION
        "15min threshold of input multicast packets."
    ::= { pmTcaIfInMltcasts15mEntry 5 }

pmTcaIfInMltcasts15mOccurTime         OBJECT-TYPE
    SYNTAX          DateAndTime
    MAX-ACCESS      read-only
    STATUS          current
    DESCRIPTION
        "Time of the occurrence of the tca."
    ::= { pmTcaIfInMltcasts15mEntry 6 }

pmTcaIfInMltcasts1hTable     OBJECT-TYPE
    SYNTAX          SEQUENCE OF PMTcaIfInMltcasts1hEntry
    MAX-ACCESS      not-accessible
    STATUS          current
    DESCRIPTION
        "A table that contains interface information of all units."
    ::= { pmIfStatistics 20 }

pmTcaIfInMltcasts1hEntry     OBJECT-TYPE
    SYNTAX          PMTcaIfInMltcasts1hEntry
    MAX-ACCESS      not-accessible
    STATUS          current
    DESCRIPTION
        "A list of interface information of all units."
    INDEX     { pmTcaIfInMltcasts1hIndex  }
    ::= { pmTcaIfInMltcasts1hTable 1 }

PMTcaIfInMltcasts1hEntry    ::=
    SEQUENCE
    {
       pmTcaIfInMltcasts1hIndex      Integer32,
       pmTcaIfInMltcasts1hId     OCTET STRING,
       pmTcaIfInMltcasts1hUnitType   INTEGER,
       pmTcaIfInMltcasts1hCnt     Counter64,
       pmTcaIfInMltcasts1hThreshold   Counter64,
       pmTcaIfInMltcasts1hOccurTime   DateAndTime
    }

pmTcaIfInMltcasts1hIndex         OBJECT-TYPE
    SYNTAX          Integer32
    MAX-ACCESS      not-accessible
    STATUS          current
    DESCRIPTION
        "An index of units."
    ::= { pmTcaIfInMltcasts1hEntry 1 }

pmTcaIfInMltcasts1hId         OBJECT-TYPE
    SYNTAX          OCTET STRING
    MAX-ACCESS      read-only
    STATUS          current
    DESCRIPTION
        "Interface name."
    ::= { pmTcaIfInMltcasts1hEntry 2 }

pmTcaIfInMltcasts1hUnitType         OBJECT-TYPE
    SYNTAX          INTEGER
    {
       mcu(0)
    }
    MAX-ACCESS      read-only
    STATUS          current
    DESCRIPTION
        "Unit type."
    ::= { pmTcaIfInMltcasts1hEntry 3 }

pmTcaIfInMltcasts1hCnt         OBJECT-TYPE
    SYNTAX          Counter64
    MAX-ACCESS      read-only
    STATUS          current
    DESCRIPTION
        "1hour counter of input multicast packets."
    ::= { pmTcaIfInMltcasts1hEntry 4 }

pmTcaIfInMltcasts1hThreshold         OBJECT-TYPE
    SYNTAX          Counter64
    MAX-ACCESS      read-only
    STATUS          current
    DESCRIPTION
        "1hour threshold of input multicast packets."
    ::= { pmTcaIfInMltcasts1hEntry 5 }

pmTcaIfInMltcasts1hOccurTime         OBJECT-TYPE
    SYNTAX          DateAndTime
    MAX-ACCESS      read-only
    STATUS          current
    DESCRIPTION
        "Time of the occurrence of the tca."
    ::= { pmTcaIfInMltcasts1hEntry 6 }

pmTcaIfInMltcasts1dTable     OBJECT-TYPE
    SYNTAX          SEQUENCE OF PMTcaIfInMltcasts1dEntry
    MAX-ACCESS      not-accessible
    STATUS          current
    DESCRIPTION
        "A table that contains interface information of all units."
    ::= { pmIfStatistics 21 }

pmTcaIfInMltcasts1dEntry     OBJECT-TYPE
    SYNTAX          PMTcaIfInMltcasts1dEntry
    MAX-ACCESS      not-accessible
    STATUS          current
    DESCRIPTION
        "A list of interface information of all units."
    INDEX     { pmTcaIfInMltcasts1dIndex  }
    ::= { pmTcaIfInMltcasts1dTable 1 }

PMTcaIfInMltcasts1dEntry    ::=
    SEQUENCE
    {
       pmTcaIfInMltcasts1dIndex      Integer32,
       pmTcaIfInMltcasts1dId     OCTET STRING,
       pmTcaIfInMltcasts1dUnitType  INTEGER,
       pmTcaIfInMltcasts1dCnt     Counter64,
       pmTcaIfInMltcasts1dThreshold   Counter64,
       pmTcaIfInMltcasts1dOccurTime   DateAndTime
    }

pmTcaIfInMltcasts1dIndex         OBJECT-TYPE
    SYNTAX          Integer32
    MAX-ACCESS      not-accessible
    STATUS          current
    DESCRIPTION
        "An index of units."
    ::= { pmTcaIfInMltcasts1dEntry 1 }

pmTcaIfInMltcasts1dId         OBJECT-TYPE
    SYNTAX          OCTET STRING
    MAX-ACCESS      read-only
    STATUS          current
    DESCRIPTION
        "Interface name."
    ::= { pmTcaIfInMltcasts1dEntry 2 }

pmTcaIfInMltcasts1dUnitType         OBJECT-TYPE
    SYNTAX          INTEGER
    {
       mcu(0)
    }
    MAX-ACCESS      read-only
    STATUS          current
    DESCRIPTION
        "Unit type."
    ::= { pmTcaIfInMltcasts1dEntry 3 }

pmTcaIfInMltcasts1dCnt         OBJECT-TYPE
    SYNTAX          Counter64
    MAX-ACCESS      read-only
    STATUS          current
    DESCRIPTION
        "1day counter of input multicast packets."
    ::= { pmTcaIfInMltcasts1dEntry 4 }

pmTcaIfInMltcasts1dThreshold         OBJECT-TYPE
    SYNTAX          Counter64
    MAX-ACCESS      read-only
    STATUS          current
    DESCRIPTION
        "1day threshold of input multicast packets."
    ::= { pmTcaIfInMltcasts1dEntry 5 }

pmTcaIfInMltcasts1dOccurTime         OBJECT-TYPE
    SYNTAX          DateAndTime
    MAX-ACCESS      read-only
    STATUS          current
    DESCRIPTION
        "Time of the occurrence of the tca."
    ::= { pmTcaIfInMltcasts1dEntry 6 }


pmTcaIfCrcErr15mTable     OBJECT-TYPE
    SYNTAX          SEQUENCE OF PMTcaIfCrcErr15mEntry
    MAX-ACCESS      not-accessible
    STATUS          current
    DESCRIPTION
        "A table that contains interface information of all units."
    ::= { pmIfStatistics 22 }

pmTcaIfCrcErr15mEntry     OBJECT-TYPE
    SYNTAX          PMTcaIfCrcErr15mEntry
    MAX-ACCESS      not-accessible
    STATUS          current
    DESCRIPTION
        "A list of interface information of all units."
    INDEX     { pmTcaIfCrcErr15mIndex  }
    ::= { pmTcaIfCrcErr15mTable 1 }

PMTcaIfCrcErr15mEntry    ::=
    SEQUENCE
    {
       pmTcaIfCrcErr15mIndex      Integer32,
       pmTcaIfCrcErr15mId     OCTET STRING,
       pmTcaIfCrcErr15mUnitType   INTEGER,
       pmTcaIfCrcErr15mCnt     Counter64,
       pmTcaIfCrcErr15mThreshold   Counter64,
       pmTcaIfCrcErr15mOccurTime   DateAndTime
    }

pmTcaIfCrcErr15mIndex         OBJECT-TYPE
    SYNTAX          Integer32
    MAX-ACCESS      not-accessible
    STATUS          current
    DESCRIPTION
        "An index of units."
    ::= { pmTcaIfCrcErr15mEntry 1 }

pmTcaIfCrcErr15mId         OBJECT-TYPE
    SYNTAX          OCTET STRING
    MAX-ACCESS      read-only
    STATUS          current
    DESCRIPTION
        "Interface name."
    ::= { pmTcaIfCrcErr15mEntry 2 }

pmTcaIfCrcErr15mUnitType         OBJECT-TYPE
    SYNTAX          INTEGER
    {
       mcu(0)
    }
    MAX-ACCESS      read-only
    STATUS          current
    DESCRIPTION
        "Unit type."
    ::= { pmTcaIfCrcErr15mEntry 3 }

pmTcaIfCrcErr15mCnt         OBJECT-TYPE
    SYNTAX          Counter64
    MAX-ACCESS      read-only
    STATUS          current
    DESCRIPTION
        "15min counter of packets with CRC error."
    ::= { pmTcaIfCrcErr15mEntry 4 }

pmTcaIfCrcErr15mThreshold         OBJECT-TYPE
    SYNTAX          Counter64
    MAX-ACCESS      read-only
    STATUS          current
    DESCRIPTION
        "15min threshold of packets with CRC error."
    ::= { pmTcaIfCrcErr15mEntry 5 }

pmTcaIfCrcErr15mOccurTime         OBJECT-TYPE
    SYNTAX          DateAndTime
    MAX-ACCESS      read-only
    STATUS          current
    DESCRIPTION
        "Time of the occurrence of the tca."
    ::= { pmTcaIfCrcErr15mEntry 6 }

pmTcaIfCrcErr1hTable     OBJECT-TYPE
    SYNTAX          SEQUENCE OF PMTcaIfCrcErr1hEntry
    MAX-ACCESS      not-accessible
    STATUS          current
    DESCRIPTION
        "A table that contains interface information of all units."
    ::= { pmIfStatistics 23 }

pmTcaIfCrcErr1hEntry     OBJECT-TYPE
    SYNTAX          PMTcaIfCrcErr1hEntry
    MAX-ACCESS      not-accessible
    STATUS          current
    DESCRIPTION
        "A list of interface information of all units."
    INDEX     { pmTcaIfCrcErr1hIndex  }
    ::= { pmTcaIfCrcErr1hTable 1 }

PMTcaIfCrcErr1hEntry    ::=
    SEQUENCE
    {
       pmTcaIfCrcErr1hIndex      Integer32,
       pmTcaIfCrcErr1hId     OCTET STRING,
       pmTcaIfCrcErr1hUnitType   INTEGER,
       pmTcaIfCrcErr1hCnt     Counter64,
       pmTcaIfCrcErr1hThreshold   Counter64,
       pmTcaIfCrcErr1hOccurTime   DateAndTime
    }

pmTcaIfCrcErr1hIndex         OBJECT-TYPE
    SYNTAX          Integer32
    MAX-ACCESS      not-accessible
    STATUS          current
    DESCRIPTION
        "An index of units."
    ::= { pmTcaIfCrcErr1hEntry 1 }

pmTcaIfCrcErr1hId         OBJECT-TYPE
    SYNTAX          OCTET STRING
    MAX-ACCESS      read-only
    STATUS          current
    DESCRIPTION
        "Interface name."
    ::= { pmTcaIfCrcErr1hEntry 2 }

pmTcaIfCrcErr1hUnitType         OBJECT-TYPE
    SYNTAX          INTEGER
    {
       mcu(0)
    }
    MAX-ACCESS      read-only
    STATUS          current
    DESCRIPTION
        "Unit type."
    ::= { pmTcaIfCrcErr1hEntry 3 }

pmTcaIfCrcErr1hCnt         OBJECT-TYPE
    SYNTAX          Counter64
    MAX-ACCESS      read-only
    STATUS          current
    DESCRIPTION
        "1hour counter of packets with CRC error."
    ::= { pmTcaIfCrcErr1hEntry 4 }

pmTcaIfCrcErr1hThreshold         OBJECT-TYPE
    SYNTAX          Counter64
    MAX-ACCESS      read-only
    STATUS          current
    DESCRIPTION
        "1hour threshold of packets with CRC error."
    ::= { pmTcaIfCrcErr1hEntry 5 }

pmTcaIfCrcErr1hOccurTime         OBJECT-TYPE
    SYNTAX          DateAndTime
    MAX-ACCESS      read-only
    STATUS          current
    DESCRIPTION
        "Time of the occurrence of the tca."
    ::= { pmTcaIfCrcErr1hEntry 6 }

pmTcaIfCrcErr1dTable     OBJECT-TYPE
    SYNTAX          SEQUENCE OF PMTcaIfCrcErr1dEntry
    MAX-ACCESS      not-accessible
    STATUS          current
    DESCRIPTION
        "A table that contains interface information of all units."
    ::= { pmIfStatistics 24 }

pmTcaIfCrcErr1dEntry     OBJECT-TYPE
    SYNTAX          PMTcaIfCrcErr1dEntry
    MAX-ACCESS      not-accessible
    STATUS          current
    DESCRIPTION
        "A list of interface information of all units."
    INDEX     { pmTcaIfCrcErr1dIndex  }
    ::= { pmTcaIfCrcErr1dTable 1 }

PMTcaIfCrcErr1dEntry    ::=
    SEQUENCE
    {
       pmTcaIfCrcErr1dIndex      Integer32,
       pmTcaIfCrcErr1dId     OCTET STRING,
       pmTcaIfCrcErr1dUnitType  INTEGER,
       pmTcaIfCrcErr1dCnt     Counter64,
       pmTcaIfCrcErr1dThreshold   Counter64,
       pmTcaIfCrcErr1dOccurTime   DateAndTime
    }

pmTcaIfCrcErr1dIndex         OBJECT-TYPE
    SYNTAX          Integer32
    MAX-ACCESS      not-accessible
    STATUS          current
    DESCRIPTION
        "An index of units."
    ::= { pmTcaIfCrcErr1dEntry 1 }

pmTcaIfCrcErr1dId         OBJECT-TYPE
    SYNTAX          OCTET STRING
    MAX-ACCESS      read-only
    STATUS          current
    DESCRIPTION
        "Interface name."
    ::= { pmTcaIfCrcErr1dEntry 2 }

pmTcaIfCrcErr1dUnitType         OBJECT-TYPE
    SYNTAX          INTEGER
    {
       mcu(0)
    }
    MAX-ACCESS      read-only
    STATUS          current
    DESCRIPTION
        "Unit type."
    ::= { pmTcaIfCrcErr1dEntry 3 }

pmTcaIfCrcErr1dCnt         OBJECT-TYPE
    SYNTAX          Counter64
    MAX-ACCESS      read-only
    STATUS          current
    DESCRIPTION
        "1day counter of packets with CRC error."
    ::= { pmTcaIfCrcErr1dEntry 4 }

pmTcaIfCrcErr1dThreshold         OBJECT-TYPE
    SYNTAX          Counter64
    MAX-ACCESS      read-only
    STATUS          current
    DESCRIPTION
        "1day threshold of packets with CRC error."
    ::= { pmTcaIfCrcErr1dEntry 5 }

pmTcaIfCrcErr1dOccurTime         OBJECT-TYPE
    SYNTAX          DateAndTime
    MAX-ACCESS      read-only
    STATUS          current
    DESCRIPTION
        "Time of the occurrence of the tca."
    ::= { pmTcaIfCrcErr1dEntry 6 }

pmTcaIfCollisions15mTable     OBJECT-TYPE
    SYNTAX          SEQUENCE OF PMTcaIfCollisions15mEntry
    MAX-ACCESS      not-accessible
    STATUS          current
    DESCRIPTION
        "A table that contains interface information of all units."
    ::= { pmIfStatistics 25 }

pmTcaIfCollisions15mEntry     OBJECT-TYPE
    SYNTAX          PMTcaIfCollisions15mEntry
    MAX-ACCESS      not-accessible
    STATUS          current
    DESCRIPTION
        "A list of temperature interface of all units."
    INDEX     { pmTcaIfCollisions15mIndex  }
    ::= { pmTcaIfCollisions15mTable 1 }

PMTcaIfCollisions15mEntry    ::=
    SEQUENCE
    {
       pmTcaIfCollisions15mIndex      Integer32,
       pmTcaIfCollisions15mId     OCTET STRING,
       pmTcaIfCollisions15mUnitType   INTEGER,
       pmTcaIfCollisions15mCnt     Counter64,
       pmTcaIfCollisions15mThreshold   Counter64,
       pmTcaIfCollisions15mOccurTime   DateAndTime
    }

pmTcaIfCollisions15mIndex         OBJECT-TYPE
    SYNTAX          Integer32
    MAX-ACCESS      not-accessible
    STATUS          current
    DESCRIPTION
        "An index of units."
    ::= { pmTcaIfCollisions15mEntry 1 }

pmTcaIfCollisions15mId         OBJECT-TYPE
    SYNTAX          OCTET STRING
    MAX-ACCESS      read-only
    STATUS          current
    DESCRIPTION
        "Interface name."
    ::= { pmTcaIfCollisions15mEntry 2 }

pmTcaIfCollisions15mUnitType         OBJECT-TYPE
    SYNTAX          INTEGER
    {
       mcu(0)
    }
    MAX-ACCESS      read-only
    STATUS          current
    DESCRIPTION
        "Unit type."
    ::= { pmTcaIfCollisions15mEntry 3 }

pmTcaIfCollisions15mCnt         OBJECT-TYPE
    SYNTAX          Counter64
    MAX-ACCESS      read-only
    STATUS          current
    DESCRIPTION
        "15min counter of collisions."
    ::= { pmTcaIfCollisions15mEntry 4 }

pmTcaIfCollisions15mThreshold         OBJECT-TYPE
    SYNTAX          Counter64
    MAX-ACCESS      read-only
    STATUS          current
    DESCRIPTION
        "15min threshold of collisions."
    ::= { pmTcaIfCollisions15mEntry 5 }

pmTcaIfCollisions15mOccurTime         OBJECT-TYPE
    SYNTAX          DateAndTime
    MAX-ACCESS      read-only
    STATUS          current
    DESCRIPTION
        "Time of the occurrence of the tca."
    ::= { pmTcaIfCollisions15mEntry 6 }

pmTcaIfCollisions1hTable     OBJECT-TYPE
    SYNTAX          SEQUENCE OF PMTcaIfCollisions1hEntry
    MAX-ACCESS      not-accessible
    STATUS          current
    DESCRIPTION
        "A table that contains interface information of all units."
    ::= { pmIfStatistics 26 }

pmTcaIfCollisions1hEntry     OBJECT-TYPE
    SYNTAX          PMTcaIfCollisions1hEntry
    MAX-ACCESS      not-accessible
    STATUS          current
    DESCRIPTION
        "A list of temperature interface of all units."
    INDEX     { pmTcaIfCollisions1hIndex  }
    ::= { pmTcaIfCollisions1hTable 1 }

PMTcaIfCollisions1hEntry    ::=
    SEQUENCE
    {
       pmTcaIfCollisions1hIndex      Integer32,
       pmTcaIfCollisions1hId     OCTET STRING,
       pmTcaIfCollisions1hUnitType   INTEGER,
       pmTcaIfCollisions1hCnt     Counter64,
       pmTcaIfCollisions1hThreshold   Counter64,
       pmTcaIfCollisions1hOccurTime   DateAndTime
    }

pmTcaIfCollisions1hIndex         OBJECT-TYPE
    SYNTAX          Integer32
    MAX-ACCESS      not-accessible
    STATUS          current
    DESCRIPTION
        "An index of units."
    ::= { pmTcaIfCollisions1hEntry 1 }

pmTcaIfCollisions1hId         OBJECT-TYPE
    SYNTAX          OCTET STRING
    MAX-ACCESS      read-only
    STATUS          current
    DESCRIPTION
        "Interface name."
    ::= { pmTcaIfCollisions1hEntry 2 }

pmTcaIfCollisions1hUnitType         OBJECT-TYPE
    SYNTAX          INTEGER
    {
       mcu(0)
    }
    MAX-ACCESS      read-only
    STATUS          current
    DESCRIPTION
        "Unit type."
    ::= { pmTcaIfCollisions1hEntry 3 }

pmTcaIfCollisions1hCnt         OBJECT-TYPE
    SYNTAX          Counter64
    MAX-ACCESS      read-only
    STATUS          current
    DESCRIPTION
        "1hour counter of collisions."
    ::= { pmTcaIfCollisions1hEntry 4 }

pmTcaIfCollisions1hThreshold         OBJECT-TYPE
    SYNTAX          Counter64
    MAX-ACCESS      read-only
    STATUS          current
    DESCRIPTION
        "1hour threshold of collisions."
    ::= { pmTcaIfCollisions1hEntry 5 }

pmTcaIfCollisions1hOccurTime         OBJECT-TYPE
    SYNTAX          DateAndTime
    MAX-ACCESS      read-only
    STATUS          current
    DESCRIPTION
        "Time of the occurrence of the tca."
    ::= { pmTcaIfCollisions1hEntry 6 }

pmTcaIfCollisions1dTable     OBJECT-TYPE
    SYNTAX          SEQUENCE OF PMTcaIfCollisions1dEntry
    MAX-ACCESS      not-accessible
    STATUS          current
    DESCRIPTION
        "A table that contains interface information of all units."
    ::= { pmIfStatistics 27 }

pmTcaIfCollisions1dEntry     OBJECT-TYPE
    SYNTAX          PMTcaIfCollisions1dEntry
    MAX-ACCESS      not-accessible
    STATUS          current
    DESCRIPTION
        "A list of interface information of all units."
    INDEX     { pmTcaIfCollisions1dIndex  }
    ::= { pmTcaIfCollisions1dTable 1 }

PMTcaIfCollisions1dEntry    ::=
    SEQUENCE
    {
       pmTcaIfCollisions1dIndex      Integer32,
       pmTcaIfCollisions1dId     OCTET STRING,
       pmTcaIfCollisions1dUnitType  INTEGER,
       pmTcaIfCollisions1dCnt     Counter64,
       pmTcaIfCollisions1dThreshold   Counter64,
       pmTcaIfCollisions1dOccurTime   DateAndTime
    }

pmTcaIfCollisions1dIndex         OBJECT-TYPE
    SYNTAX          Integer32
    MAX-ACCESS      not-accessible
    STATUS          current
    DESCRIPTION
        "An index of units."
    ::= { pmTcaIfCollisions1dEntry 1 }

pmTcaIfCollisions1dId         OBJECT-TYPE
    SYNTAX          OCTET STRING
    MAX-ACCESS      read-only
    STATUS          current
    DESCRIPTION
        "Interface name."
    ::= { pmTcaIfCollisions1dEntry 2 }

pmTcaIfCollisions1dUnitType         OBJECT-TYPE
    SYNTAX          INTEGER
    {
       mcu(0)
    }
    MAX-ACCESS      read-only
    STATUS          current
    DESCRIPTION
        "Unit type."
    ::= { pmTcaIfCollisions1dEntry 3 }

pmTcaIfCollisions1dCnt         OBJECT-TYPE
    SYNTAX          Counter64
    MAX-ACCESS      read-only
    STATUS          current
    DESCRIPTION
        "1day counter of collisions."
    ::= { pmTcaIfCollisions1dEntry 4 }

pmTcaIfCollisions1dThreshold         OBJECT-TYPE
    SYNTAX          Counter64
    MAX-ACCESS      read-only
    STATUS          current
    DESCRIPTION
        "1day threshold of collisions."
    ::= { pmTcaIfCollisions1dEntry 5 }

pmTcaIfCollisions1dOccurTime         OBJECT-TYPE
    SYNTAX          DateAndTime
    MAX-ACCESS      read-only
    STATUS          current
    DESCRIPTION
        "Time of the occurrence of the tca."
    ::= { pmTcaIfCollisions1dEntry 6 }


pmTcaIfUndersized15mTable     OBJECT-TYPE
    SYNTAX          SEQUENCE OF PMTcaIfUndersized15mEntry
    MAX-ACCESS      not-accessible
    STATUS          current
    DESCRIPTION
        "A table that contains interface information of all units."
    ::= { pmIfStatistics 28 }

pmTcaIfUndersized15mEntry     OBJECT-TYPE
    SYNTAX          PMTcaIfUndersized15mEntry
    MAX-ACCESS      not-accessible
    STATUS          current
    DESCRIPTION
        "A list of temperature interface of all units."
    INDEX     { pmTcaIfUndersized15mIndex  }
    ::= { pmTcaIfUndersized15mTable 1 }

PMTcaIfUndersized15mEntry    ::=
    SEQUENCE
    {
       pmTcaIfUndersized15mIndex      Integer32,
       pmTcaIfUndersized15mId     OCTET STRING,
       pmTcaIfUndersized15mUnitType   INTEGER,
       pmTcaIfUndersized15mCnt     Counter64,
       pmTcaIfUndersized15mThreshold   Counter64,
       pmTcaIfUndersized15mOccurTime   DateAndTime
    }

pmTcaIfUndersized15mIndex         OBJECT-TYPE
    SYNTAX          Integer32
    MAX-ACCESS      not-accessible
    STATUS          current
    DESCRIPTION
        "An index of units."
    ::= { pmTcaIfUndersized15mEntry 1 }

pmTcaIfUndersized15mId         OBJECT-TYPE
    SYNTAX          OCTET STRING
    MAX-ACCESS      read-only
    STATUS          current
    DESCRIPTION
        "Interface name."
    ::= { pmTcaIfUndersized15mEntry 2 }

pmTcaIfUndersized15mUnitType         OBJECT-TYPE
    SYNTAX          INTEGER
    {
       mcu(0)
    }
    MAX-ACCESS      read-only
    STATUS          current
    DESCRIPTION
        "Unit type."
    ::= { pmTcaIfUndersized15mEntry 3 }

pmTcaIfUndersized15mCnt         OBJECT-TYPE
    SYNTAX          Counter64
    MAX-ACCESS      read-only
    STATUS          current
    DESCRIPTION
        "15min counter of undersized packets."
    ::= { pmTcaIfUndersized15mEntry 4 }

pmTcaIfUndersized15mThreshold         OBJECT-TYPE
    SYNTAX          Counter64
    MAX-ACCESS      read-only
    STATUS          current
    DESCRIPTION
        "15min threshold of undersized packets."
    ::= { pmTcaIfUndersized15mEntry 5 }

pmTcaIfUndersized15mOccurTime         OBJECT-TYPE
    SYNTAX          DateAndTime
    MAX-ACCESS      read-only
    STATUS          current
    DESCRIPTION
        "Time of the occurrence of the tca."
    ::= { pmTcaIfUndersized15mEntry 6 }

pmTcaIfUndersized1hTable     OBJECT-TYPE
    SYNTAX          SEQUENCE OF PMTcaIfUndersized1hEntry
    MAX-ACCESS      not-accessible
    STATUS          current
    DESCRIPTION
        "A table that contains interface information of all units."
    ::= { pmIfStatistics 29 }

pmTcaIfUndersized1hEntry     OBJECT-TYPE
    SYNTAX          PMTcaIfUndersized1hEntry
    MAX-ACCESS      not-accessible
    STATUS          current
    DESCRIPTION
        "A list of temperature interface of all units."
    INDEX     { pmTcaIfUndersized1hIndex  }
    ::= { pmTcaIfUndersized1hTable 1 }

PMTcaIfUndersized1hEntry    ::=
    SEQUENCE
    {
       pmTcaIfUndersized1hIndex      Integer32,
       pmTcaIfUndersized1hId     OCTET STRING,
       pmTcaIfUndersized1hUnitType   INTEGER,
       pmTcaIfUndersized1hCnt     Counter64,
       pmTcaIfUndersized1hThreshold   Counter64,
       pmTcaIfUndersized1hOccurTime   DateAndTime
    }

pmTcaIfUndersized1hIndex         OBJECT-TYPE
    SYNTAX          Integer32
    MAX-ACCESS      not-accessible
    STATUS          current
    DESCRIPTION
        "An index of units."
    ::= { pmTcaIfUndersized1hEntry 1 }

pmTcaIfUndersized1hId         OBJECT-TYPE
    SYNTAX          OCTET STRING
    MAX-ACCESS      read-only
    STATUS          current
    DESCRIPTION
        "Interface name."
    ::= { pmTcaIfUndersized1hEntry 2 }

pmTcaIfUndersized1hUnitType         OBJECT-TYPE
    SYNTAX          INTEGER
    {
       mcu(0)
    }
    MAX-ACCESS      read-only
    STATUS          current
    DESCRIPTION
        "Unit type."
    ::= { pmTcaIfUndersized1hEntry 3 }

pmTcaIfUndersized1hCnt         OBJECT-TYPE
    SYNTAX          Counter64
    MAX-ACCESS      read-only
    STATUS          current
    DESCRIPTION
        "1hour counter of undersized packets."
    ::= { pmTcaIfUndersized1hEntry 4 }

pmTcaIfUndersized1hThreshold         OBJECT-TYPE
    SYNTAX          Counter64
    MAX-ACCESS      read-only
    STATUS          current
    DESCRIPTION
        "1hour threshold of undersized packets."
    ::= { pmTcaIfUndersized1hEntry 5 }

pmTcaIfUndersized1hOccurTime         OBJECT-TYPE
    SYNTAX          DateAndTime
    MAX-ACCESS      read-only
    STATUS          current
    DESCRIPTION
        "Time of the occurrence of the tca."
    ::= { pmTcaIfUndersized1hEntry 6 }

pmTcaIfUndersized1dTable     OBJECT-TYPE
    SYNTAX          SEQUENCE OF PMTcaIfUndersized1dEntry
    MAX-ACCESS      not-accessible
    STATUS          current
    DESCRIPTION
        "A table that contains interface information of all units."
    ::= { pmIfStatistics 30 }

pmTcaIfUndersized1dEntry     OBJECT-TYPE
    SYNTAX          PMTcaIfUndersized1dEntry
    MAX-ACCESS      not-accessible
    STATUS          current
    DESCRIPTION
        "A list of temperature interface of all units."
    INDEX     { pmTcaIfUndersized1dIndex  }
    ::= { pmTcaIfUndersized1dTable 1 }

PMTcaIfUndersized1dEntry    ::=
    SEQUENCE
    {
       pmTcaIfUndersized1dIndex      Integer32,
       pmTcaIfUndersized1dId     OCTET STRING,
       pmTcaIfUndersized1dUnitType  INTEGER,
       pmTcaIfUndersized1dCnt     Counter64,
       pmTcaIfUndersized1dThreshold   Counter64,
       pmTcaIfUndersized1dOccurTime   DateAndTime
    }

pmTcaIfUndersized1dIndex         OBJECT-TYPE
    SYNTAX          Integer32
    MAX-ACCESS      not-accessible
    STATUS          current
    DESCRIPTION
        "An index of units."
    ::= { pmTcaIfUndersized1dEntry 1 }

pmTcaIfUndersized1dId         OBJECT-TYPE
    SYNTAX          OCTET STRING
    MAX-ACCESS      read-only
    STATUS          current
    DESCRIPTION
        "Interface name."
    ::= { pmTcaIfUndersized1dEntry 2 }

pmTcaIfUndersized1dUnitType         OBJECT-TYPE
    SYNTAX          INTEGER
    {
       mcu(0)
    }
    MAX-ACCESS      read-only
    STATUS          current
    DESCRIPTION
        "Unit type."
    ::= { pmTcaIfUndersized1dEntry 3 }

pmTcaIfUndersized1dCnt         OBJECT-TYPE
    SYNTAX          Counter64
    MAX-ACCESS      read-only
    STATUS          current
    DESCRIPTION
        "1day counter of undersized packets."
    ::= { pmTcaIfUndersized1dEntry 4 }

pmTcaIfUndersized1dThreshold         OBJECT-TYPE
    SYNTAX          Counter64
    MAX-ACCESS      read-only
    STATUS          current
    DESCRIPTION
        "1day threshold of undersized packets."
    ::= { pmTcaIfUndersized1dEntry 5 }

pmTcaIfUndersized1dOccurTime         OBJECT-TYPE
    SYNTAX          DateAndTime
    MAX-ACCESS      read-only
    STATUS          current
    DESCRIPTION
        "Time of the occurrence of the tca."
    ::= { pmTcaIfUndersized1dEntry 6 }


pmTcaIfOversized15mTable     OBJECT-TYPE
    SYNTAX          SEQUENCE OF PMTcaIfOversized15mEntry
    MAX-ACCESS      not-accessible
    STATUS          current
    DESCRIPTION
        "A table that contains interface information of all units."
    ::= { pmIfStatistics 31 }

pmTcaIfOversized15mEntry     OBJECT-TYPE
    SYNTAX          PMTcaIfOversized15mEntry
    MAX-ACCESS      not-accessible
    STATUS          current
    DESCRIPTION
        "A list of temperature interface of all units."
    INDEX     { pmTcaIfOversized15mIndex  }
    ::= { pmTcaIfOversized15mTable 1 }

PMTcaIfOversized15mEntry    ::=
    SEQUENCE
    {
       pmTcaIfOversized15mIndex      Integer32,
       pmTcaIfOversized15mId     OCTET STRING,
       pmTcaIfOversized15mUnitType   INTEGER,
       pmTcaIfOversized15mCnt     Counter64,
       pmTcaIfOversized15mThreshold   Counter64,
       pmTcaIfOversized15mOccurTime   DateAndTime
    }

pmTcaIfOversized15mIndex         OBJECT-TYPE
    SYNTAX          Integer32
    MAX-ACCESS      not-accessible
    STATUS          current
    DESCRIPTION
        "An index of units."
    ::= { pmTcaIfOversized15mEntry 1 }

pmTcaIfOversized15mId         OBJECT-TYPE
    SYNTAX          OCTET STRING
    MAX-ACCESS      read-only
    STATUS          current
    DESCRIPTION
        "Interface name."
    ::= { pmTcaIfOversized15mEntry 2 }

pmTcaIfOversized15mUnitType         OBJECT-TYPE
    SYNTAX          INTEGER
    {
       mcu(0)
    }
    MAX-ACCESS      read-only
    STATUS          current
    DESCRIPTION
        "Unit type."
    ::= { pmTcaIfOversized15mEntry 3 }

pmTcaIfOversized15mCnt         OBJECT-TYPE
    SYNTAX          Counter64
    MAX-ACCESS      read-only
    STATUS          current
    DESCRIPTION
        "15min counter of oversized packets."
    ::= { pmTcaIfOversized15mEntry 4 }

pmTcaIfOversized15mThreshold         OBJECT-TYPE
    SYNTAX          Counter64
    MAX-ACCESS      read-only
    STATUS          current
    DESCRIPTION
        "15min threshold of oversized packets."
    ::= { pmTcaIfOversized15mEntry 5 }

pmTcaIfOversized15mOccurTime         OBJECT-TYPE
    SYNTAX          DateAndTime
    MAX-ACCESS      read-only
    STATUS          current
    DESCRIPTION
        "Time of the occurrence of the tca."
    ::= { pmTcaIfOversized15mEntry 6 }

pmTcaIfOversized1hTable     OBJECT-TYPE
    SYNTAX          SEQUENCE OF PMTcaIfOversized1hEntry
    MAX-ACCESS      not-accessible
    STATUS          current
    DESCRIPTION
        "A table that contains interface information of all units."
    ::= { pmIfStatistics 32 }

pmTcaIfOversized1hEntry     OBJECT-TYPE
    SYNTAX          PMTcaIfOversized1hEntry
    MAX-ACCESS      not-accessible
    STATUS          current
    DESCRIPTION
        "A list of temperature interface of all units."
    INDEX     { pmTcaIfOversized1hIndex  }
    ::= { pmTcaIfOversized1hTable 1 }

PMTcaIfOversized1hEntry    ::=
    SEQUENCE
    {
       pmTcaIfOversized1hIndex      Integer32,
       pmTcaIfOversized1hId     OCTET STRING,
       pmTcaIfOversized1hUnitType   INTEGER,
       pmTcaIfOversized1hCnt     Counter64,
       pmTcaIfOversized1hThreshold   Counter64,
       pmTcaIfOversized1hOccurTime   DateAndTime
    }

pmTcaIfOversized1hIndex         OBJECT-TYPE
    SYNTAX          Integer32
    MAX-ACCESS      not-accessible
    STATUS          current
    DESCRIPTION
        "An index of units."
    ::= { pmTcaIfOversized1hEntry 1 }

pmTcaIfOversized1hId         OBJECT-TYPE
    SYNTAX          OCTET STRING
    MAX-ACCESS      read-only
    STATUS          current
    DESCRIPTION
        "Interface name."
    ::= { pmTcaIfOversized1hEntry 2 }

pmTcaIfOversized1hUnitType         OBJECT-TYPE
    SYNTAX          INTEGER
    {
       mcu(0)
    }
    MAX-ACCESS      read-only
    STATUS          current
    DESCRIPTION
        "Unit type."
    ::= { pmTcaIfOversized1hEntry 3 }

pmTcaIfOversized1hCnt         OBJECT-TYPE
    SYNTAX          Counter64
    MAX-ACCESS      read-only
    STATUS          current
    DESCRIPTION
        "1hour counter of oversized packets."
    ::= { pmTcaIfOversized1hEntry 4 }

pmTcaIfOversized1hThreshold         OBJECT-TYPE
    SYNTAX          Counter64
    MAX-ACCESS      read-only
    STATUS          current
    DESCRIPTION
        "1hour threshold of oversized packets."
    ::= { pmTcaIfOversized1hEntry 5 }

pmTcaIfOversized1hOccurTime         OBJECT-TYPE
    SYNTAX          DateAndTime
    MAX-ACCESS      read-only
    STATUS          current
    DESCRIPTION
        "Time of the occurrence of the tca."
    ::= { pmTcaIfOversized1hEntry 6 }

pmTcaIfOversized1dTable     OBJECT-TYPE
    SYNTAX          SEQUENCE OF PMTcaIfOversized1dEntry
    MAX-ACCESS      not-accessible
    STATUS          current
    DESCRIPTION
        "A table that contains interface information of all units."
    ::= { pmIfStatistics 33 }

pmTcaIfOversized1dEntry     OBJECT-TYPE
    SYNTAX          PMTcaIfOversized1dEntry
    MAX-ACCESS      not-accessible
    STATUS          current
    DESCRIPTION
        "A list of interface information of all units."
    INDEX     { pmTcaIfOversized1dIndex  }
    ::= { pmTcaIfOversized1dTable 1 }

PMTcaIfOversized1dEntry    ::=
    SEQUENCE
    {
       pmTcaIfOversized1dIndex      Integer32,
       pmTcaIfOversized1dId     OCTET STRING,
       pmTcaIfOversized1dUnitType  INTEGER,
       pmTcaIfOversized1dCnt     Counter64,
       pmTcaIfOversized1dThreshold   Counter64,
       pmTcaIfOversized1dOccurTime   DateAndTime
    }

pmTcaIfOversized1dIndex         OBJECT-TYPE
    SYNTAX          Integer32
    MAX-ACCESS      not-accessible
    STATUS          current
    DESCRIPTION
        "An index of units."
    ::= { pmTcaIfOversized1dEntry 1 }

pmTcaIfOversized1dId         OBJECT-TYPE
    SYNTAX          OCTET STRING
    MAX-ACCESS      read-only
    STATUS          current
    DESCRIPTION
        "Interface name."
    ::= { pmTcaIfOversized1dEntry 2 }

pmTcaIfOversized1dUnitType         OBJECT-TYPE
    SYNTAX          INTEGER
    {
       mcu(0)
    }
    MAX-ACCESS      read-only
    STATUS          current
    DESCRIPTION
        "Unit type."
    ::= { pmTcaIfOversized1dEntry 3 }

pmTcaIfOversized1dCnt         OBJECT-TYPE
    SYNTAX          Counter64
    MAX-ACCESS      read-only
    STATUS          current
    DESCRIPTION
        "1day counter of oversized packets."
    ::= { pmTcaIfOversized1dEntry 4 }

pmTcaIfOversized1dThreshold         OBJECT-TYPE
    SYNTAX          Counter64
    MAX-ACCESS      read-only
    STATUS          current
    DESCRIPTION
        "1day threshold of oversized packets."
    ::= { pmTcaIfOversized1dEntry 5 }

pmTcaIfOversized1dOccurTime         OBJECT-TYPE
    SYNTAX          DateAndTime
    MAX-ACCESS      read-only
    STATUS          current
    DESCRIPTION
        "Time of the occurrence of the tca."
    ::= { pmTcaIfOversized1dEntry 6 }


pmTcaIfFragments15mTable     OBJECT-TYPE
    SYNTAX          SEQUENCE OF PMTcaIfFragments15mEntry
    MAX-ACCESS      not-accessible
    STATUS          current
    DESCRIPTION
        "A table that contains interface information of all units."
    ::= { pmIfStatistics 34 }

pmTcaIfFragments15mEntry     OBJECT-TYPE
    SYNTAX          PMTcaIfFragments15mEntry
    MAX-ACCESS      not-accessible
    STATUS          current
    DESCRIPTION
        "A list of interface information of all units."
    INDEX     { pmTcaIfFragments15mIndex  }
    ::= { pmTcaIfFragments15mTable 1 }

PMTcaIfFragments15mEntry    ::=
    SEQUENCE
    {
       pmTcaIfFragments15mIndex      Integer32,
       pmTcaIfFragments15mId     OCTET STRING,
       pmTcaIfFragments15mUnitType   INTEGER,
       pmTcaIfFragments15mCnt     Counter64,
       pmTcaIfFragments15mThreshold   Counter64,
       pmTcaIfFragments15mOccurTime   DateAndTime
    }

pmTcaIfFragments15mIndex         OBJECT-TYPE
    SYNTAX          Integer32
    MAX-ACCESS      not-accessible
    STATUS          current
    DESCRIPTION
        "An index of units."
    ::= { pmTcaIfFragments15mEntry 1 }

pmTcaIfFragments15mId         OBJECT-TYPE
    SYNTAX          OCTET STRING
    MAX-ACCESS      read-only
    STATUS          current
    DESCRIPTION
        "Interface name."
    ::= { pmTcaIfFragments15mEntry 2 }

pmTcaIfFragments15mUnitType         OBJECT-TYPE
    SYNTAX          INTEGER
    {
       mcu(0)
    }
    MAX-ACCESS      read-only
    STATUS          current
    DESCRIPTION
        "Unit type."
    ::= { pmTcaIfFragments15mEntry 3 }

pmTcaIfFragments15mCnt         OBJECT-TYPE
    SYNTAX          Counter64
    MAX-ACCESS      read-only
    STATUS          current
    DESCRIPTION
        "15min counter of fragment packets."
    ::= { pmTcaIfFragments15mEntry 4 }

pmTcaIfFragments15mThreshold         OBJECT-TYPE
    SYNTAX          Counter64
    MAX-ACCESS      read-only
    STATUS          current
    DESCRIPTION
        "15min threshold of fragment packets."
    ::= { pmTcaIfFragments15mEntry 5 }

pmTcaIfFragments15mOccurTime         OBJECT-TYPE
    SYNTAX          DateAndTime
    MAX-ACCESS      read-only
    STATUS          current
    DESCRIPTION
        "Time of the occurrence of the tca."
    ::= { pmTcaIfFragments15mEntry 6 }

pmTcaIfFragments1hTable     OBJECT-TYPE
    SYNTAX          SEQUENCE OF PMTcaIfFragments1hEntry
    MAX-ACCESS      not-accessible
    STATUS          current
    DESCRIPTION
        "A table that contains interface information of all units."
    ::= { pmIfStatistics 35 }

pmTcaIfFragments1hEntry     OBJECT-TYPE
    SYNTAX          PMTcaIfFragments1hEntry
    MAX-ACCESS      not-accessible
    STATUS          current
    DESCRIPTION
        "A list of interface information of all units."
    INDEX     { pmTcaIfFragments1hIndex  }
    ::= { pmTcaIfFragments1hTable 1 }

PMTcaIfFragments1hEntry    ::=
    SEQUENCE
    {
       pmTcaIfFragments1hIndex      Integer32,
       pmTcaIfFragments1hId     OCTET STRING,
       pmTcaIfFragments1hUnitType   INTEGER,
       pmTcaIfFragments1hCnt     Counter64,
       pmTcaIfFragments1hThreshold   Counter64,
       pmTcaIfFragments1hOccurTime   DateAndTime
    }

pmTcaIfFragments1hIndex         OBJECT-TYPE
    SYNTAX          Integer32
    MAX-ACCESS      not-accessible
    STATUS          current
    DESCRIPTION
        "An index of units."
    ::= { pmTcaIfFragments1hEntry 1 }

pmTcaIfFragments1hId         OBJECT-TYPE
    SYNTAX          OCTET STRING
    MAX-ACCESS      read-only
    STATUS          current
    DESCRIPTION
        "Interface name."
    ::= { pmTcaIfFragments1hEntry 2 }

pmTcaIfFragments1hUnitType         OBJECT-TYPE
    SYNTAX          INTEGER
    {
       mcu(0)
    }
    MAX-ACCESS      read-only
    STATUS          current
    DESCRIPTION
        "Unit type."
    ::= { pmTcaIfFragments1hEntry 3 }

pmTcaIfFragments1hCnt         OBJECT-TYPE
    SYNTAX          Counter64
    MAX-ACCESS      read-only
    STATUS          current
    DESCRIPTION
        "1hour counter of fragment packets."
    ::= { pmTcaIfFragments1hEntry 4 }

pmTcaIfFragments1hThreshold         OBJECT-TYPE
    SYNTAX          Counter64
    MAX-ACCESS      read-only
    STATUS          current
    DESCRIPTION
        "1hour threshold of fragment packets."
    ::= { pmTcaIfFragments1hEntry 5 }

pmTcaIfFragments1hOccurTime         OBJECT-TYPE
    SYNTAX          DateAndTime
    MAX-ACCESS      read-only
    STATUS          current
    DESCRIPTION
        "Time of the occurrence of the tca."
    ::= { pmTcaIfFragments1hEntry 6 }

pmTcaIfFragments1dTable     OBJECT-TYPE
    SYNTAX          SEQUENCE OF PMTcaIfFragments1dEntry
    MAX-ACCESS      not-accessible
    STATUS          current
    DESCRIPTION
        "A table that contains interface information of all units."
    ::= { pmIfStatistics 36 }

pmTcaIfFragments1dEntry     OBJECT-TYPE
    SYNTAX          PMTcaIfFragments1dEntry
    MAX-ACCESS      not-accessible
    STATUS          current
    DESCRIPTION
        "A list of interface information of all units."
    INDEX     { pmTcaIfFragments1dIndex  }
    ::= { pmTcaIfFragments1dTable 1 }

PMTcaIfFragments1dEntry    ::=
    SEQUENCE
    {
       pmTcaIfFragments1dIndex      Integer32,
       pmTcaIfFragments1dId     OCTET STRING,
       pmTcaIfFragments1dUnitType  INTEGER,
       pmTcaIfFragments1dCnt     Counter64,
       pmTcaIfFragments1dThreshold   Counter64,
       pmTcaIfFragments1dOccurTime   DateAndTime
    }

pmTcaIfFragments1dIndex         OBJECT-TYPE
    SYNTAX          Integer32
    MAX-ACCESS      not-accessible
    STATUS          current
    DESCRIPTION
        "An index of units."
    ::= { pmTcaIfFragments1dEntry 1 }

pmTcaIfFragments1dId         OBJECT-TYPE
    SYNTAX          OCTET STRING
    MAX-ACCESS      read-only
    STATUS          current
    DESCRIPTION
        "Interface name."
    ::= { pmTcaIfFragments1dEntry 2 }

pmTcaIfFragments1dUnitType         OBJECT-TYPE
    SYNTAX          INTEGER
    {
       mcu(0)
    }
    MAX-ACCESS      read-only
    STATUS          current
    DESCRIPTION
        "Unit type."
    ::= { pmTcaIfFragments1dEntry 3 }

pmTcaIfFragments1dCnt         OBJECT-TYPE
    SYNTAX          Counter64
    MAX-ACCESS      read-only
    STATUS          current
    DESCRIPTION
        "1day counter of fragment packets."
    ::= { pmTcaIfFragments1dEntry 4 }

pmTcaIfFragments1dThreshold         OBJECT-TYPE
    SYNTAX          Counter64
    MAX-ACCESS      read-only
    STATUS          current
    DESCRIPTION
        "1day threshold of fragment packets."
    ::= { pmTcaIfFragments1dEntry 5 }

pmTcaIfFragments1dOccurTime         OBJECT-TYPE
    SYNTAX          DateAndTime
    MAX-ACCESS      read-only
    STATUS          current
    DESCRIPTION
        "Time of the occurrence of the tca."
    ::= { pmTcaIfFragments1dEntry 6 }


pmTcaIfJabbers15mTable     OBJECT-TYPE
    SYNTAX          SEQUENCE OF PMTcaIfJabbers15mEntry
    MAX-ACCESS      not-accessible
    STATUS          current
    DESCRIPTION
        "A table that contains interface information of all units."
    ::= { pmIfStatistics 37 }

pmTcaIfJabbers15mEntry     OBJECT-TYPE
    SYNTAX          PMTcaIfJabbers15mEntry
    MAX-ACCESS      not-accessible
    STATUS          current
    DESCRIPTION
        "A list of interface information of all units."
    INDEX     { pmTcaIfJabbers15mIndex  }
    ::= { pmTcaIfJabbers15mTable 1 }

PMTcaIfJabbers15mEntry    ::=
    SEQUENCE
    {
       pmTcaIfJabbers15mIndex      Integer32,
       pmTcaIfJabbers15mId     OCTET STRING,
       pmTcaIfJabbers15mUnitType   INTEGER,
       pmTcaIfJabbers15mCnt     Counter64,
       pmTcaIfJabbers15mThreshold   Counter64,
       pmTcaIfJabbers15mOccurTime   DateAndTime
    }

pmTcaIfJabbers15mIndex         OBJECT-TYPE
    SYNTAX          Integer32
    MAX-ACCESS      not-accessible
    STATUS          current
    DESCRIPTION
        "An index of units."
    ::= { pmTcaIfJabbers15mEntry 1 }

pmTcaIfJabbers15mId         OBJECT-TYPE
    SYNTAX          OCTET STRING
    MAX-ACCESS      read-only
    STATUS          current
    DESCRIPTION
        "Interface name."
    ::= { pmTcaIfJabbers15mEntry 2 }

pmTcaIfJabbers15mUnitType         OBJECT-TYPE
    SYNTAX          INTEGER
    {
       mcu(0)
    }
    MAX-ACCESS      read-only
    STATUS          current
    DESCRIPTION
        "Unit type."
    ::= { pmTcaIfJabbers15mEntry 3 }

pmTcaIfJabbers15mCnt         OBJECT-TYPE
    SYNTAX          Counter64
    MAX-ACCESS      read-only
    STATUS          current
    DESCRIPTION
        "15min counter of jabber packets."
    ::= { pmTcaIfJabbers15mEntry 4 }

pmTcaIfJabbers15mThreshold         OBJECT-TYPE
    SYNTAX          Counter64
    MAX-ACCESS      read-only
    STATUS          current
    DESCRIPTION
        "15min threshold of jabber packets."
    ::= { pmTcaIfJabbers15mEntry 5 }

pmTcaIfJabbers15mOccurTime         OBJECT-TYPE
    SYNTAX          DateAndTime
    MAX-ACCESS      read-only
    STATUS          current
    DESCRIPTION
        "Time of the occurrence of the tca."
    ::= { pmTcaIfJabbers15mEntry 6 }

pmTcaIfJabbers1hTable     OBJECT-TYPE
    SYNTAX          SEQUENCE OF PMTcaIfJabbers1hEntry
    MAX-ACCESS      not-accessible
    STATUS          current
    DESCRIPTION
        "A table that contains interface information of all units."
    ::= { pmIfStatistics 38 }

pmTcaIfJabbers1hEntry     OBJECT-TYPE
    SYNTAX          PMTcaIfJabbers1hEntry
    MAX-ACCESS      not-accessible
    STATUS          current
    DESCRIPTION
        "A list of interface information of all units."
    INDEX     { pmTcaIfJabbers1hIndex  }
    ::= { pmTcaIfJabbers1hTable 1 }

PMTcaIfJabbers1hEntry    ::=
    SEQUENCE
    {
       pmTcaIfJabbers1hIndex      Integer32,
       pmTcaIfJabbers1hId     OCTET STRING,
       pmTcaIfJabbers1hUnitType   INTEGER,
       pmTcaIfJabbers1hCnt     Counter64,
       pmTcaIfJabbers1hThreshold   Counter64,
       pmTcaIfJabbers1hOccurTime   DateAndTime
    }

pmTcaIfJabbers1hIndex         OBJECT-TYPE
    SYNTAX          Integer32
    MAX-ACCESS      not-accessible
    STATUS          current
    DESCRIPTION
        "An index of units."
    ::= { pmTcaIfJabbers1hEntry 1 }

pmTcaIfJabbers1hId         OBJECT-TYPE
    SYNTAX          OCTET STRING
    MAX-ACCESS      read-only
    STATUS          current
    DESCRIPTION
        "Interface name."
    ::= { pmTcaIfJabbers1hEntry 2 }

pmTcaIfJabbers1hUnitType         OBJECT-TYPE
    SYNTAX          INTEGER
    {
       mcu(0)
    }
    MAX-ACCESS      read-only
    STATUS          current
    DESCRIPTION
        "Unit type."
    ::= { pmTcaIfJabbers1hEntry 3 }

pmTcaIfJabbers1hCnt         OBJECT-TYPE
    SYNTAX          Counter64
    MAX-ACCESS      read-only
    STATUS          current
    DESCRIPTION
        "1hour counter of jabber packets."
    ::= { pmTcaIfJabbers1hEntry 4 }

pmTcaIfJabbers1hThreshold         OBJECT-TYPE
    SYNTAX          Counter64
    MAX-ACCESS      read-only
    STATUS          current
    DESCRIPTION
        "1hour threshold of jabber packets."
    ::= { pmTcaIfJabbers1hEntry 5 }

pmTcaIfJabbers1hOccurTime         OBJECT-TYPE
    SYNTAX          DateAndTime
    MAX-ACCESS      read-only
    STATUS          current
    DESCRIPTION
        "Time of the occurrence of the tca."
    ::= { pmTcaIfJabbers1hEntry 6 }

pmTcaIfJabbers1dTable     OBJECT-TYPE
    SYNTAX          SEQUENCE OF PMTcaIfJabbers1dEntry
    MAX-ACCESS      not-accessible
    STATUS          current
    DESCRIPTION
        "A table that contains interface information of all units."
    ::= { pmIfStatistics 39 }

pmTcaIfJabbers1dEntry     OBJECT-TYPE
    SYNTAX          PMTcaIfJabbers1dEntry
    MAX-ACCESS      not-accessible
    STATUS          current
    DESCRIPTION
        "A list of interface information of all units."
    INDEX     { pmTcaIfJabbers1dIndex  }
    ::= { pmTcaIfJabbers1dTable 1 }

PMTcaIfJabbers1dEntry    ::=
    SEQUENCE
    {
       pmTcaIfJabbers1dIndex      Integer32,
       pmTcaIfJabbers1dId     OCTET STRING,
       pmTcaIfJabbers1dUnitType  INTEGER,
       pmTcaIfJabbers1dCnt     Counter64,
       pmTcaIfJabbers1dThreshold   Counter64,
       pmTcaIfJabbers1dOccurTime   DateAndTime
    }

pmTcaIfJabbers1dIndex         OBJECT-TYPE
    SYNTAX          Integer32
    MAX-ACCESS      not-accessible
    STATUS          current
    DESCRIPTION
        "An index of units."
    ::= { pmTcaIfJabbers1dEntry 1 }

pmTcaIfJabbers1dId         OBJECT-TYPE
    SYNTAX          OCTET STRING
    MAX-ACCESS      read-only
    STATUS          current
    DESCRIPTION
        "Interface name."
    ::= { pmTcaIfJabbers1dEntry 2 }

pmTcaIfJabbers1dUnitType         OBJECT-TYPE
    SYNTAX          INTEGER
    {
       mcu(0)
    }
    MAX-ACCESS      read-only
    STATUS          current
    DESCRIPTION
        "Unit type."
    ::= { pmTcaIfJabbers1dEntry 3 }

pmTcaIfJabbers1dCnt         OBJECT-TYPE
    SYNTAX          Counter64
    MAX-ACCESS      read-only
    STATUS          current
    DESCRIPTION
        "1day counter of jabber packets."
    ::= { pmTcaIfJabbers1dEntry 4 }

pmTcaIfJabbers1dThreshold         OBJECT-TYPE
    SYNTAX          Counter64
    MAX-ACCESS      read-only
    STATUS          current
    DESCRIPTION
        "1day threshold of jabber packets."
    ::= { pmTcaIfJabbers1dEntry 5 }

pmTcaIfJabbers1dOccurTime         OBJECT-TYPE
    SYNTAX          DateAndTime
    MAX-ACCESS      read-only
    STATUS          current
    DESCRIPTION
        "Time of the occurrence of the tca."
    ::= { pmTcaIfJabbers1dEntry 6 }


pmTcaIfPkt6415mTable     OBJECT-TYPE
    SYNTAX          SEQUENCE OF PMTcaIfPkt6415mEntry
    MAX-ACCESS      not-accessible
    STATUS          current
    DESCRIPTION
        "A table that contains interface information of all units."
    ::= { pmIfStatistics 40 }

pmTcaIfPkt6415mEntry     OBJECT-TYPE
    SYNTAX          PMTcaIfPkt6415mEntry
    MAX-ACCESS      not-accessible
    STATUS          current
    DESCRIPTION
        "A list of interface information of all units."
    INDEX     { pmTcaIfPkt6415mIndex  }
    ::= { pmTcaIfPkt6415mTable 1 }

PMTcaIfPkt6415mEntry    ::=
    SEQUENCE
    {
       pmTcaIfPkt6415mIndex      Integer32,
       pmTcaIfPkt6415mId     OCTET STRING,
       pmTcaIfPkt6415mUnitType   INTEGER,
       pmTcaIfPkt6415mCnt     Counter64,
       pmTcaIfPkt6415mThreshold   Counter64,
       pmTcaIfPkt6415mOccurTime   DateAndTime
    }

pmTcaIfPkt6415mIndex         OBJECT-TYPE
    SYNTAX          Integer32
    MAX-ACCESS      not-accessible
    STATUS          current
    DESCRIPTION
        "An index of units."
    ::= { pmTcaIfPkt6415mEntry 1 }

pmTcaIfPkt6415mId         OBJECT-TYPE
    SYNTAX          OCTET STRING
    MAX-ACCESS      read-only
    STATUS          current
    DESCRIPTION
        "Interface name."
    ::= { pmTcaIfPkt6415mEntry 2 }

pmTcaIfPkt6415mUnitType         OBJECT-TYPE
    SYNTAX          INTEGER
    {
       mcu(0)
    }
    MAX-ACCESS      read-only
    STATUS          current
    DESCRIPTION
        "Unit type."
    ::= { pmTcaIfPkt6415mEntry 3 }

pmTcaIfPkt6415mCnt         OBJECT-TYPE
    SYNTAX          Counter64
    MAX-ACCESS      read-only
    STATUS          current
    DESCRIPTION
        "15min counter of packets with size under 64."
    ::= { pmTcaIfPkt6415mEntry 4 }

pmTcaIfPkt6415mThreshold         OBJECT-TYPE
    SYNTAX          Counter64
    MAX-ACCESS      read-only
    STATUS          current
    DESCRIPTION
        "15min threshold of packets with size under 64."
    ::= { pmTcaIfPkt6415mEntry 5 }

pmTcaIfPkt6415mOccurTime         OBJECT-TYPE
    SYNTAX          DateAndTime
    MAX-ACCESS      read-only
    STATUS          current
    DESCRIPTION
        "Time of the occurrence of the tca."
    ::= { pmTcaIfPkt6415mEntry 6 }

pmTcaIfPkt641hTable     OBJECT-TYPE
    SYNTAX          SEQUENCE OF PMTcaIfPkt641hEntry
    MAX-ACCESS      not-accessible
    STATUS          current
    DESCRIPTION
        "A table that contains interface information of all units."
    ::= { pmIfStatistics 41 }

pmTcaIfPkt641hEntry     OBJECT-TYPE
    SYNTAX          PMTcaIfPkt641hEntry
    MAX-ACCESS      not-accessible
    STATUS          current
    DESCRIPTION
        "A list of interface information of all units."
    INDEX     { pmTcaIfPkt641hIndex  }
    ::= { pmTcaIfPkt641hTable 1 }

PMTcaIfPkt641hEntry    ::=
    SEQUENCE
    {
       pmTcaIfPkt641hIndex      Integer32,
       pmTcaIfPkt641hId     OCTET STRING,
       pmTcaIfPkt641hUnitType   INTEGER,
       pmTcaIfPkt641hCnt     Counter64,
       pmTcaIfPkt641hThreshold   Counter64,
       pmTcaIfPkt641hOccurTime   DateAndTime
    }

pmTcaIfPkt641hIndex         OBJECT-TYPE
    SYNTAX          Integer32
    MAX-ACCESS      not-accessible
    STATUS          current
    DESCRIPTION
        "An index of units."
    ::= { pmTcaIfPkt641hEntry 1 }

pmTcaIfPkt641hId         OBJECT-TYPE
    SYNTAX          OCTET STRING
    MAX-ACCESS      read-only
    STATUS          current
    DESCRIPTION
        "Interface name."
    ::= { pmTcaIfPkt641hEntry 2 }

pmTcaIfPkt641hUnitType         OBJECT-TYPE
    SYNTAX          INTEGER
    {
       mcu(0)
    }
    MAX-ACCESS      read-only
    STATUS          current
    DESCRIPTION
        "Unit type."
    ::= { pmTcaIfPkt641hEntry 3 }

pmTcaIfPkt641hCnt         OBJECT-TYPE
    SYNTAX          Counter64
    MAX-ACCESS      read-only
    STATUS          current
    DESCRIPTION
        "1hour counter of packets with size under 64."
    ::= { pmTcaIfPkt641hEntry 4 }

pmTcaIfPkt641hThreshold         OBJECT-TYPE
    SYNTAX          Counter64
    MAX-ACCESS      read-only
    STATUS          current
    DESCRIPTION
        "1hour threshold of packets with size under 64."
    ::= { pmTcaIfPkt641hEntry 5 }

pmTcaIfPkt641hOccurTime         OBJECT-TYPE
    SYNTAX          DateAndTime
    MAX-ACCESS      read-only
    STATUS          current
    DESCRIPTION
        "Time of the occurrence of the tca."
    ::= { pmTcaIfPkt641hEntry 6 }

pmTcaIfPkt641dTable     OBJECT-TYPE
    SYNTAX          SEQUENCE OF PMTcaIfPkt641dEntry
    MAX-ACCESS      not-accessible
    STATUS          current
    DESCRIPTION
        "A table that contains interface information of all units."
    ::= { pmIfStatistics 42 }

pmTcaIfPkt641dEntry     OBJECT-TYPE
    SYNTAX          PMTcaIfPkt641dEntry
    MAX-ACCESS      not-accessible
    STATUS          current
    DESCRIPTION
        "A list of interface information of all units."
    INDEX     { pmTcaIfPkt641dIndex  }
    ::= { pmTcaIfPkt641dTable 1 }

PMTcaIfPkt641dEntry    ::=
    SEQUENCE
    {
       pmTcaIfPkt641dIndex      Integer32,
       pmTcaIfPkt641dId     OCTET STRING,
       pmTcaIfPkt641dUnitType  INTEGER,
       pmTcaIfPkt641dCnt     Counter64,
       pmTcaIfPkt641dThreshold   Counter64,
       pmTcaIfPkt641dOccurTime   DateAndTime
    }

pmTcaIfPkt641dIndex         OBJECT-TYPE
    SYNTAX          Integer32
    MAX-ACCESS      not-accessible
    STATUS          current
    DESCRIPTION
        "An index of units."
    ::= { pmTcaIfPkt641dEntry 1 }

pmTcaIfPkt641dId         OBJECT-TYPE
    SYNTAX          OCTET STRING
    MAX-ACCESS      read-only
    STATUS          current
    DESCRIPTION
        "Interface name."
    ::= { pmTcaIfPkt641dEntry 2 }

pmTcaIfPkt641dUnitType         OBJECT-TYPE
    SYNTAX          INTEGER
    {
       mcu(0)
    }
    MAX-ACCESS      read-only
    STATUS          current
    DESCRIPTION
        "Unit type."
    ::= { pmTcaIfPkt641dEntry 3 }

pmTcaIfPkt641dCnt         OBJECT-TYPE
    SYNTAX          Counter64
    MAX-ACCESS      read-only
    STATUS          current
    DESCRIPTION
        "1day counter of packets with size under 64."
    ::= { pmTcaIfPkt641dEntry 4 }

pmTcaIfPkt641dThreshold         OBJECT-TYPE
    SYNTAX          Counter64
    MAX-ACCESS      read-only
    STATUS          current
    DESCRIPTION
        "1day threshold of packets with size under 64."
    ::= { pmTcaIfPkt641dEntry 5 }

pmTcaIfPkt641dOccurTime         OBJECT-TYPE
    SYNTAX          DateAndTime
    MAX-ACCESS      read-only
    STATUS          current
    DESCRIPTION
        "Time of the occurrence of the tca."
    ::= { pmTcaIfPkt641dEntry 6 }


pmTcaIfPkt65to12715mTable     OBJECT-TYPE
    SYNTAX          SEQUENCE OF PMTcaIfPkt65to12715mEntry
    MAX-ACCESS      not-accessible
    STATUS          current
    DESCRIPTION
        "A table that contains interface information of all units."
    ::= { pmIfStatistics 43 }

pmTcaIfPkt65to12715mEntry     OBJECT-TYPE
    SYNTAX          PMTcaIfPkt65to12715mEntry
    MAX-ACCESS      not-accessible
    STATUS          current
    DESCRIPTION
        "A list of interface information of all units."
    INDEX     { pmTcaIfPkt65to12715mIndex  }
    ::= { pmTcaIfPkt65to12715mTable 1 }

PMTcaIfPkt65to12715mEntry    ::=
    SEQUENCE
    {
       pmTcaIfPkt65to12715mIndex      Integer32,
       pmTcaIfPkt65to12715mId     OCTET STRING,
       pmTcaIfPkt65to12715mUnitType   INTEGER,
       pmTcaIfPkt65to12715mCnt     Counter64,
       pmTcaIfPkt65to12715mThreshold   Counter64,
       pmTcaIfPkt65to12715mOccurTime   DateAndTime
    }

pmTcaIfPkt65to12715mIndex         OBJECT-TYPE
    SYNTAX          Integer32
    MAX-ACCESS      not-accessible
    STATUS          current
    DESCRIPTION
        "An index of units."
    ::= { pmTcaIfPkt65to12715mEntry 1 }

pmTcaIfPkt65to12715mId         OBJECT-TYPE
    SYNTAX          OCTET STRING
    MAX-ACCESS      read-only
    STATUS          current
    DESCRIPTION
        "Interface name."
    ::= { pmTcaIfPkt65to12715mEntry 2 }

pmTcaIfPkt65to12715mUnitType         OBJECT-TYPE
    SYNTAX          INTEGER
    {
       mcu(0)
    }
    MAX-ACCESS      read-only
    STATUS          current
    DESCRIPTION
        "Unit type."
    ::= { pmTcaIfPkt65to12715mEntry 3 }

pmTcaIfPkt65to12715mCnt         OBJECT-TYPE
    SYNTAX          Counter64
    MAX-ACCESS      read-only
    STATUS          current
    DESCRIPTION
        "15min counter of packets with size between 65 to 127."
    ::= { pmTcaIfPkt65to12715mEntry 4 }

pmTcaIfPkt65to12715mThreshold         OBJECT-TYPE
    SYNTAX          Counter64
    MAX-ACCESS      read-only
    STATUS          current
    DESCRIPTION
        "15min threshold of packets with size between 65 to 127."
    ::= { pmTcaIfPkt65to12715mEntry 5 }

pmTcaIfPkt65to12715mOccurTime         OBJECT-TYPE
    SYNTAX          DateAndTime
    MAX-ACCESS      read-only
    STATUS          current
    DESCRIPTION
        "Time of the occurrence of the tca."
    ::= { pmTcaIfPkt65to12715mEntry 6 }

pmTcaIfPkt65to1271hTable     OBJECT-TYPE
    SYNTAX          SEQUENCE OF PMTcaIfPkt65to1271hEntry
    MAX-ACCESS      not-accessible
    STATUS          current
    DESCRIPTION
        "A table that contains interface information of all units."
    ::= { pmIfStatistics 44 }

pmTcaIfPkt65to1271hEntry     OBJECT-TYPE
    SYNTAX          PMTcaIfPkt65to1271hEntry
    MAX-ACCESS      not-accessible
    STATUS          current
    DESCRIPTION
        "A list of interface information of all units."
    INDEX     { pmTcaIfPkt65to1271hIndex  }
    ::= { pmTcaIfPkt65to1271hTable 1 }

PMTcaIfPkt65to1271hEntry    ::=
    SEQUENCE
    {
       pmTcaIfPkt65to1271hIndex      Integer32,
       pmTcaIfPkt65to1271hId     OCTET STRING,
       pmTcaIfPkt65to1271hUnitType   INTEGER,
       pmTcaIfPkt65to1271hCnt     Counter64,
       pmTcaIfPkt65to1271hThreshold   Counter64,
       pmTcaIfPkt65to1271hOccurTime   DateAndTime
    }

pmTcaIfPkt65to1271hIndex         OBJECT-TYPE
    SYNTAX          Integer32
    MAX-ACCESS      not-accessible
    STATUS          current
    DESCRIPTION
        "An index of units."
    ::= { pmTcaIfPkt65to1271hEntry 1 }

pmTcaIfPkt65to1271hId         OBJECT-TYPE
    SYNTAX          OCTET STRING
    MAX-ACCESS      read-only
    STATUS          current
    DESCRIPTION
        "Interface name."
    ::= { pmTcaIfPkt65to1271hEntry 2 }

pmTcaIfPkt65to1271hUnitType         OBJECT-TYPE
    SYNTAX          INTEGER
    {
       mcu(0)
    }
    MAX-ACCESS      read-only
    STATUS          current
    DESCRIPTION
        "Unit type."
    ::= { pmTcaIfPkt65to1271hEntry 3 }

pmTcaIfPkt65to1271hCnt         OBJECT-TYPE
    SYNTAX          Counter64
    MAX-ACCESS      read-only
    STATUS          current
    DESCRIPTION
        "1hour counter of packets with size between 65 to 127."
    ::= { pmTcaIfPkt65to1271hEntry 4 }

pmTcaIfPkt65to1271hThreshold         OBJECT-TYPE
    SYNTAX          Counter64
    MAX-ACCESS      read-only
    STATUS          current
    DESCRIPTION
        "1hour threshold of packets with size between 65 to 127."
    ::= { pmTcaIfPkt65to1271hEntry 5 }

pmTcaIfPkt65to1271hOccurTime         OBJECT-TYPE
    SYNTAX          DateAndTime
    MAX-ACCESS      read-only
    STATUS          current
    DESCRIPTION
        "Time of the occurrence of the tca."
    ::= { pmTcaIfPkt65to1271hEntry 6 }

pmTcaIfPkt65to1271dTable     OBJECT-TYPE
    SYNTAX          SEQUENCE OF PMTcaIfPkt65to1271dEntry
    MAX-ACCESS      not-accessible
    STATUS          current
    DESCRIPTION
        "A table that contains interface information of all units."
    ::= { pmIfStatistics 45 }

pmTcaIfPkt65to1271dEntry     OBJECT-TYPE
    SYNTAX          PMTcaIfPkt65to1271dEntry
    MAX-ACCESS      not-accessible
    STATUS          current
    DESCRIPTION
        "A list of interface information of all units."
    INDEX     { pmTcaIfPkt65to1271dIndex  }
    ::= { pmTcaIfPkt65to1271dTable 1 }

PMTcaIfPkt65to1271dEntry    ::=
    SEQUENCE
    {
       pmTcaIfPkt65to1271dIndex      Integer32,
       pmTcaIfPkt65to1271dId     OCTET STRING,
       pmTcaIfPkt65to1271dUnitType  INTEGER,
       pmTcaIfPkt65to1271dCnt     Counter64,
       pmTcaIfPkt65to1271dThreshold   Counter64,
       pmTcaIfPkt65to1271dOccurTime   DateAndTime
    }

pmTcaIfPkt65to1271dIndex         OBJECT-TYPE
    SYNTAX          Integer32
    MAX-ACCESS      not-accessible
    STATUS          current
    DESCRIPTION
        "An index of units."
    ::= { pmTcaIfPkt65to1271dEntry 1 }

pmTcaIfPkt65to1271dId         OBJECT-TYPE
    SYNTAX          OCTET STRING
    MAX-ACCESS      read-only
    STATUS          current
    DESCRIPTION
        "Interface name."
    ::= { pmTcaIfPkt65to1271dEntry 2 }

pmTcaIfPkt65to1271dUnitType         OBJECT-TYPE
    SYNTAX          INTEGER
    {
       mcu(0)
    }
    MAX-ACCESS      read-only
    STATUS          current
    DESCRIPTION
        "Unit type."
    ::= { pmTcaIfPkt65to1271dEntry 3 }

pmTcaIfPkt65to1271dCnt         OBJECT-TYPE
    SYNTAX          Counter64
    MAX-ACCESS      read-only
    STATUS          current
    DESCRIPTION
        "1day counter of packets with size between 65 to 127."
    ::= { pmTcaIfPkt65to1271dEntry 4 }

pmTcaIfPkt65to1271dThreshold         OBJECT-TYPE
    SYNTAX          Counter64
    MAX-ACCESS      read-only
    STATUS          current
    DESCRIPTION
        "1day threshold of packets with size between 65 to 127."
    ::= { pmTcaIfPkt65to1271dEntry 5 }

pmTcaIfPkt65to1271dOccurTime         OBJECT-TYPE
    SYNTAX          DateAndTime
    MAX-ACCESS      read-only
    STATUS          current
    DESCRIPTION
        "Time of the occurrence of the tca."
    ::= { pmTcaIfPkt65to1271dEntry 6 }


pmTcaIfPkt128to25515mTable     OBJECT-TYPE
    SYNTAX          SEQUENCE OF PMTcaIfPkt128to25515mEntry
    MAX-ACCESS      not-accessible
    STATUS          current
    DESCRIPTION
        "A table that contains interface information of all units."
    ::= { pmIfStatistics 46 }

pmTcaIfPkt128to25515mEntry     OBJECT-TYPE
    SYNTAX          PMTcaIfPkt128to25515mEntry
    MAX-ACCESS      not-accessible
    STATUS          current
    DESCRIPTION
        "A list of interface information of all units."
    INDEX     { pmTcaIfPkt128to25515mIndex  }
    ::= { pmTcaIfPkt128to25515mTable 1 }

PMTcaIfPkt128to25515mEntry    ::=
    SEQUENCE
    {
       pmTcaIfPkt128to25515mIndex      Integer32,
       pmTcaIfPkt128to25515mId     OCTET STRING,
       pmTcaIfPkt128to25515mUnitType   INTEGER,
       pmTcaIfPkt128to25515mCnt     Counter64,
       pmTcaIfPkt128to25515mThreshold   Counter64,
       pmTcaIfPkt128to25515mOccurTime   DateAndTime
    }

pmTcaIfPkt128to25515mIndex         OBJECT-TYPE
    SYNTAX          Integer32
    MAX-ACCESS      not-accessible
    STATUS          current
    DESCRIPTION
        "An index of units."
    ::= { pmTcaIfPkt128to25515mEntry 1 }

pmTcaIfPkt128to25515mId         OBJECT-TYPE
    SYNTAX          OCTET STRING
    MAX-ACCESS      read-only
    STATUS          current
    DESCRIPTION
        "Interface name."
    ::= { pmTcaIfPkt128to25515mEntry 2 }

pmTcaIfPkt128to25515mUnitType         OBJECT-TYPE
    SYNTAX          INTEGER
    {
       mcu(0)
    }
    MAX-ACCESS      read-only
    STATUS          current
    DESCRIPTION
        "Unit type."
    ::= { pmTcaIfPkt128to25515mEntry 3 }

pmTcaIfPkt128to25515mCnt         OBJECT-TYPE
    SYNTAX          Counter64
    MAX-ACCESS      read-only
    STATUS          current
    DESCRIPTION
        "15min counter of packets with size between 128 to 255."
    ::= { pmTcaIfPkt128to25515mEntry 4 }

pmTcaIfPkt128to25515mThreshold         OBJECT-TYPE
    SYNTAX          Counter64
    MAX-ACCESS      read-only
    STATUS          current
    DESCRIPTION
        "15min threshold of packets with size between 128 to 255."
    ::= { pmTcaIfPkt128to25515mEntry 5 }

pmTcaIfPkt128to25515mOccurTime         OBJECT-TYPE
    SYNTAX          DateAndTime
    MAX-ACCESS      read-only
    STATUS          current
    DESCRIPTION
        "Time of the occurrence of the tca."
    ::= { pmTcaIfPkt128to25515mEntry 6 }

pmTcaIfPkt128to2551hTable     OBJECT-TYPE
    SYNTAX          SEQUENCE OF PMTcaIfPkt128to2551hEntry
    MAX-ACCESS      not-accessible
    STATUS          current
    DESCRIPTION
        "A table that contains interface information of all units."
    ::= { pmIfStatistics 47 }

pmTcaIfPkt128to2551hEntry     OBJECT-TYPE
    SYNTAX          PMTcaIfPkt128to2551hEntry
    MAX-ACCESS      not-accessible
    STATUS          current
    DESCRIPTION
        "A list of interface information of all units."
    INDEX     { pmTcaIfPkt128to2551hIndex  }
    ::= { pmTcaIfPkt128to2551hTable 1 }

PMTcaIfPkt128to2551hEntry    ::=
    SEQUENCE
    {
       pmTcaIfPkt128to2551hIndex      Integer32,
       pmTcaIfPkt128to2551hId     OCTET STRING,
       pmTcaIfPkt128to2551hUnitType   INTEGER,
       pmTcaIfPkt128to2551hCnt     Counter64,
       pmTcaIfPkt128to2551hThreshold   Counter64,
       pmTcaIfPkt128to2551hOccurTime   DateAndTime
    }

pmTcaIfPkt128to2551hIndex         OBJECT-TYPE
    SYNTAX          Integer32
    MAX-ACCESS      not-accessible
    STATUS          current
    DESCRIPTION
        "An index of units."
    ::= { pmTcaIfPkt128to2551hEntry 1 }

pmTcaIfPkt128to2551hId         OBJECT-TYPE
    SYNTAX          OCTET STRING
    MAX-ACCESS      read-only
    STATUS          current
    DESCRIPTION
        "Interface name."
    ::= { pmTcaIfPkt128to2551hEntry 2 }

pmTcaIfPkt128to2551hUnitType         OBJECT-TYPE
    SYNTAX          INTEGER
    {
       mcu(0)
    }
    MAX-ACCESS      read-only
    STATUS          current
    DESCRIPTION
        "Unit type."
    ::= { pmTcaIfPkt128to2551hEntry 3 }

pmTcaIfPkt128to2551hCnt         OBJECT-TYPE
    SYNTAX          Counter64
    MAX-ACCESS      read-only
    STATUS          current
    DESCRIPTION
        "1hour counter of packets with size between 128 to 255."
    ::= { pmTcaIfPkt128to2551hEntry 4 }

pmTcaIfPkt128to2551hThreshold         OBJECT-TYPE
    SYNTAX          Counter64
    MAX-ACCESS      read-only
    STATUS          current
    DESCRIPTION
        "1hour threshold of packets with size between 128 to 255."
    ::= { pmTcaIfPkt128to2551hEntry 5 }

pmTcaIfPkt128to2551hOccurTime         OBJECT-TYPE
    SYNTAX          DateAndTime
    MAX-ACCESS      read-only
    STATUS          current
    DESCRIPTION
        "Time of the occurrence of the tca."
    ::= { pmTcaIfPkt128to2551hEntry 6 }

pmTcaIfPkt128to2551dTable     OBJECT-TYPE
    SYNTAX          SEQUENCE OF PMTcaIfPkt128to2551dEntry
    MAX-ACCESS      not-accessible
    STATUS          current
    DESCRIPTION
        "A table that contains interface information of all units."
    ::= { pmIfStatistics 48 }

pmTcaIfPkt128to2551dEntry     OBJECT-TYPE
    SYNTAX          PMTcaIfPkt128to2551dEntry
    MAX-ACCESS      not-accessible
    STATUS          current
    DESCRIPTION
        "A list of interface information of all units."
    INDEX     { pmTcaIfPkt128to2551dIndex  }
    ::= { pmTcaIfPkt128to2551dTable 1 }

PMTcaIfPkt128to2551dEntry    ::=
    SEQUENCE
    {
       pmTcaIfPkt128to2551dIndex      Integer32,
       pmTcaIfPkt128to2551dId     OCTET STRING,
       pmTcaIfPkt128to2551dUnitType  INTEGER,
       pmTcaIfPkt128to2551dCnt     Counter64,
       pmTcaIfPkt128to2551dThreshold   Counter64,
       pmTcaIfPkt128to2551dOccurTime   DateAndTime
    }

pmTcaIfPkt128to2551dIndex         OBJECT-TYPE
    SYNTAX          Integer32
    MAX-ACCESS      not-accessible
    STATUS          current
    DESCRIPTION
        "An index of units."
    ::= { pmTcaIfPkt128to2551dEntry 1 }

pmTcaIfPkt128to2551dId         OBJECT-TYPE
    SYNTAX          OCTET STRING
    MAX-ACCESS      read-only
    STATUS          current
    DESCRIPTION
        "Interface name."
    ::= { pmTcaIfPkt128to2551dEntry 2 }

pmTcaIfPkt128to2551dUnitType         OBJECT-TYPE
    SYNTAX          INTEGER
    {
       mcu(0)
    }
    MAX-ACCESS      read-only
    STATUS          current
    DESCRIPTION
        "Unit type."
    ::= { pmTcaIfPkt128to2551dEntry 3 }

pmTcaIfPkt128to2551dCnt         OBJECT-TYPE
    SYNTAX          Counter64
    MAX-ACCESS      read-only
    STATUS          current
    DESCRIPTION
        "1day counter of packets with size between 128 to 255."
    ::= { pmTcaIfPkt128to2551dEntry 4 }

pmTcaIfPkt128to2551dThreshold         OBJECT-TYPE
    SYNTAX          Counter64
    MAX-ACCESS      read-only
    STATUS          current
    DESCRIPTION
        "1day threshold of packets with size between 128 to 255."
    ::= { pmTcaIfPkt128to2551dEntry 5 }

pmTcaIfPkt128to2551dOccurTime         OBJECT-TYPE
    SYNTAX          DateAndTime
    MAX-ACCESS      read-only
    STATUS          current
    DESCRIPTION
        "Time of the occurrence of the tca."
    ::= { pmTcaIfPkt128to2551dEntry 6 }


pmTcaIfPkt256to51115mTable     OBJECT-TYPE
    SYNTAX          SEQUENCE OF PMTcaIfPkt256to51115mEntry
    MAX-ACCESS      not-accessible
    STATUS          current
    DESCRIPTION
        "A table that contains interface information of all units."
    ::= { pmIfStatistics 49 }

pmTcaIfPkt256to51115mEntry     OBJECT-TYPE
    SYNTAX          PMTcaIfPkt256to51115mEntry
    MAX-ACCESS      not-accessible
    STATUS          current
    DESCRIPTION
        "A list of interface information of all units."
    INDEX     { pmTcaIfPkt256to51115mIndex  }
    ::= { pmTcaIfPkt256to51115mTable 1 }

PMTcaIfPkt256to51115mEntry    ::=
    SEQUENCE
    {
       pmTcaIfPkt256to51115mIndex      Integer32,
       pmTcaIfPkt256to51115mId     OCTET STRING,
       pmTcaIfPkt256to51115mUnitType   INTEGER,
       pmTcaIfPkt256to51115mCnt     Counter64,
       pmTcaIfPkt256to51115mThreshold   Counter64,
       pmTcaIfPkt256to51115mOccurTime   DateAndTime
    }

pmTcaIfPkt256to51115mIndex         OBJECT-TYPE
    SYNTAX          Integer32
    MAX-ACCESS      not-accessible
    STATUS          current
    DESCRIPTION
        "An index of units."
    ::= { pmTcaIfPkt256to51115mEntry 1 }

pmTcaIfPkt256to51115mId         OBJECT-TYPE
    SYNTAX          OCTET STRING
    MAX-ACCESS      read-only
    STATUS          current
    DESCRIPTION
        "Interface name."
    ::= { pmTcaIfPkt256to51115mEntry 2 }

pmTcaIfPkt256to51115mUnitType         OBJECT-TYPE
    SYNTAX          INTEGER
    {
       mcu(0)
    }
    MAX-ACCESS      read-only
    STATUS          current
    DESCRIPTION
        "Unit type."
    ::= { pmTcaIfPkt256to51115mEntry 3 }

pmTcaIfPkt256to51115mCnt         OBJECT-TYPE
    SYNTAX          Counter64
    MAX-ACCESS      read-only
    STATUS          current
    DESCRIPTION
        "15min counter of packets with size between 256 to 511."
    ::= { pmTcaIfPkt256to51115mEntry 4 }

pmTcaIfPkt256to51115mThreshold         OBJECT-TYPE
    SYNTAX          Counter64
    MAX-ACCESS      read-only
    STATUS          current
    DESCRIPTION
        "15min threshold of packets with size between 256 to 511."
    ::= { pmTcaIfPkt256to51115mEntry 5 }

pmTcaIfPkt256to51115mOccurTime         OBJECT-TYPE
    SYNTAX          DateAndTime
    MAX-ACCESS      read-only
    STATUS          current
    DESCRIPTION
        "Time of the occurrence of the tca."
    ::= { pmTcaIfPkt256to51115mEntry 6 }

pmTcaIfPkt256to5111hTable     OBJECT-TYPE
    SYNTAX          SEQUENCE OF PMTcaIfPkt256to5111hEntry
    MAX-ACCESS      not-accessible
    STATUS          current
    DESCRIPTION
        "A table that contains interface information of all units."
    ::= { pmIfStatistics 50 }

pmTcaIfPkt256to5111hEntry     OBJECT-TYPE
    SYNTAX          PMTcaIfPkt256to5111hEntry
    MAX-ACCESS      not-accessible
    STATUS          current
    DESCRIPTION
        "A list of interface information of all units."
    INDEX     { pmTcaIfPkt256to5111hIndex  }
    ::= { pmTcaIfPkt256to5111hTable 1 }

PMTcaIfPkt256to5111hEntry    ::=
    SEQUENCE
    {
       pmTcaIfPkt256to5111hIndex      Integer32,
       pmTcaIfPkt256to5111hId     OCTET STRING,
       pmTcaIfPkt256to5111hUnitType   INTEGER,
       pmTcaIfPkt256to5111hCnt     Counter64,
       pmTcaIfPkt256to5111hThreshold   Counter64,
       pmTcaIfPkt256to5111hOccurTime   DateAndTime
    }

pmTcaIfPkt256to5111hIndex         OBJECT-TYPE
    SYNTAX          Integer32
    MAX-ACCESS      not-accessible
    STATUS          current
    DESCRIPTION
        "An index of units."
    ::= { pmTcaIfPkt256to5111hEntry 1 }

pmTcaIfPkt256to5111hId         OBJECT-TYPE
    SYNTAX          OCTET STRING
    MAX-ACCESS      read-only
    STATUS          current
    DESCRIPTION
        "Interface name."
    ::= { pmTcaIfPkt256to5111hEntry 2 }

pmTcaIfPkt256to5111hUnitType         OBJECT-TYPE
    SYNTAX          INTEGER
    {
       mcu(0)
    }
    MAX-ACCESS      read-only
    STATUS          current
    DESCRIPTION
        "Unit type."
    ::= { pmTcaIfPkt256to5111hEntry 3 }

pmTcaIfPkt256to5111hCnt         OBJECT-TYPE
    SYNTAX          Counter64
    MAX-ACCESS      read-only
    STATUS          current
    DESCRIPTION
        "1hour counter of packets with size between 256 to 511."
    ::= { pmTcaIfPkt256to5111hEntry 4 }

pmTcaIfPkt256to5111hThreshold         OBJECT-TYPE
    SYNTAX          Counter64
    MAX-ACCESS      read-only
    STATUS          current
    DESCRIPTION
        "1hour threshold of packets with size between 256 to 511."
    ::= { pmTcaIfPkt256to5111hEntry 5 }

pmTcaIfPkt256to5111hOccurTime         OBJECT-TYPE
    SYNTAX          DateAndTime
    MAX-ACCESS      read-only
    STATUS          current
    DESCRIPTION
        "Time of the occurrence of the tca."
    ::= { pmTcaIfPkt256to5111hEntry 6 }

pmTcaIfPkt256to5111dTable     OBJECT-TYPE
    SYNTAX          SEQUENCE OF PMTcaIfPkt256to5111dEntry
    MAX-ACCESS      not-accessible
    STATUS          current
    DESCRIPTION
        "A table that contains interface information of all units."
    ::= { pmIfStatistics 51 }

pmTcaIfPkt256to5111dEntry     OBJECT-TYPE
    SYNTAX          PMTcaIfPkt256to5111dEntry
    MAX-ACCESS      not-accessible
    STATUS          current
    DESCRIPTION
        "A list of interface information of all units."
    INDEX     { pmTcaIfPkt256to5111dIndex  }
    ::= { pmTcaIfPkt256to5111dTable 1 }

PMTcaIfPkt256to5111dEntry    ::=
    SEQUENCE
    {
       pmTcaIfPkt256to5111dIndex      Integer32,
       pmTcaIfPkt256to5111dId     OCTET STRING,
       pmTcaIfPkt256to5111dUnitType  INTEGER,
       pmTcaIfPkt256to5111dCnt     Counter64,
       pmTcaIfPkt256to5111dThreshold   Counter64,
       pmTcaIfPkt256to5111dOccurTime   DateAndTime
    }

pmTcaIfPkt256to5111dIndex         OBJECT-TYPE
    SYNTAX          Integer32
    MAX-ACCESS      not-accessible
    STATUS          current
    DESCRIPTION
        "An index of units."
    ::= { pmTcaIfPkt256to5111dEntry 1 }

pmTcaIfPkt256to5111dId         OBJECT-TYPE
    SYNTAX          OCTET STRING
    MAX-ACCESS      read-only
    STATUS          current
    DESCRIPTION
        "Interface name."
    ::= { pmTcaIfPkt256to5111dEntry 2 }

pmTcaIfPkt256to5111dUnitType         OBJECT-TYPE
    SYNTAX          INTEGER
    {
       mcu(0)
    }
    MAX-ACCESS      read-only
    STATUS          current
    DESCRIPTION
        "Unit type."
    ::= { pmTcaIfPkt256to5111dEntry 3 }

pmTcaIfPkt256to5111dCnt         OBJECT-TYPE
    SYNTAX          Counter64
    MAX-ACCESS      read-only
    STATUS          current
    DESCRIPTION
        "1day counter of packets with size between 256 to 511."
    ::= { pmTcaIfPkt256to5111dEntry 4 }

pmTcaIfPkt256to5111dThreshold         OBJECT-TYPE
    SYNTAX          Counter64
    MAX-ACCESS      read-only
    STATUS          current
    DESCRIPTION
        "1day threshold of packets with size between 256 to 511."
    ::= { pmTcaIfPkt256to5111dEntry 5 }

pmTcaIfPkt256to5111dOccurTime         OBJECT-TYPE
    SYNTAX          DateAndTime
    MAX-ACCESS      read-only
    STATUS          current
    DESCRIPTION
        "Time of the occurrence of the tca."
    ::= { pmTcaIfPkt256to5111dEntry 6 }


pmTcaIfPkt512to102315mTable     OBJECT-TYPE
    SYNTAX          SEQUENCE OF PMTcaIfPkt512to102315mEntry
    MAX-ACCESS      not-accessible
    STATUS          current
    DESCRIPTION
        "A table that contains interface information of all units."
    ::= { pmIfStatistics 52 }

pmTcaIfPkt512to102315mEntry     OBJECT-TYPE
    SYNTAX          PMTcaIfPkt512to102315mEntry
    MAX-ACCESS      not-accessible
    STATUS          current
    DESCRIPTION
        "A list of interface information of all units."
    INDEX     { pmTcaIfPkt512to102315mIndex  }
    ::= { pmTcaIfPkt512to102315mTable 1 }

PMTcaIfPkt512to102315mEntry    ::=
    SEQUENCE
    {
       pmTcaIfPkt512to102315mIndex      Integer32,
       pmTcaIfPkt512to102315mId     OCTET STRING,
       pmTcaIfPkt512to102315mUnitType   INTEGER,
       pmTcaIfPkt512to102315mCnt     Counter64,
       pmTcaIfPkt512to102315mThreshold   Counter64,
       pmTcaIfPkt512to102315mOccurTime   DateAndTime
    }

pmTcaIfPkt512to102315mIndex         OBJECT-TYPE
    SYNTAX          Integer32
    MAX-ACCESS      not-accessible
    STATUS          current
    DESCRIPTION
        "An index of units."
    ::= { pmTcaIfPkt512to102315mEntry 1 }

pmTcaIfPkt512to102315mId         OBJECT-TYPE
    SYNTAX          OCTET STRING
    MAX-ACCESS      read-only
    STATUS          current
    DESCRIPTION
        "Interface name."
    ::= { pmTcaIfPkt512to102315mEntry 2 }

pmTcaIfPkt512to102315mUnitType         OBJECT-TYPE
    SYNTAX          INTEGER
    {
       mcu(0)
    }
    MAX-ACCESS      read-only
    STATUS          current
    DESCRIPTION
        "Unit type."
    ::= { pmTcaIfPkt512to102315mEntry 3 }

pmTcaIfPkt512to102315mCnt         OBJECT-TYPE
    SYNTAX          Counter64
    MAX-ACCESS      read-only
    STATUS          current
    DESCRIPTION
        "15min counter of packets with size between 512 to 1023."
    ::= { pmTcaIfPkt512to102315mEntry 4 }

pmTcaIfPkt512to102315mThreshold         OBJECT-TYPE
    SYNTAX          Counter64
    MAX-ACCESS      read-only
    STATUS          current
    DESCRIPTION
        "15min threshold of packets with size between 512 to 1023."
    ::= { pmTcaIfPkt512to102315mEntry 5 }

pmTcaIfPkt512to102315mOccurTime         OBJECT-TYPE
    SYNTAX          DateAndTime
    MAX-ACCESS      read-only
    STATUS          current
    DESCRIPTION
        "Time of the occurrence of the tca."
    ::= { pmTcaIfPkt512to102315mEntry 6 }

pmTcaIfPkt512to10231hTable     OBJECT-TYPE
    SYNTAX          SEQUENCE OF PMTcaIfPkt512to10231hEntry
    MAX-ACCESS      not-accessible
    STATUS          current
    DESCRIPTION
        "A table that contains interface information of all units."
    ::= { pmIfStatistics 53 }

pmTcaIfPkt512to10231hEntry     OBJECT-TYPE
    SYNTAX          PMTcaIfPkt512to10231hEntry
    MAX-ACCESS      not-accessible
    STATUS          current
    DESCRIPTION
        "A list of interface information of all units."
    INDEX     { pmTcaIfPkt512to10231hIndex  }
    ::= { pmTcaIfPkt512to10231hTable 1 }

PMTcaIfPkt512to10231hEntry    ::=
    SEQUENCE
    {
       pmTcaIfPkt512to10231hIndex      Integer32,
       pmTcaIfPkt512to10231hId     OCTET STRING,
       pmTcaIfPkt512to10231hUnitType   INTEGER,
       pmTcaIfPkt512to10231hCnt     Counter64,
       pmTcaIfPkt512to10231hThreshold   Counter64,
       pmTcaIfPkt512to10231hOccurTime   DateAndTime
    }

pmTcaIfPkt512to10231hIndex         OBJECT-TYPE
    SYNTAX          Integer32
    MAX-ACCESS      not-accessible
    STATUS          current
    DESCRIPTION
        "An index of units."
    ::= { pmTcaIfPkt512to10231hEntry 1 }

pmTcaIfPkt512to10231hId         OBJECT-TYPE
    SYNTAX          OCTET STRING
    MAX-ACCESS      read-only
    STATUS          current
    DESCRIPTION
        "Interface name."
    ::= { pmTcaIfPkt512to10231hEntry 2 }

pmTcaIfPkt512to10231hUnitType         OBJECT-TYPE
    SYNTAX          INTEGER
    {
       mcu(0)
    }
    MAX-ACCESS      read-only
    STATUS          current
    DESCRIPTION
        "Unit type."
    ::= { pmTcaIfPkt512to10231hEntry 3 }

pmTcaIfPkt512to10231hCnt         OBJECT-TYPE
    SYNTAX          Counter64
    MAX-ACCESS      read-only
    STATUS          current
    DESCRIPTION
        "1hour counter of packets with size between 512 to 1023."
    ::= { pmTcaIfPkt512to10231hEntry 4 }

pmTcaIfPkt512to10231hThreshold         OBJECT-TYPE
    SYNTAX          Counter64
    MAX-ACCESS      read-only
    STATUS          current
    DESCRIPTION
        "1hour threshold of packets with size between 512 to 1023."
    ::= { pmTcaIfPkt512to10231hEntry 5 }

pmTcaIfPkt512to10231hOccurTime         OBJECT-TYPE
    SYNTAX          DateAndTime
    MAX-ACCESS      read-only
    STATUS          current
    DESCRIPTION
        "Time of the occurrence of the tca."
    ::= { pmTcaIfPkt512to10231hEntry 6 }

pmTcaIfPkt512to10231dTable     OBJECT-TYPE
    SYNTAX          SEQUENCE OF PMTcaIfPkt512to10231dEntry
    MAX-ACCESS      not-accessible
    STATUS          current
    DESCRIPTION
        "A table that contains interface information of all units."
    ::= { pmIfStatistics 54 }

pmTcaIfPkt512to10231dEntry     OBJECT-TYPE
    SYNTAX          PMTcaIfPkt512to10231dEntry
    MAX-ACCESS      not-accessible
    STATUS          current
    DESCRIPTION
        "A list of interface information of all units."
    INDEX     { pmTcaIfPkt512to10231dIndex  }
    ::= { pmTcaIfPkt512to10231dTable 1 }

PMTcaIfPkt512to10231dEntry    ::=
    SEQUENCE
    {
       pmTcaIfPkt512to10231dIndex      Integer32,
       pmTcaIfPkt512to10231dId     OCTET STRING,
       pmTcaIfPkt512to10231dUnitType  INTEGER,
       pmTcaIfPkt512to10231dCnt     Counter64,
       pmTcaIfPkt512to10231dThreshold   Counter64,
       pmTcaIfPkt512to10231dOccurTime   DateAndTime
    }

pmTcaIfPkt512to10231dIndex         OBJECT-TYPE
    SYNTAX          Integer32
    MAX-ACCESS      not-accessible
    STATUS          current
    DESCRIPTION
        "An index of units."
    ::= { pmTcaIfPkt512to10231dEntry 1 }

pmTcaIfPkt512to10231dId         OBJECT-TYPE
    SYNTAX          OCTET STRING
    MAX-ACCESS      read-only
    STATUS          current
    DESCRIPTION
        "Interface name."
    ::= { pmTcaIfPkt512to10231dEntry 2 }

pmTcaIfPkt512to10231dUnitType         OBJECT-TYPE
    SYNTAX          INTEGER
    {
       mcu(0)
    }
    MAX-ACCESS      read-only
    STATUS          current
    DESCRIPTION
        "Unit type."
    ::= { pmTcaIfPkt512to10231dEntry 3 }

pmTcaIfPkt512to10231dCnt         OBJECT-TYPE
    SYNTAX          Counter64
    MAX-ACCESS      read-only
    STATUS          current
    DESCRIPTION
        "1day counter of packets with size between 512 to 1023."
    ::= { pmTcaIfPkt512to10231dEntry 4 }

pmTcaIfPkt512to10231dThreshold         OBJECT-TYPE
    SYNTAX          Counter64
    MAX-ACCESS      read-only
    STATUS          current
    DESCRIPTION
        "1day threshold of packets with size between 512 to 1023."
    ::= { pmTcaIfPkt512to10231dEntry 5 }

pmTcaIfPkt512to10231dOccurTime         OBJECT-TYPE
    SYNTAX          DateAndTime
    MAX-ACCESS      read-only
    STATUS          current
    DESCRIPTION
        "Time of the occurrence of the tca."
    ::= { pmTcaIfPkt512to10231dEntry 6 }


pmTcaIfPkt102415mTable     OBJECT-TYPE
    SYNTAX          SEQUENCE OF PMTcaIfPkt102415mEntry
    MAX-ACCESS      not-accessible
    STATUS          current
    DESCRIPTION
        "A table that contains interface information of all units."
    ::= { pmIfStatistics 55 }

pmTcaIfPkt102415mEntry     OBJECT-TYPE
    SYNTAX          PMTcaIfPkt102415mEntry
    MAX-ACCESS      not-accessible
    STATUS          current
    DESCRIPTION
        "A list of interface information of all units."
    INDEX     { pmTcaIfPkt102415mIndex  }
    ::= { pmTcaIfPkt102415mTable 1 }

PMTcaIfPkt102415mEntry    ::=
    SEQUENCE
    {
       pmTcaIfPkt102415mIndex      Integer32,
       pmTcaIfPkt102415mId     OCTET STRING,
       pmTcaIfPkt102415mUnitType   INTEGER,
       pmTcaIfPkt102415mCnt     Counter64,
       pmTcaIfPkt102415mThreshold   Counter64,
       pmTcaIfPkt102415mOccurTime   DateAndTime
    }

pmTcaIfPkt102415mIndex         OBJECT-TYPE
    SYNTAX          Integer32
    MAX-ACCESS      not-accessible
    STATUS          current
    DESCRIPTION
        "An index of units."
    ::= { pmTcaIfPkt102415mEntry 1 }

pmTcaIfPkt102415mId         OBJECT-TYPE
    SYNTAX          OCTET STRING
    MAX-ACCESS      read-only
    STATUS          current
    DESCRIPTION
        "Interface name."
    ::= { pmTcaIfPkt102415mEntry 2 }

pmTcaIfPkt102415mUnitType         OBJECT-TYPE
    SYNTAX          INTEGER
    {
       mcu(0)
    }
    MAX-ACCESS      read-only
    STATUS          current
    DESCRIPTION
        "Unit type."
    ::= { pmTcaIfPkt102415mEntry 3 }

pmTcaIfPkt102415mCnt         OBJECT-TYPE
    SYNTAX          Counter64
    MAX-ACCESS      read-only
    STATUS          current
    DESCRIPTION
        "15min counter of packets with size over 1024."
    ::= { pmTcaIfPkt102415mEntry 4 }

pmTcaIfPkt102415mThreshold         OBJECT-TYPE
    SYNTAX          Counter64
    MAX-ACCESS      read-only
    STATUS          current
    DESCRIPTION
        "15min threshold of packets with size over 1024."
    ::= { pmTcaIfPkt102415mEntry 5 }

pmTcaIfPkt102415mOccurTime         OBJECT-TYPE
    SYNTAX          DateAndTime
    MAX-ACCESS      read-only
    STATUS          current
    DESCRIPTION
        "Time of the occurrence of the tca."
    ::= { pmTcaIfPkt102415mEntry 6 }

pmTcaIfPkt10241hTable     OBJECT-TYPE
    SYNTAX          SEQUENCE OF PMTcaIfPkt10241hEntry
    MAX-ACCESS      not-accessible
    STATUS          current
    DESCRIPTION
        "A table that contains interface information of all units."
    ::= { pmIfStatistics 56 }

pmTcaIfPkt10241hEntry     OBJECT-TYPE
    SYNTAX          PMTcaIfPkt10241hEntry
    MAX-ACCESS      not-accessible
    STATUS          current
    DESCRIPTION
        "A list of interface information of all units."
    INDEX     { pmTcaIfPkt10241hIndex  }
    ::= { pmTcaIfPkt10241hTable 1 }

PMTcaIfPkt10241hEntry    ::=
    SEQUENCE
    {
       pmTcaIfPkt10241hIndex      Integer32,
       pmTcaIfPkt10241hId     OCTET STRING,
       pmTcaIfPkt10241hUnitType   INTEGER,
       pmTcaIfPkt10241hCnt     Counter64,
       pmTcaIfPkt10241hThreshold   Counter64,
       pmTcaIfPkt10241hOccurTime   DateAndTime
    }

pmTcaIfPkt10241hIndex         OBJECT-TYPE
    SYNTAX          Integer32
    MAX-ACCESS      not-accessible
    STATUS          current
    DESCRIPTION
        "An index of units."
    ::= { pmTcaIfPkt10241hEntry 1 }

pmTcaIfPkt10241hId         OBJECT-TYPE
    SYNTAX          OCTET STRING
    MAX-ACCESS      read-only
    STATUS          current
    DESCRIPTION
        "Interface name."
    ::= { pmTcaIfPkt10241hEntry 2 }

pmTcaIfPkt10241hUnitType         OBJECT-TYPE
    SYNTAX          INTEGER
    {
       mcu(0)
    }
    MAX-ACCESS      read-only
    STATUS          current
    DESCRIPTION
        "Unit type."
    ::= { pmTcaIfPkt10241hEntry 3 }

pmTcaIfPkt10241hCnt         OBJECT-TYPE
    SYNTAX          Counter64
    MAX-ACCESS      read-only
    STATUS          current
    DESCRIPTION
        "1hour counter of packets with size over 1024."
    ::= { pmTcaIfPkt10241hEntry 4 }

pmTcaIfPkt10241hThreshold         OBJECT-TYPE
    SYNTAX          Counter64
    MAX-ACCESS      read-only
    STATUS          current
    DESCRIPTION
        "1hour threshold of packets with size over 1024."
    ::= { pmTcaIfPkt10241hEntry 5 }

pmTcaIfPkt10241hOccurTime         OBJECT-TYPE
    SYNTAX          DateAndTime
    MAX-ACCESS      read-only
    STATUS          current
    DESCRIPTION
        "Time of the occurrence of the tca."
    ::= { pmTcaIfPkt10241hEntry 6 }

pmTcaIfPkt10241dTable     OBJECT-TYPE
    SYNTAX          SEQUENCE OF PMTcaIfPkt10241dEntry
    MAX-ACCESS      not-accessible
    STATUS          current
    DESCRIPTION
        "A table that contains interface information of all units."
    ::= { pmIfStatistics 57 }

pmTcaIfPkt10241dEntry     OBJECT-TYPE
    SYNTAX          PMTcaIfPkt10241dEntry
    MAX-ACCESS      not-accessible
    STATUS          current
    DESCRIPTION
        "A list of interface information of all units."
    INDEX     { pmTcaIfPkt10241dIndex  }
    ::= { pmTcaIfPkt10241dTable 1 }

PMTcaIfPkt10241dEntry    ::=
    SEQUENCE
    {
       pmTcaIfPkt10241dIndex      Integer32,
       pmTcaIfPkt10241dId     OCTET STRING,
       pmTcaIfPkt10241dUnitType  INTEGER,
       pmTcaIfPkt10241dCnt     Counter64,
       pmTcaIfPkt10241dThreshold   Counter64,
       pmTcaIfPkt10241dOccurTime   DateAndTime
    }

pmTcaIfPkt10241dIndex         OBJECT-TYPE
    SYNTAX          Integer32
    MAX-ACCESS      not-accessible
    STATUS          current
    DESCRIPTION
        "An index of units."
    ::= { pmTcaIfPkt10241dEntry 1 }

pmTcaIfPkt10241dId         OBJECT-TYPE
    SYNTAX          OCTET STRING
    MAX-ACCESS      read-only
    STATUS          current
    DESCRIPTION
        "Interface name."
    ::= { pmTcaIfPkt10241dEntry 2 }

pmTcaIfPkt10241dUnitType         OBJECT-TYPE
    SYNTAX          INTEGER
    {
       mcu(0)
    }
    MAX-ACCESS      read-only
    STATUS          current
    DESCRIPTION
        "Unit type."
    ::= { pmTcaIfPkt10241dEntry 3 }

pmTcaIfPkt10241dCnt         OBJECT-TYPE
    SYNTAX          Counter64
    MAX-ACCESS      read-only
    STATUS          current
    DESCRIPTION
        "1day counter of packets with size over 1024."
    ::= { pmTcaIfPkt10241dEntry 4 }

pmTcaIfPkt10241dThreshold         OBJECT-TYPE
    SYNTAX          Counter64
    MAX-ACCESS      read-only
    STATUS          current
    DESCRIPTION
        "1day threshold of packets with size over 1024."
    ::= { pmTcaIfPkt10241dEntry 5 }

pmTcaIfPkt10241dOccurTime         OBJECT-TYPE
    SYNTAX          DateAndTime
    MAX-ACCESS      read-only
    STATUS          current
    DESCRIPTION
        "Time of the occurrence of the tca."
    ::= { pmTcaIfPkt10241dEntry 6 }


pmTcaIfOutPkts15mTable     OBJECT-TYPE
    SYNTAX          SEQUENCE OF PMTcaIfOutPkts15mEntry
    MAX-ACCESS      not-accessible
    STATUS          current
    DESCRIPTION
        "A table that contains interface information of all units."
    ::= { pmIfStatistics 58 }

pmTcaIfOutPkts15mEntry     OBJECT-TYPE
    SYNTAX          PMTcaIfOutPkts15mEntry
    MAX-ACCESS      not-accessible
    STATUS          current
    DESCRIPTION
        "A list of interface information of all units."
    INDEX     { pmTcaIfOutPkts15mIndex  }
    ::= { pmTcaIfOutPkts15mTable 1 }

PMTcaIfOutPkts15mEntry    ::=
    SEQUENCE
    {
       pmTcaIfOutPkts15mIndex      Integer32,
       pmTcaIfOutPkts15mId     OCTET STRING,
       pmTcaIfOutPkts15mUnitType   INTEGER,
       pmTcaIfOutPkts15mCnt     Counter64,
       pmTcaIfOutPkts15mThreshold   Counter64,
       pmTcaIfOutPkts15mOccurTime   DateAndTime
    }

pmTcaIfOutPkts15mIndex         OBJECT-TYPE
    SYNTAX          Integer32
    MAX-ACCESS      not-accessible
    STATUS          current
    DESCRIPTION
        "An index of units."
    ::= { pmTcaIfOutPkts15mEntry 1 }

pmTcaIfOutPkts15mId         OBJECT-TYPE
    SYNTAX          OCTET STRING
    MAX-ACCESS      read-only
    STATUS          current
    DESCRIPTION
        "Interface name."
    ::= { pmTcaIfOutPkts15mEntry 2 }

pmTcaIfOutPkts15mUnitType         OBJECT-TYPE
    SYNTAX          INTEGER
    {
       mcu(0)
    }
    MAX-ACCESS      read-only
    STATUS          current
    DESCRIPTION
        "Unit type."
    ::= { pmTcaIfOutPkts15mEntry 3 }

pmTcaIfOutPkts15mCnt         OBJECT-TYPE
    SYNTAX          Counter64
    MAX-ACCESS      read-only
    STATUS          current
    DESCRIPTION
        "15min counter of output packets."
    ::= { pmTcaIfOutPkts15mEntry 4 }

pmTcaIfOutPkts15mThreshold         OBJECT-TYPE
    SYNTAX          Counter64
    MAX-ACCESS      read-only
    STATUS          current
    DESCRIPTION
        "15min threshold of output packets."
    ::= { pmTcaIfOutPkts15mEntry 5 }

pmTcaIfOutPkts15mOccurTime         OBJECT-TYPE
    SYNTAX          DateAndTime
    MAX-ACCESS      read-only
    STATUS          current
    DESCRIPTION
        "Time of the occurrence of the tca."
    ::= { pmTcaIfOutPkts15mEntry 6 }

pmTcaIfOutPkts1hTable     OBJECT-TYPE
    SYNTAX          SEQUENCE OF PMTcaIfOutPkts1hEntry
    MAX-ACCESS      not-accessible
    STATUS          current
    DESCRIPTION
        "A table that contains interface information of all units."
    ::= { pmIfStatistics 59 }

pmTcaIfOutPkts1hEntry     OBJECT-TYPE
    SYNTAX          PMTcaIfOutPkts1hEntry
    MAX-ACCESS      not-accessible
    STATUS          current
    DESCRIPTION
        "A list of interface information of all units."
    INDEX     { pmTcaIfOutPkts1hIndex  }
    ::= { pmTcaIfOutPkts1hTable 1 }

PMTcaIfOutPkts1hEntry    ::=
    SEQUENCE
    {
       pmTcaIfOutPkts1hIndex      Integer32,
       pmTcaIfOutPkts1hId     OCTET STRING,
       pmTcaIfOutPkts1hUnitType   INTEGER,
       pmTcaIfOutPkts1hCnt     Counter64,
       pmTcaIfOutPkts1hThreshold   Counter64,
       pmTcaIfOutPkts1hOccurTime   DateAndTime
    }

pmTcaIfOutPkts1hIndex         OBJECT-TYPE
    SYNTAX          Integer32
    MAX-ACCESS      not-accessible
    STATUS          current
    DESCRIPTION
        "An index of units."
    ::= { pmTcaIfOutPkts1hEntry 1 }

pmTcaIfOutPkts1hId         OBJECT-TYPE
    SYNTAX          OCTET STRING
    MAX-ACCESS      read-only
    STATUS          current
    DESCRIPTION
        "Interface name."
    ::= { pmTcaIfOutPkts1hEntry 2 }

pmTcaIfOutPkts1hUnitType         OBJECT-TYPE
    SYNTAX          INTEGER
    {
       mcu(0)
    }
    MAX-ACCESS      read-only
    STATUS          current
    DESCRIPTION
        "Unit type."
    ::= { pmTcaIfOutPkts1hEntry 3 }

pmTcaIfOutPkts1hCnt         OBJECT-TYPE
    SYNTAX          Counter64
    MAX-ACCESS      read-only
    STATUS          current
    DESCRIPTION
        "1hour counter of output packets."
    ::= { pmTcaIfOutPkts1hEntry 4 }

pmTcaIfOutPkts1hThreshold         OBJECT-TYPE
    SYNTAX          Counter64
    MAX-ACCESS      read-only
    STATUS          current
    DESCRIPTION
        "1hour threshold of output packets."
    ::= { pmTcaIfOutPkts1hEntry 5 }

pmTcaIfOutPkts1hOccurTime         OBJECT-TYPE
    SYNTAX          DateAndTime
    MAX-ACCESS      read-only
    STATUS          current
    DESCRIPTION
        "Time of the occurrence of the tca."
    ::= { pmTcaIfOutPkts1hEntry 6 }

pmTcaIfOutPkts1dTable     OBJECT-TYPE
    SYNTAX          SEQUENCE OF PMTcaIfOutPkts1dEntry
    MAX-ACCESS      not-accessible
    STATUS          current
    DESCRIPTION
        "A table that contains interface information of all units."
    ::= { pmIfStatistics 60 }

pmTcaIfOutPkts1dEntry     OBJECT-TYPE
    SYNTAX          PMTcaIfOutPkts1dEntry
    MAX-ACCESS      not-accessible
    STATUS          current
    DESCRIPTION
        "A list of interface information of all units."
    INDEX     { pmTcaIfOutPkts1dIndex  }
    ::= { pmTcaIfOutPkts1dTable 1 }

PMTcaIfOutPkts1dEntry    ::=
    SEQUENCE
    {
       pmTcaIfOutPkts1dIndex      Integer32,
       pmTcaIfOutPkts1dId     OCTET STRING,
       pmTcaIfOutPkts1dUnitType  INTEGER,
       pmTcaIfOutPkts1dCnt     Counter64,
       pmTcaIfOutPkts1dThreshold   Counter64,
       pmTcaIfOutPkts1dOccurTime   DateAndTime
    }

pmTcaIfOutPkts1dIndex         OBJECT-TYPE
    SYNTAX          Integer32
    MAX-ACCESS      not-accessible
    STATUS          current
    DESCRIPTION
        "An index of units."
    ::= { pmTcaIfOutPkts1dEntry 1 }

pmTcaIfOutPkts1dId         OBJECT-TYPE
    SYNTAX          OCTET STRING
    MAX-ACCESS      read-only
    STATUS          current
    DESCRIPTION
        "Interface name."
    ::= { pmTcaIfOutPkts1dEntry 2 }

pmTcaIfOutPkts1dUnitType         OBJECT-TYPE
    SYNTAX          INTEGER
    {
       mcu(0)
    }
    MAX-ACCESS      read-only
    STATUS          current
    DESCRIPTION
        "Unit type."
    ::= { pmTcaIfOutPkts1dEntry 3 }

pmTcaIfOutPkts1dCnt         OBJECT-TYPE
    SYNTAX          Counter64
    MAX-ACCESS      read-only
    STATUS          current
    DESCRIPTION
        "1day counter of output packets."
    ::= { pmTcaIfOutPkts1dEntry 4 }

pmTcaIfOutPkts1dThreshold         OBJECT-TYPE
    SYNTAX          Counter64
    MAX-ACCESS      read-only
    STATUS          current
    DESCRIPTION
        "1day threshold of output packets."
    ::= { pmTcaIfOutPkts1dEntry 5 }

pmTcaIfOutPkts1dOccurTime         OBJECT-TYPE
    SYNTAX          DateAndTime
    MAX-ACCESS      read-only
    STATUS          current
    DESCRIPTION
        "Time of the occurrence of the tca."
    ::= { pmTcaIfOutPkts1dEntry 6 }


pmTcaIfOutBytes15mTable     OBJECT-TYPE
    SYNTAX          SEQUENCE OF PMTcaIfOutBytes15mEntry
    MAX-ACCESS      not-accessible
    STATUS          current
    DESCRIPTION
        "A table that contains interface information of all units."
    ::= { pmIfStatistics 61 }

pmTcaIfOutBytes15mEntry     OBJECT-TYPE
    SYNTAX          PMTcaIfOutBytes15mEntry
    MAX-ACCESS      not-accessible
    STATUS          current
    DESCRIPTION
        "A list of interface information of all units."
    INDEX     { pmTcaIfOutBytes15mIndex  }
    ::= { pmTcaIfOutBytes15mTable 1 }

PMTcaIfOutBytes15mEntry    ::=
    SEQUENCE
    {
       pmTcaIfOutBytes15mIndex      Integer32,
       pmTcaIfOutBytes15mId     OCTET STRING,
       pmTcaIfOutBytes15mUnitType   INTEGER,
       pmTcaIfOutBytes15mCnt     Counter64,
       pmTcaIfOutBytes15mThreshold   Counter64,
       pmTcaIfOutBytes15mOccurTime   DateAndTime
    }

pmTcaIfOutBytes15mIndex         OBJECT-TYPE
    SYNTAX          Integer32
    MAX-ACCESS      not-accessible
    STATUS          current
    DESCRIPTION
        "An index of units."
    ::= { pmTcaIfOutBytes15mEntry 1 }

pmTcaIfOutBytes15mId         OBJECT-TYPE
    SYNTAX          OCTET STRING
    MAX-ACCESS      read-only
    STATUS          current
    DESCRIPTION
        "Interface name."
    ::= { pmTcaIfOutBytes15mEntry 2 }

pmTcaIfOutBytes15mUnitType         OBJECT-TYPE
    SYNTAX          INTEGER
    {
       mcu(0)
    }
    MAX-ACCESS      read-only
    STATUS          current
    DESCRIPTION
        "Unit type."
    ::= { pmTcaIfOutBytes15mEntry 3 }

pmTcaIfOutBytes15mCnt         OBJECT-TYPE
    SYNTAX          Counter64
    MAX-ACCESS      read-only
    STATUS          current
    DESCRIPTION
        "15min counter of output bytes."
    ::= { pmTcaIfOutBytes15mEntry 4 }

pmTcaIfOutBytes15mThreshold         OBJECT-TYPE
    SYNTAX          Counter64
    MAX-ACCESS      read-only
    STATUS          current
    DESCRIPTION
        "15min threshold of output bytes."
    ::= { pmTcaIfOutBytes15mEntry 5 }

pmTcaIfOutBytes15mOccurTime         OBJECT-TYPE
    SYNTAX          DateAndTime
    MAX-ACCESS      read-only
    STATUS          current
    DESCRIPTION
        "Time of the occurrence of the tca."
    ::= { pmTcaIfOutBytes15mEntry 6 }

pmTcaIfOutBytes1hTable     OBJECT-TYPE
    SYNTAX          SEQUENCE OF PMTcaIfOutBytes1hEntry
    MAX-ACCESS      not-accessible
    STATUS          current
    DESCRIPTION
        "A table that contains interface information of all units."
    ::= { pmIfStatistics 62 }

pmTcaIfOutBytes1hEntry     OBJECT-TYPE
    SYNTAX          PMTcaIfOutBytes1hEntry
    MAX-ACCESS      not-accessible
    STATUS          current
    DESCRIPTION
        "A list of interface information of all units."
    INDEX     { pmTcaIfOutBytes1hIndex  }
    ::= { pmTcaIfOutBytes1hTable 1 }

PMTcaIfOutBytes1hEntry    ::=
    SEQUENCE
    {
       pmTcaIfOutBytes1hIndex      Integer32,
       pmTcaIfOutBytes1hId     OCTET STRING,
       pmTcaIfOutBytes1hUnitType   INTEGER,
       pmTcaIfOutBytes1hCnt     Counter64,
       pmTcaIfOutBytes1hThreshold   Counter64,
       pmTcaIfOutBytes1hOccurTime   DateAndTime
    }

pmTcaIfOutBytes1hIndex         OBJECT-TYPE
    SYNTAX          Integer32
    MAX-ACCESS      not-accessible
    STATUS          current
    DESCRIPTION
        "An index of units."
    ::= { pmTcaIfOutBytes1hEntry 1 }

pmTcaIfOutBytes1hId         OBJECT-TYPE
    SYNTAX          OCTET STRING
    MAX-ACCESS      read-only
    STATUS          current
    DESCRIPTION
        "Interface name."
    ::= { pmTcaIfOutBytes1hEntry 2 }

pmTcaIfOutBytes1hUnitType         OBJECT-TYPE
    SYNTAX          INTEGER
    {
       mcu(0)
    }
    MAX-ACCESS      read-only
    STATUS          current
    DESCRIPTION
        "Unit type."
    ::= { pmTcaIfOutBytes1hEntry 3 }

pmTcaIfOutBytes1hCnt         OBJECT-TYPE
    SYNTAX          Counter64
    MAX-ACCESS      read-only
    STATUS          current
    DESCRIPTION
        "1hour counter of output bytes."
    ::= { pmTcaIfOutBytes1hEntry 4 }

pmTcaIfOutBytes1hThreshold         OBJECT-TYPE
    SYNTAX          Counter64
    MAX-ACCESS      read-only
    STATUS          current
    DESCRIPTION
        "1hour threshold of output bytes."
    ::= { pmTcaIfOutBytes1hEntry 5 }

pmTcaIfOutBytes1hOccurTime         OBJECT-TYPE
    SYNTAX          DateAndTime
    MAX-ACCESS      read-only
    STATUS          current
    DESCRIPTION
        "Time of the occurrence of the tca."
    ::= { pmTcaIfOutBytes1hEntry 6 }

pmTcaIfOutBytes1dTable     OBJECT-TYPE
    SYNTAX          SEQUENCE OF PMTcaIfOutBytes1dEntry
    MAX-ACCESS      not-accessible
    STATUS          current
    DESCRIPTION
        "A table that contains interface information of all units."
    ::= { pmIfStatistics 63 }

pmTcaIfOutBytes1dEntry     OBJECT-TYPE
    SYNTAX          PMTcaIfOutBytes1dEntry
    MAX-ACCESS      not-accessible
    STATUS          current
    DESCRIPTION
        "A list of interface information of all units."
    INDEX     { pmTcaIfOutBytes1dIndex  }
    ::= { pmTcaIfOutBytes1dTable 1 }

PMTcaIfOutBytes1dEntry    ::=
    SEQUENCE
    {
       pmTcaIfOutBytes1dIndex      Integer32,
       pmTcaIfOutBytes1dId     OCTET STRING,
       pmTcaIfOutBytes1dUnitType  INTEGER,
       pmTcaIfOutBytes1dCnt     Counter64,
       pmTcaIfOutBytes1dThreshold   Counter64,
       pmTcaIfOutBytes1dOccurTime   DateAndTime
    }

pmTcaIfOutBytes1dIndex         OBJECT-TYPE
    SYNTAX          Integer32
    MAX-ACCESS      not-accessible
    STATUS          current
    DESCRIPTION
        "An index of units."
    ::= { pmTcaIfOutBytes1dEntry 1 }

pmTcaIfOutBytes1dId         OBJECT-TYPE
    SYNTAX          OCTET STRING
    MAX-ACCESS      read-only
    STATUS          current
    DESCRIPTION
        "Interface name."
    ::= { pmTcaIfOutBytes1dEntry 2 }

pmTcaIfOutBytes1dUnitType         OBJECT-TYPE
    SYNTAX          INTEGER
    {
       mcu(0)
    }
    MAX-ACCESS      read-only
    STATUS          current
    DESCRIPTION
        "Unit type."
    ::= { pmTcaIfOutBytes1dEntry 3 }

pmTcaIfOutBytes1dCnt         OBJECT-TYPE
    SYNTAX          Counter64
    MAX-ACCESS      read-only
    STATUS          current
    DESCRIPTION
        "1day counter of output bytes."
    ::= { pmTcaIfOutBytes1dEntry 4 }

pmTcaIfOutBytes1dThreshold         OBJECT-TYPE
    SYNTAX          Counter64
    MAX-ACCESS      read-only
    STATUS          current
    DESCRIPTION
        "1day threshold of output bytes."
    ::= { pmTcaIfOutBytes1dEntry 5 }

pmTcaIfOutBytes1dOccurTime         OBJECT-TYPE
    SYNTAX          DateAndTime
    MAX-ACCESS      read-only
    STATUS          current
    DESCRIPTION
        "Time of the occurrence of the tca."
    ::= { pmTcaIfOutBytes1dEntry 6 }


pmLspPe        OBJECT IDENTIFIER ::= { pm 103 }


pmLspPeCurr15mTable     OBJECT-TYPE
    SYNTAX          SEQUENCE OF PMLspPeCurr15mEntry
    MAX-ACCESS      not-accessible
    STATUS          current
    DESCRIPTION
        "A table that contains lsp-pe information of all units."
    ::= { pmLspPe 1 }

pmLspPeCurr15mEntry     OBJECT-TYPE
    SYNTAX          PMLspPeCurr15mEntry
    MAX-ACCESS      not-accessible
    STATUS          current
    DESCRIPTION
        "A list of lsp-pe information of all units."
    INDEX     { pmLspPeCurr15mIndex  }
    ::= { pmLspPeCurr15mTable 1 }

PMLspPeCurr15mEntry    ::=
    SEQUENCE
    {
       pmLspPeCurr15mIndex     Integer32,
       pmLspPeCurr15mId    OCTET STRING,
       pmLspPeCurr15mUnitType  INTEGER,
       pmLspPeCurr15mOutPkts    Counter64,
       pmLspPeCurr15mOutBytes    Counter64,
       pmLspPeCurr15mStartTime  DateAndTime,
       pmLspPeCurr15mStopTime  DateAndTime
    }

pmLspPeCurr15mIndex         OBJECT-TYPE
    SYNTAX          Integer32
    MAX-ACCESS      not-accessible
    STATUS          current
    DESCRIPTION
        "An index of units."
    ::= { pmLspPeCurr15mEntry 1 }

pmLspPeCurr15mId         OBJECT-TYPE
    SYNTAX          OCTET STRING
    MAX-ACCESS      read-only
    STATUS          current
    DESCRIPTION
        "Lsp-pe name."
    ::= { pmLspPeCurr15mEntry 2 }

pmLspPeCurr15mUnitType         OBJECT-TYPE
    SYNTAX          INTEGER
    {
       mcu(0)
    }
    MAX-ACCESS      read-only
    STATUS          current
    DESCRIPTION
        "Unit type."
    ::= { pmLspPeCurr15mEntry 3 }

pmLspPeCurr15mOutPkts         OBJECT-TYPE
    SYNTAX          Counter64
    MAX-ACCESS      read-only
    STATUS          current
    DESCRIPTION
        "Current 15min counter of lsp-pe out packets."
    ::= { pmLspPeCurr15mEntry 4 }

pmLspPeCurr15mOutBytes         OBJECT-TYPE
    SYNTAX          Counter64
    MAX-ACCESS      read-only
    STATUS          current
    DESCRIPTION
        "Current 15min counter of lsp-pe out bytes."
    ::= { pmLspPeCurr15mEntry 5 }

pmLspPeCurr15mStartTime         OBJECT-TYPE
    SYNTAX          DateAndTime
    MAX-ACCESS      read-only
    STATUS          current
    DESCRIPTION
        "Current 15min start time."
    ::= { pmLspPeCurr15mEntry 100 }

pmLspPeCurr15mStopTime         OBJECT-TYPE
    SYNTAX          DateAndTime
    MAX-ACCESS      read-only
    STATUS          current
    DESCRIPTION
        "Current 15min stop time."
    ::= { pmLspPeCurr15mEntry 101 }


pmLspPePrev15mTable     OBJECT-TYPE
    SYNTAX          SEQUENCE OF PMLspPePrev15mEntry
    MAX-ACCESS      not-accessible
    STATUS          current
    DESCRIPTION
        "A table that contains lsp-pe information of all units."
    ::= { pmLspPe 2 }

pmLspPePrev15mEntry     OBJECT-TYPE
    SYNTAX          PMLspPePrev15mEntry
    MAX-ACCESS      not-accessible
    STATUS          current
    DESCRIPTION
        "A list of lsp-pe information of all units."
    INDEX     { pmLspPePrev15mIndex  }
    ::= { pmLspPePrev15mTable 1 }

PMLspPePrev15mEntry    ::=
    SEQUENCE
    {
       pmLspPePrev15mIndex     Integer32,
       pmLspPePrev15mId    OCTET STRING,
       pmLspPePrev15mUnitType  INTEGER,
       pmLspPePrev15mOutPkts    Counter64,
       pmLspPePrev15mOutBytes    Counter64,
       pmLspPePrev15mStartTime  DateAndTime,
       pmLspPePrev15mStopTime  DateAndTime
    }

pmLspPePrev15mIndex         OBJECT-TYPE
    SYNTAX          Integer32
    MAX-ACCESS      not-accessible
    STATUS          current
    DESCRIPTION
        "An index of units."
    ::= { pmLspPePrev15mEntry 1 }

pmLspPePrev15mId         OBJECT-TYPE
    SYNTAX          OCTET STRING
    MAX-ACCESS      read-only
    STATUS          current
    DESCRIPTION
        "Lsp-pe name."
    ::= { pmLspPePrev15mEntry 2 }

pmLspPePrev15mUnitType         OBJECT-TYPE
    SYNTAX          INTEGER
    {
       mcu(0)
    }
    MAX-ACCESS      read-only
    STATUS          current
    DESCRIPTION
        "Unit type."
    ::= { pmLspPePrev15mEntry 3 }

pmLspPePrev15mOutPkts         OBJECT-TYPE
    SYNTAX          Counter64
    MAX-ACCESS      read-only
    STATUS          current
    DESCRIPTION
        "Previous 15min counter of lsp-pe out packets."
    ::= { pmLspPePrev15mEntry 4 }

pmLspPePrev15mOutBytes         OBJECT-TYPE
    SYNTAX          Counter64
    MAX-ACCESS      read-only
    STATUS          current
    DESCRIPTION
        "Previous 15min counter of lsp-pe out bytes."
    ::= { pmLspPePrev15mEntry 5 }

pmLspPePrev15mStartTime         OBJECT-TYPE
    SYNTAX          DateAndTime
    MAX-ACCESS      read-only
    STATUS          current
    DESCRIPTION
        "Previous 15min start time."
    ::= { pmLspPePrev15mEntry 100 }

pmLspPePrev15mStopTime         OBJECT-TYPE
    SYNTAX          DateAndTime
    MAX-ACCESS      read-only
    STATUS          current
    DESCRIPTION
        "Previous 15min stop time."
    ::= { pmLspPePrev15mEntry 101 }


pmLspPeCurr1hTable     OBJECT-TYPE
    SYNTAX          SEQUENCE OF PMLspPeCurr1hEntry
    MAX-ACCESS      not-accessible
    STATUS          current
    DESCRIPTION
        "A table that contains lsp-pe information of all units."
    ::= { pmLspPe 3 }

pmLspPeCurr1hEntry     OBJECT-TYPE
    SYNTAX          PMLspPeCurr1hEntry
    MAX-ACCESS      not-accessible
    STATUS          current
    DESCRIPTION
        "A list of lsp-pe information of all units."
    INDEX     { pmLspPeCurr1hIndex  }
    ::= { pmLspPeCurr1hTable 1 }

PMLspPeCurr1hEntry    ::=
    SEQUENCE
    {
       pmLspPeCurr1hIndex     Integer32,
       pmLspPeCurr1hId    OCTET STRING,
       pmLspPeCurr1hUnitType  INTEGER,
       pmLspPeCurr1hOutPkts    Counter64,
       pmLspPeCurr1hOutBytes    Counter64,
       pmLspPeCurr1hStartTime  DateAndTime,
       pmLspPeCurr1hStopTime  DateAndTime
    }

pmLspPeCurr1hIndex         OBJECT-TYPE
    SYNTAX          Integer32
    MAX-ACCESS      not-accessible
    STATUS          current
    DESCRIPTION
        "An index of units."
    ::= { pmLspPeCurr1hEntry 1 }

pmLspPeCurr1hId         OBJECT-TYPE
    SYNTAX          OCTET STRING
    MAX-ACCESS      read-only
    STATUS          current
    DESCRIPTION
        "Lsp-pe name."
    ::= { pmLspPeCurr1hEntry 2 }

pmLspPeCurr1hUnitType         OBJECT-TYPE
    SYNTAX          INTEGER
    {
       mcu(0)
    }
    MAX-ACCESS      read-only
    STATUS          current
    DESCRIPTION
        "Unit type."
    ::= { pmLspPeCurr1hEntry 3 }

pmLspPeCurr1hOutPkts         OBJECT-TYPE
    SYNTAX          Counter64
    MAX-ACCESS      read-only
    STATUS          current
    DESCRIPTION
        "Current 1hour counter of lsp-pe out packets."
    ::= { pmLspPeCurr1hEntry 4 }

pmLspPeCurr1hOutBytes         OBJECT-TYPE
    SYNTAX          Counter64
    MAX-ACCESS      read-only
    STATUS          current
    DESCRIPTION
        "Current 1hour counter of lsp-pe out bytes."
    ::= { pmLspPeCurr1hEntry 5 }

pmLspPeCurr1hStartTime         OBJECT-TYPE
    SYNTAX          DateAndTime
    MAX-ACCESS      read-only
    STATUS          current
    DESCRIPTION
        "Current 1hour start time."
    ::= { pmLspPeCurr1hEntry 100 }

pmLspPeCurr1hStopTime         OBJECT-TYPE
    SYNTAX          DateAndTime
    MAX-ACCESS      read-only
    STATUS          current
    DESCRIPTION
        "Current 1hour stop time."
    ::= { pmLspPeCurr1hEntry 101 }


pmLspPePrev1hTable     OBJECT-TYPE
    SYNTAX          SEQUENCE OF PMLspPePrev1hEntry
    MAX-ACCESS      not-accessible
    STATUS          current
    DESCRIPTION
        "A table that contains lsp-pe information of all units."
    ::= { pmLspPe 4 }

pmLspPePrev1hEntry     OBJECT-TYPE
    SYNTAX          PMLspPePrev1hEntry
    MAX-ACCESS      not-accessible
    STATUS          current
    DESCRIPTION
        "A list of lsp-pe information of all units."
    INDEX     { pmLspPePrev1hIndex  }
    ::= { pmLspPePrev1hTable 1 }

PMLspPePrev1hEntry    ::=
    SEQUENCE
    {
       pmLspPePrev1hIndex     Integer32,
       pmLspPePrev1hId    OCTET STRING,
       pmLspPePrev1hUnitType  INTEGER,
       pmLspPePrev1hOutPkts    Counter64,
       pmLspPePrev1hOutBytes    Counter64,
       pmLspPePrev1hStartTime  DateAndTime,
       pmLspPePrev1hStopTime  DateAndTime
    }

pmLspPePrev1hIndex         OBJECT-TYPE
    SYNTAX          Integer32
    MAX-ACCESS      not-accessible
    STATUS          current
    DESCRIPTION
        "An index of units."
    ::= { pmLspPePrev1hEntry 1 }

pmLspPePrev1hId         OBJECT-TYPE
    SYNTAX          OCTET STRING
    MAX-ACCESS      read-only
    STATUS          current
    DESCRIPTION
        "Lsp-pe name."
    ::= { pmLspPePrev1hEntry 2 }

pmLspPePrev1hUnitType         OBJECT-TYPE
    SYNTAX          INTEGER
    {
       mcu(0)
    }
    MAX-ACCESS      read-only
    STATUS          current
    DESCRIPTION
        "Unit type."
    ::= { pmLspPePrev1hEntry 3 }

pmLspPePrev1hOutPkts         OBJECT-TYPE
    SYNTAX          Counter64
    MAX-ACCESS      read-only
    STATUS          current
    DESCRIPTION
        "Previous 1hour counter of lsp-pe out packets."
    ::= { pmLspPePrev1hEntry 4 }

pmLspPePrev1hOutBytes         OBJECT-TYPE
    SYNTAX          Counter64
    MAX-ACCESS      read-only
    STATUS          current
    DESCRIPTION
        "Previous 1hour counter of lsp-pe out bytes."
    ::= { pmLspPePrev1hEntry 5 }

pmLspPePrev1hStartTime         OBJECT-TYPE
    SYNTAX          DateAndTime
    MAX-ACCESS      read-only
    STATUS          current
    DESCRIPTION
        "Previous 1hour start time."
    ::= { pmLspPePrev1hEntry 100 }

pmLspPePrev1hStopTime         OBJECT-TYPE
    SYNTAX          DateAndTime
    MAX-ACCESS      read-only
    STATUS          current
    DESCRIPTION
        "Previous 1hour stop time."
    ::= { pmLspPePrev1hEntry 101 }


pmLspPeCurr1dTable     OBJECT-TYPE
    SYNTAX          SEQUENCE OF PMLspPeCurr1dEntry
    MAX-ACCESS      not-accessible
    STATUS          current
    DESCRIPTION
        "A table that contains lsp-pe information of all units."
    ::= { pmLspPe 5 }

pmLspPeCurr1dEntry     OBJECT-TYPE
    SYNTAX          PMLspPeCurr1dEntry
    MAX-ACCESS      not-accessible
    STATUS          current
    DESCRIPTION
        "A list of lsp-pe information of all units."
    INDEX     { pmLspPeCurr1dIndex  }
    ::= { pmLspPeCurr1dTable 1 }

PMLspPeCurr1dEntry    ::=
    SEQUENCE
    {
       pmLspPeCurr1dIndex     Integer32,
       pmLspPeCurr1dId    OCTET STRING,
       pmLspPeCurr1dUnitType  INTEGER,
       pmLspPeCurr1dOutPkts    Counter64,
       pmLspPeCurr1dOutBytes    Counter64,
       pmLspPeCurr1dStartTime  DateAndTime,
       pmLspPeCurr1dStopTime  DateAndTime
    }

pmLspPeCurr1dIndex         OBJECT-TYPE
    SYNTAX          Integer32
    MAX-ACCESS      not-accessible
    STATUS          current
    DESCRIPTION
        "An index of units."
    ::= { pmLspPeCurr1dEntry 1 }

pmLspPeCurr1dId         OBJECT-TYPE
    SYNTAX          OCTET STRING
    MAX-ACCESS      read-only
    STATUS          current
    DESCRIPTION
        "Lsp-pe name."
    ::= { pmLspPeCurr1dEntry 2 }

pmLspPeCurr1dUnitType         OBJECT-TYPE
    SYNTAX          INTEGER
    {
       mcu(0)
    }
    MAX-ACCESS      read-only
    STATUS          current
    DESCRIPTION
        "Unit type."
    ::= { pmLspPeCurr1dEntry 3 }

pmLspPeCurr1dOutPkts         OBJECT-TYPE
    SYNTAX          Counter64
    MAX-ACCESS      read-only
    STATUS          current
    DESCRIPTION
        "Current 1day counter of lsp-pe out packets."
    ::= { pmLspPeCurr1dEntry 4 }

pmLspPeCurr1dOutBytes         OBJECT-TYPE
    SYNTAX          Counter64
    MAX-ACCESS      read-only
    STATUS          current
    DESCRIPTION
        "Current 1day counter of lsp-pe out bytes."
    ::= { pmLspPeCurr1dEntry 5 }

pmLspPeCurr1dStartTime         OBJECT-TYPE
    SYNTAX          DateAndTime
    MAX-ACCESS      read-only
    STATUS          current
    DESCRIPTION
        "Current 1day start time."
    ::= { pmLspPeCurr1dEntry 100 }

pmLspPeCurr1dStopTime         OBJECT-TYPE
    SYNTAX          DateAndTime
    MAX-ACCESS      read-only
    STATUS          current
    DESCRIPTION
        "Current 1day stop time."
    ::= { pmLspPeCurr1dEntry 101 }


pmLspPePrev1dTable     OBJECT-TYPE
    SYNTAX          SEQUENCE OF PMLspPePrev1dEntry
    MAX-ACCESS      not-accessible
    STATUS          current
    DESCRIPTION
        "A table that contains lsp-pe information of all units."
    ::= { pmLspPe 6 }

pmLspPePrev1dEntry     OBJECT-TYPE
    SYNTAX          PMLspPePrev1dEntry
    MAX-ACCESS      not-accessible
    STATUS          current
    DESCRIPTION
        "A list of lsp-pe information of all units."
    INDEX     { pmLspPePrev1dIndex  }
    ::= { pmLspPePrev1dTable 1 }

PMLspPePrev1dEntry    ::=
    SEQUENCE
    {
       pmLspPePrev1dIndex     Integer32,
       pmLspPePrev1dId    OCTET STRING,
       pmLspPePrev1dUnitType  INTEGER,
       pmLspPePrev1dOutPkts    Counter64,
       pmLspPePrev1dOutBytes    Counter64,
       pmLspPePrev1dStartTime  DateAndTime,
       pmLspPePrev1dStopTime  DateAndTime
    }

pmLspPePrev1dIndex         OBJECT-TYPE
    SYNTAX          Integer32
    MAX-ACCESS      not-accessible
    STATUS          current
    DESCRIPTION
        "An index of units."
    ::= { pmLspPePrev1dEntry 1 }

pmLspPePrev1dId         OBJECT-TYPE
    SYNTAX          OCTET STRING
    MAX-ACCESS      read-only
    STATUS          current
    DESCRIPTION
        "Lsp-pe name."
    ::= { pmLspPePrev1dEntry 2 }

pmLspPePrev1dUnitType         OBJECT-TYPE
    SYNTAX          INTEGER
    {
       mcu(0)
    }
    MAX-ACCESS      read-only
    STATUS          current
    DESCRIPTION
        "Unit type."
    ::= { pmLspPePrev1dEntry 3 }

pmLspPePrev1dOutPkts         OBJECT-TYPE
    SYNTAX          Counter64
    MAX-ACCESS      read-only
    STATUS          current
    DESCRIPTION
        "Previous1day counter of lsp-pe out packets."
    ::= { pmLspPePrev1dEntry 4 }

pmLspPePrev1dOutBytes         OBJECT-TYPE
    SYNTAX          Counter64
    MAX-ACCESS      read-only
    STATUS          current
    DESCRIPTION
        "Previous1day counter of lsp-pe out bytes."
    ::= { pmLspPePrev1dEntry 5 }

pmLspPePrev1dStartTime         OBJECT-TYPE
    SYNTAX          DateAndTime
    MAX-ACCESS      read-only
    STATUS          current
    DESCRIPTION
        "Previous1day start time."
    ::= { pmLspPePrev1dEntry 100 }

pmLspPePrev1dStopTime         OBJECT-TYPE
    SYNTAX          DateAndTime
    MAX-ACCESS      read-only
    STATUS          current
    DESCRIPTION
        "Previous1day stop time."
    ::= { pmLspPePrev1dEntry 101 }


pmTcaLspPeOutPkts15mTable     OBJECT-TYPE
    SYNTAX          SEQUENCE OF PMTcaLspPeOutPkts15mEntry
    MAX-ACCESS      not-accessible
    STATUS          current
    DESCRIPTION
        "A table that contains lsp-pe information of all units."
    ::= { pmLspPe 7 }

pmTcaLspPeOutPkts15mEntry     OBJECT-TYPE
    SYNTAX          PMTcaLspPeOutPkts15mEntry
    MAX-ACCESS      not-accessible
    STATUS          current
    DESCRIPTION
        "A list of lsp-pe information of all units."
    INDEX     { pmTcaLspPeOutPkts15mIndex  }
    ::= { pmTcaLspPeOutPkts15mTable 1 }

PMTcaLspPeOutPkts15mEntry    ::=
    SEQUENCE
    {
       pmTcaLspPeOutPkts15mIndex      Integer32,
       pmTcaLspPeOutPkts15mId     OCTET STRING,
       pmTcaLspPeOutPkts15mUnitType   INTEGER,
       pmTcaLspPeOutPkts15mCnt     Counter64,
       pmTcaLspPeOutPkts15mThreshold   Counter64,
       pmTcaLspPeOutPkts15mOccurTime   DateAndTime
    }

pmTcaLspPeOutPkts15mIndex         OBJECT-TYPE
    SYNTAX          Integer32
    MAX-ACCESS      not-accessible
    STATUS          current
    DESCRIPTION
        "An index of units."
    ::= { pmTcaLspPeOutPkts15mEntry 1 }

pmTcaLspPeOutPkts15mId         OBJECT-TYPE
    SYNTAX          OCTET STRING
    MAX-ACCESS      read-only
    STATUS          current
    DESCRIPTION
        "Lsp-pe name."
    ::= { pmTcaLspPeOutPkts15mEntry 2 }

pmTcaLspPeOutPkts15mUnitType         OBJECT-TYPE
    SYNTAX          INTEGER
    {
       mcu(0)
    }
    MAX-ACCESS      read-only
    STATUS          current
    DESCRIPTION
        "Unit type."
    ::= { pmTcaLspPeOutPkts15mEntry 3 }

pmTcaLspPeOutPkts15mCnt         OBJECT-TYPE
    SYNTAX          Counter64
    MAX-ACCESS      read-only
    STATUS          current
    DESCRIPTION
        "15min counter of lsp-pe out packets."
    ::= { pmTcaLspPeOutPkts15mEntry 4 }

pmTcaLspPeOutPkts15mThreshold         OBJECT-TYPE
    SYNTAX          Counter64
    MAX-ACCESS      read-only
    STATUS          current
    DESCRIPTION
        "15min threshold of lsp-pe out packets."
    ::= { pmTcaLspPeOutPkts15mEntry 5 }

pmTcaLspPeOutPkts15mOccurTime         OBJECT-TYPE
    SYNTAX          DateAndTime
    MAX-ACCESS      read-only
    STATUS          current
    DESCRIPTION
        "Time of the occurrence of the tca."
    ::= { pmTcaLspPeOutPkts15mEntry 6 }

pmTcaLspPeOutPkts1hTable     OBJECT-TYPE
    SYNTAX          SEQUENCE OF PMTcaLspPeOutPkts1hEntry
    MAX-ACCESS      not-accessible
    STATUS          current
    DESCRIPTION
        "A table that contains lsp-pe information of all units."
    ::= { pmLspPe 8 }

pmTcaLspPeOutPkts1hEntry     OBJECT-TYPE
    SYNTAX          PMTcaLspPeOutPkts1hEntry
    MAX-ACCESS      not-accessible
    STATUS          current
    DESCRIPTION
        "A list of lsp-pe information of all units."
    INDEX     { pmTcaLspPeOutPkts1hIndex  }
    ::= { pmTcaLspPeOutPkts1hTable 1 }

PMTcaLspPeOutPkts1hEntry    ::=
    SEQUENCE
    {
       pmTcaLspPeOutPkts1hIndex      Integer32,
       pmTcaLspPeOutPkts1hId     OCTET STRING,
       pmTcaLspPeOutPkts1hUnitType   INTEGER,
       pmTcaLspPeOutPkts1hCnt     Counter64,
       pmTcaLspPeOutPkts1hThreshold   Counter64,
       pmTcaLspPeOutPkts1hOccurTime   DateAndTime
    }

pmTcaLspPeOutPkts1hIndex         OBJECT-TYPE
    SYNTAX          Integer32
    MAX-ACCESS      not-accessible
    STATUS          current
    DESCRIPTION
        "An index of units."
    ::= { pmTcaLspPeOutPkts1hEntry 1 }

pmTcaLspPeOutPkts1hId         OBJECT-TYPE
    SYNTAX          OCTET STRING
    MAX-ACCESS      read-only
    STATUS          current
    DESCRIPTION
        "Lsp-pe name."
    ::= { pmTcaLspPeOutPkts1hEntry 2 }

pmTcaLspPeOutPkts1hUnitType         OBJECT-TYPE
    SYNTAX          INTEGER
    {
       mcu(0)
    }
    MAX-ACCESS      read-only
    STATUS          current
    DESCRIPTION
        "Unit type."
    ::= { pmTcaLspPeOutPkts1hEntry 3 }

pmTcaLspPeOutPkts1hCnt         OBJECT-TYPE
    SYNTAX          Counter64
    MAX-ACCESS      read-only
    STATUS          current
    DESCRIPTION
        "1hour counter of lsp-pe out packets."
    ::= { pmTcaLspPeOutPkts1hEntry 4 }

pmTcaLspPeOutPkts1hThreshold         OBJECT-TYPE
    SYNTAX          Counter64
    MAX-ACCESS      read-only
    STATUS          current
    DESCRIPTION
        "1hour threshold of lsp-pe out packets."
    ::= { pmTcaLspPeOutPkts1hEntry 5 }

pmTcaLspPeOutPkts1hOccurTime         OBJECT-TYPE
    SYNTAX          DateAndTime
    MAX-ACCESS      read-only
    STATUS          current
    DESCRIPTION
        "Time of the occurrence of the tca."
    ::= { pmTcaLspPeOutPkts1hEntry 6 }

pmTcaLspPeOutPkts1dTable     OBJECT-TYPE
    SYNTAX          SEQUENCE OF PMTcaLspPeOutPkts1dEntry
    MAX-ACCESS      not-accessible
    STATUS          current
    DESCRIPTION
        "A table that contains lsp-pe information of all units."
    ::= { pmLspPe 9 }

pmTcaLspPeOutPkts1dEntry     OBJECT-TYPE
    SYNTAX          PMTcaLspPeOutPkts1dEntry
    MAX-ACCESS      not-accessible
    STATUS          current
    DESCRIPTION
        "A list of lsp-pe information of all units."
    INDEX     { pmTcaLspPeOutPkts1dIndex  }
    ::= { pmTcaLspPeOutPkts1dTable 1 }

PMTcaLspPeOutPkts1dEntry    ::=
    SEQUENCE
    {
       pmTcaLspPeOutPkts1dIndex      Integer32,
       pmTcaLspPeOutPkts1dId     OCTET STRING,
       pmTcaLspPeOutPkts1dUnitType  INTEGER,
       pmTcaLspPeOutPkts1dCnt     Counter64,
       pmTcaLspPeOutPkts1dThreshold   Counter64,
       pmTcaLspPeOutPkts1dOccurTime   DateAndTime
    }

pmTcaLspPeOutPkts1dIndex         OBJECT-TYPE
    SYNTAX          Integer32
    MAX-ACCESS      not-accessible
    STATUS          current
    DESCRIPTION
        "An index of units."
    ::= { pmTcaLspPeOutPkts1dEntry 1 }

pmTcaLspPeOutPkts1dId         OBJECT-TYPE
    SYNTAX          OCTET STRING
    MAX-ACCESS      read-only
    STATUS          current
    DESCRIPTION
        "Lsp-pe name."
    ::= { pmTcaLspPeOutPkts1dEntry 2 }

pmTcaLspPeOutPkts1dUnitType         OBJECT-TYPE
    SYNTAX          INTEGER
    {
       mcu(0)
    }
    MAX-ACCESS      read-only
    STATUS          current
    DESCRIPTION
        "Unit type."
    ::= { pmTcaLspPeOutPkts1dEntry 3 }

pmTcaLspPeOutPkts1dCnt         OBJECT-TYPE
    SYNTAX          Counter64
    MAX-ACCESS      read-only
    STATUS          current
    DESCRIPTION
        "1day counter of lsp-pe out packets."
    ::= { pmTcaLspPeOutPkts1dEntry 4 }

pmTcaLspPeOutPkts1dThreshold         OBJECT-TYPE
    SYNTAX          Counter64
    MAX-ACCESS      read-only
    STATUS          current
    DESCRIPTION
        "1day threshold of lsp-pe out packets."
    ::= { pmTcaLspPeOutPkts1dEntry 5 }

pmTcaLspPeOutPkts1dOccurTime         OBJECT-TYPE
    SYNTAX          DateAndTime
    MAX-ACCESS      read-only
    STATUS          current
    DESCRIPTION
        "Time of the occurrence of the tca."
    ::= { pmTcaLspPeOutPkts1dEntry 6 }


pmTcaLspPeOutBytes15mTable     OBJECT-TYPE
    SYNTAX          SEQUENCE OF PMTcaLspPeOutBytes15mEntry
    MAX-ACCESS      not-accessible
    STATUS          current
    DESCRIPTION
        "A table that contains lsp-pe information of all units."
    ::= { pmLspPe 10 }

pmTcaLspPeOutBytes15mEntry     OBJECT-TYPE
    SYNTAX          PMTcaLspPeOutBytes15mEntry
    MAX-ACCESS      not-accessible
    STATUS          current
    DESCRIPTION
        "A list of lsp-pe information of all units."
    INDEX     { pmTcaLspPeOutBytes15mIndex  }
    ::= { pmTcaLspPeOutBytes15mTable 1 }

PMTcaLspPeOutBytes15mEntry    ::=
    SEQUENCE
    {
       pmTcaLspPeOutBytes15mIndex      Integer32,
       pmTcaLspPeOutBytes15mId     OCTET STRING,
       pmTcaLspPeOutBytes15mUnitType   INTEGER,
       pmTcaLspPeOutBytes15mCnt     Counter64,
       pmTcaLspPeOutBytes15mThreshold   Counter64,
       pmTcaLspPeOutBytes15mOccurTime   DateAndTime
    }

pmTcaLspPeOutBytes15mIndex         OBJECT-TYPE
    SYNTAX          Integer32
    MAX-ACCESS      not-accessible
    STATUS          current
    DESCRIPTION
        "An index of units."
    ::= { pmTcaLspPeOutBytes15mEntry 1 }

pmTcaLspPeOutBytes15mId         OBJECT-TYPE
    SYNTAX          OCTET STRING
    MAX-ACCESS      read-only
    STATUS          current
    DESCRIPTION
        "Lsp-pe name."
    ::= { pmTcaLspPeOutBytes15mEntry 2 }

pmTcaLspPeOutBytes15mUnitType         OBJECT-TYPE
    SYNTAX          INTEGER
    {
       mcu(0)
    }
    MAX-ACCESS      read-only
    STATUS          current
    DESCRIPTION
        "Unit type."
    ::= { pmTcaLspPeOutBytes15mEntry 3 }

pmTcaLspPeOutBytes15mCnt         OBJECT-TYPE
    SYNTAX          Counter64
    MAX-ACCESS      read-only
    STATUS          current
    DESCRIPTION
        "15min counter of lsp-pe out bytes."
    ::= { pmTcaLspPeOutBytes15mEntry 4 }

pmTcaLspPeOutBytes15mThreshold         OBJECT-TYPE
    SYNTAX          Counter64
    MAX-ACCESS      read-only
    STATUS          current
    DESCRIPTION
        "15min threshold of lsp-pe out bytes."
    ::= { pmTcaLspPeOutBytes15mEntry 5 }

pmTcaLspPeOutBytes15mOccurTime         OBJECT-TYPE
    SYNTAX          DateAndTime
    MAX-ACCESS      read-only
    STATUS          current
    DESCRIPTION
        "Time of the occurrence of the tca."
    ::= { pmTcaLspPeOutBytes15mEntry 6 }

pmTcaLspPeOutBytes1hTable     OBJECT-TYPE
    SYNTAX          SEQUENCE OF PMTcaLspPeOutBytes1hEntry
    MAX-ACCESS      not-accessible
    STATUS          current
    DESCRIPTION
        "A table that contains lsp-pe information of all units."
    ::= { pmLspPe 11 }

pmTcaLspPeOutBytes1hEntry     OBJECT-TYPE
    SYNTAX          PMTcaLspPeOutBytes1hEntry
    MAX-ACCESS      not-accessible
    STATUS          current
    DESCRIPTION
        "A list of lsp-pe information of all units."
    INDEX     { pmTcaLspPeOutBytes1hIndex  }
    ::= { pmTcaLspPeOutBytes1hTable 1 }

PMTcaLspPeOutBytes1hEntry    ::=
    SEQUENCE
    {
       pmTcaLspPeOutBytes1hIndex      Integer32,
       pmTcaLspPeOutBytes1hId     OCTET STRING,
       pmTcaLspPeOutBytes1hUnitType   INTEGER,
       pmTcaLspPeOutBytes1hCnt     Counter64,
       pmTcaLspPeOutBytes1hThreshold   Counter64,
       pmTcaLspPeOutBytes1hOccurTime   DateAndTime
    }

pmTcaLspPeOutBytes1hIndex         OBJECT-TYPE
    SYNTAX          Integer32
    MAX-ACCESS      not-accessible
    STATUS          current
    DESCRIPTION
        "An index of units."
    ::= { pmTcaLspPeOutBytes1hEntry 1 }

pmTcaLspPeOutBytes1hId         OBJECT-TYPE
    SYNTAX          OCTET STRING
    MAX-ACCESS      read-only
    STATUS          current
    DESCRIPTION
        "Lsp-pe name."
    ::= { pmTcaLspPeOutBytes1hEntry 2 }

pmTcaLspPeOutBytes1hUnitType         OBJECT-TYPE
    SYNTAX          INTEGER
    {
       mcu(0)
    }
    MAX-ACCESS      read-only
    STATUS          current
    DESCRIPTION
        "Unit type."
    ::= { pmTcaLspPeOutBytes1hEntry 3 }

pmTcaLspPeOutBytes1hCnt         OBJECT-TYPE
    SYNTAX          Counter64
    MAX-ACCESS      read-only
    STATUS          current
    DESCRIPTION
        "1hour counter of lsp-pe out bytes."
    ::= { pmTcaLspPeOutBytes1hEntry 4 }

pmTcaLspPeOutBytes1hThreshold         OBJECT-TYPE
    SYNTAX          Counter64
    MAX-ACCESS      read-only
    STATUS          current
    DESCRIPTION
        "1hour threshold of lsp-pe out bytes."
    ::= { pmTcaLspPeOutBytes1hEntry 5 }

pmTcaLspPeOutBytes1hOccurTime         OBJECT-TYPE
    SYNTAX          DateAndTime
    MAX-ACCESS      read-only
    STATUS          current
    DESCRIPTION
        "Time of the occurrence of the tca."
    ::= { pmTcaLspPeOutBytes1hEntry 6 }

pmTcaLspPeOutBytes1dTable     OBJECT-TYPE
    SYNTAX          SEQUENCE OF PMTcaLspPeOutBytes1dEntry
    MAX-ACCESS      not-accessible
    STATUS          current
    DESCRIPTION
        "A table that contains lsp-pe information of all units."
    ::= { pmLspPe 12 }

pmTcaLspPeOutBytes1dEntry     OBJECT-TYPE
    SYNTAX          PMTcaLspPeOutBytes1dEntry
    MAX-ACCESS      not-accessible
    STATUS          current
    DESCRIPTION
        "A list of lsp-pe information of all units."
    INDEX     { pmTcaLspPeOutBytes1dIndex  }
    ::= { pmTcaLspPeOutBytes1dTable 1 }

PMTcaLspPeOutBytes1dEntry    ::=
    SEQUENCE
    {
       pmTcaLspPeOutBytes1dIndex      Integer32,
       pmTcaLspPeOutBytes1dId     OCTET STRING,
       pmTcaLspPeOutBytes1dUnitType  INTEGER,
       pmTcaLspPeOutBytes1dCnt     Counter64,
       pmTcaLspPeOutBytes1dThreshold   Counter64,
       pmTcaLspPeOutBytes1dOccurTime   DateAndTime
    }

pmTcaLspPeOutBytes1dIndex         OBJECT-TYPE
    SYNTAX          Integer32
    MAX-ACCESS      not-accessible
    STATUS          current
    DESCRIPTION
        "An index of units."
    ::= { pmTcaLspPeOutBytes1dEntry 1 }

pmTcaLspPeOutBytes1dId         OBJECT-TYPE
    SYNTAX          OCTET STRING
    MAX-ACCESS      read-only
    STATUS          current
    DESCRIPTION
        "Lsp-pe name."
    ::= { pmTcaLspPeOutBytes1dEntry 2 }

pmTcaLspPeOutBytes1dUnitType         OBJECT-TYPE
    SYNTAX          INTEGER
    {
       mcu(0)
    }
    MAX-ACCESS      read-only
    STATUS          current
    DESCRIPTION
        "Unit type."
    ::= { pmTcaLspPeOutBytes1dEntry 3 }

pmTcaLspPeOutBytes1dCnt         OBJECT-TYPE
    SYNTAX          Counter64
    MAX-ACCESS      read-only
    STATUS          current
    DESCRIPTION
        "1day counter of lsp-pe out bytes."
    ::= { pmTcaLspPeOutBytes1dEntry 4 }

pmTcaLspPeOutBytes1dThreshold         OBJECT-TYPE
    SYNTAX          Counter64
    MAX-ACCESS      read-only
    STATUS          current
    DESCRIPTION
        "1day threshold of lsp-pe out bytes."
    ::= { pmTcaLspPeOutBytes1dEntry 5 }

pmTcaLspPeOutBytes1dOccurTime         OBJECT-TYPE
    SYNTAX          DateAndTime
    MAX-ACCESS      read-only
    STATUS          current
    DESCRIPTION
        "Time of the occurrence of the tca."
    ::= { pmTcaLspPeOutBytes1dEntry 6 }


pmLspP        OBJECT IDENTIFIER ::= { pm 104 }


pmLspPCurr15mTable     OBJECT-TYPE
    SYNTAX          SEQUENCE OF PMLspPCurr15mEntry
    MAX-ACCESS      not-accessible
    STATUS          current
    DESCRIPTION
        "A table that contains lsp-p information of all units."
    ::= { pmLspP 1 }

pmLspPCurr15mEntry     OBJECT-TYPE
    SYNTAX          PMLspPCurr15mEntry
    MAX-ACCESS      not-accessible
    STATUS          current
    DESCRIPTION
        "A list of ls-p information of all units."
    INDEX     { pmLspPCurr15mIndex  }
    ::= { pmLspPCurr15mTable 1 }

PMLspPCurr15mEntry    ::=
    SEQUENCE
    {
       pmLspPCurr15mIndex     Integer32,
       pmLspPCurr15mId    OCTET STRING,
       pmLspPCurr15mUnitType  INTEGER,
       pmLspPCurr15mEastInPkts    Counter64,
       pmLspPCurr15mEastInBytes    Counter64,
       pmLspPCurr15mWestInPkts    Counter64,
       pmLspPCurr15mWestInBytes    Counter64,
       pmLspPCurr15mStartTime  DateAndTime,
       pmLspPCurr15mStopTime  DateAndTime
    }

pmLspPCurr15mIndex         OBJECT-TYPE
    SYNTAX          Integer32
    MAX-ACCESS      not-accessible
    STATUS          current
    DESCRIPTION
        "An index of units."
    ::= { pmLspPCurr15mEntry 1 }

pmLspPCurr15mId         OBJECT-TYPE
    SYNTAX          OCTET STRING
    MAX-ACCESS      read-only
    STATUS          current
    DESCRIPTION
        "Lsp-p name."
    ::= { pmLspPCurr15mEntry 2 }

pmLspPCurr15mUnitType         OBJECT-TYPE
    SYNTAX          INTEGER
    {
       mcu(0)
    }
    MAX-ACCESS      read-only
    STATUS          current
    DESCRIPTION
        "Unit type."
    ::= { pmLspPCurr15mEntry 3 }

pmLspPCurr15mEastInPkts         OBJECT-TYPE
    SYNTAX          Counter64
    MAX-ACCESS      read-only
    STATUS          current
    DESCRIPTION
        "Current 15min counter of lsp-p east ingress packets."
    ::= { pmLspPCurr15mEntry 4 }

pmLspPCurr15mEastInBytes         OBJECT-TYPE
    SYNTAX          Counter64
    MAX-ACCESS      read-only
    STATUS          current
    DESCRIPTION
        "Current 15min counter of lsp-p east ingress bytes."
    ::= { pmLspPCurr15mEntry 5 }

pmLspPCurr15mWestInPkts         OBJECT-TYPE
    SYNTAX          Counter64
    MAX-ACCESS      read-only
    STATUS          current
    DESCRIPTION
        "Current 15min counter of lsp-p west ingress packets."
    ::= { pmLspPCurr15mEntry 6 }

pmLspPCurr15mWestInBytes         OBJECT-TYPE
    SYNTAX          Counter64
    MAX-ACCESS      read-only
    STATUS          current
    DESCRIPTION
        "Current 15min counter of lsp-p west ingress bytes."
    ::= { pmLspPCurr15mEntry 7 }

pmLspPCurr15mStartTime         OBJECT-TYPE
    SYNTAX          DateAndTime
    MAX-ACCESS      read-only
    STATUS          current
    DESCRIPTION
        "Current 15min start time."
    ::= { pmLspPCurr15mEntry 100 }

pmLspPCurr15mStopTime         OBJECT-TYPE
    SYNTAX          DateAndTime
    MAX-ACCESS      read-only
    STATUS          current
    DESCRIPTION
        "Current 15min stop time."
    ::= { pmLspPCurr15mEntry 101 }


pmLspPPrev15mTable     OBJECT-TYPE
    SYNTAX          SEQUENCE OF PMLspPPrev15mEntry
    MAX-ACCESS      not-accessible
    STATUS          current
    DESCRIPTION
        "A table that contains lsp-p information of all units."
    ::= { pmLspP 2 }

pmLspPPrev15mEntry     OBJECT-TYPE
    SYNTAX          PMLspPPrev15mEntry
    MAX-ACCESS      not-accessible
    STATUS          current
    DESCRIPTION
        "A list of ls-p information of all units."
    INDEX     { pmLspPPrev15mIndex  }
    ::= { pmLspPPrev15mTable 1 }

PMLspPPrev15mEntry    ::=
    SEQUENCE
    {
       pmLspPPrev15mIndex     Integer32,
       pmLspPPrev15mId    OCTET STRING,
       pmLspPPrev15mUnitType  INTEGER,
       pmLspPPrev15mEastInPkts    Counter64,
       pmLspPPrev15mEastInBytes    Counter64,
       pmLspPPrev15mWestInPkts    Counter64,
       pmLspPPrev15mWestInBytes    Counter64,
       pmLspPPrev15mStartTime  DateAndTime,
       pmLspPPrev15mStopTime  DateAndTime
    }

pmLspPPrev15mIndex         OBJECT-TYPE
    SYNTAX          Integer32
    MAX-ACCESS      not-accessible
    STATUS          current
    DESCRIPTION
        "An index of units."
    ::= { pmLspPPrev15mEntry 1 }

pmLspPPrev15mId         OBJECT-TYPE
    SYNTAX          OCTET STRING
    MAX-ACCESS      read-only
    STATUS          current
    DESCRIPTION
        "Lsp-p name."
    ::= { pmLspPPrev15mEntry 2 }

pmLspPPrev15mUnitType         OBJECT-TYPE
    SYNTAX          INTEGER
    {
       mcu(0)
    }
    MAX-ACCESS      read-only
    STATUS          current
    DESCRIPTION
        "Unit type."
    ::= { pmLspPPrev15mEntry 3 }

pmLspPPrev15mEastInPkts         OBJECT-TYPE
    SYNTAX          Counter64
    MAX-ACCESS      read-only
    STATUS          current
    DESCRIPTION
        "Previous 15min counter of lsp-p east ingress packets."
    ::= { pmLspPPrev15mEntry 4 }

pmLspPPrev15mEastInBytes         OBJECT-TYPE
    SYNTAX          Counter64
    MAX-ACCESS      read-only
    STATUS          current
    DESCRIPTION
        "Previous 15min counter of lsp-p east ingress bytes."
    ::= { pmLspPPrev15mEntry 5 }

pmLspPPrev15mWestInPkts         OBJECT-TYPE
    SYNTAX          Counter64
    MAX-ACCESS      read-only
    STATUS          current
    DESCRIPTION
        "Previous 15min counter of lsp-p west ingress packets."
    ::= { pmLspPPrev15mEntry 6 }

pmLspPPrev15mWestInBytes         OBJECT-TYPE
    SYNTAX          Counter64
    MAX-ACCESS      read-only
    STATUS          current
    DESCRIPTION
        "Previous 15min counter of lsp-p west ingress bytes."
    ::= { pmLspPPrev15mEntry 7 }

pmLspPPrev15mStartTime         OBJECT-TYPE
    SYNTAX          DateAndTime
    MAX-ACCESS      read-only
    STATUS          current
    DESCRIPTION
        "Previous 15min start time."
    ::= { pmLspPPrev15mEntry 100 }

pmLspPPrev15mStopTime         OBJECT-TYPE
    SYNTAX          DateAndTime
    MAX-ACCESS      read-only
    STATUS          current
    DESCRIPTION
        "Previous 15min stop time."
    ::= { pmLspPPrev15mEntry 101 }


pmLspPCurr1hTable     OBJECT-TYPE
    SYNTAX          SEQUENCE OF PMLspPCurr1hEntry
    MAX-ACCESS      not-accessible
    STATUS          current
    DESCRIPTION
        "A table that contains lsp-p information of all units."
    ::= { pmLspP 3 }

pmLspPCurr1hEntry     OBJECT-TYPE
    SYNTAX          PMLspPCurr1hEntry
    MAX-ACCESS      not-accessible
    STATUS          current
    DESCRIPTION
        "A list of ls-p information of all units."
    INDEX     { pmLspPCurr1hIndex  }
    ::= { pmLspPCurr1hTable 1 }

PMLspPCurr1hEntry    ::=
    SEQUENCE
    {
       pmLspPCurr1hIndex     Integer32,
       pmLspPCurr1hId    OCTET STRING,
       pmLspPCurr1hUnitType  INTEGER,
       pmLspPCurr1hEastInPkts    Counter64,
       pmLspPCurr1hEastInBytes    Counter64,
       pmLspPCurr1hWestInPkts    Counter64,
       pmLspPCurr1hWestInBytes    Counter64,
       pmLspPCurr1hStartTime  DateAndTime,
       pmLspPCurr1hStopTime  DateAndTime
    }

pmLspPCurr1hIndex         OBJECT-TYPE
    SYNTAX          Integer32
    MAX-ACCESS      not-accessible
    STATUS          current
    DESCRIPTION
        "An index of units."
    ::= { pmLspPCurr1hEntry 1 }

pmLspPCurr1hId         OBJECT-TYPE
    SYNTAX          OCTET STRING
    MAX-ACCESS      read-only
    STATUS          current
    DESCRIPTION
        "Lsp-p name."
    ::= { pmLspPCurr1hEntry 2 }

pmLspPCurr1hUnitType         OBJECT-TYPE
    SYNTAX          INTEGER
    {
       mcu(0)
    }
    MAX-ACCESS      read-only
    STATUS          current
    DESCRIPTION
        "Unit type."
    ::= { pmLspPCurr1hEntry 3 }

pmLspPCurr1hEastInPkts         OBJECT-TYPE
    SYNTAX          Counter64
    MAX-ACCESS      read-only
    STATUS          current
    DESCRIPTION
        "Current 1hour counter of lsp-p east ingress packets."
    ::= { pmLspPCurr1hEntry 4 }

pmLspPCurr1hEastInBytes         OBJECT-TYPE
    SYNTAX          Counter64
    MAX-ACCESS      read-only
    STATUS          current
    DESCRIPTION
        "Current 1hour counter of lsp-p east ingress bytes."
    ::= { pmLspPCurr1hEntry 5 }

pmLspPCurr1hWestInPkts         OBJECT-TYPE
    SYNTAX          Counter64
    MAX-ACCESS      read-only
    STATUS          current
    DESCRIPTION
        "Current 1hour counter of lsp-p west ingress packets."
    ::= { pmLspPCurr1hEntry 6 }

pmLspPCurr1hWestInBytes         OBJECT-TYPE
    SYNTAX          Counter64
    MAX-ACCESS      read-only
    STATUS          current
    DESCRIPTION
        "Current 1hour counter of lsp-p west ingress bytes."
    ::= { pmLspPCurr1hEntry 7 }

pmLspPCurr1hStartTime         OBJECT-TYPE
    SYNTAX          DateAndTime
    MAX-ACCESS      read-only
    STATUS          current
    DESCRIPTION
        "Current 1hour start time."
    ::= { pmLspPCurr1hEntry 100 }

pmLspPCurr1hStopTime         OBJECT-TYPE
    SYNTAX          DateAndTime
    MAX-ACCESS      read-only
    STATUS          current
    DESCRIPTION
        "Current 1hour stop time."
    ::= { pmLspPCurr1hEntry 101 }


pmLspPPrev1hTable     OBJECT-TYPE
    SYNTAX          SEQUENCE OF PMLspPPrev1hEntry
    MAX-ACCESS      not-accessible
    STATUS          current
    DESCRIPTION
        "A table that contains lsp-p information of all units."
    ::= { pmLspP 4 }

pmLspPPrev1hEntry     OBJECT-TYPE
    SYNTAX          PMLspPPrev1hEntry
    MAX-ACCESS      not-accessible
    STATUS          current
    DESCRIPTION
        "A list of ls-p information of all units."
    INDEX     { pmLspPPrev1hIndex  }
    ::= { pmLspPPrev1hTable 1 }

PMLspPPrev1hEntry    ::=
    SEQUENCE
    {
       pmLspPPrev1hIndex     Integer32,
       pmLspPPrev1hId    OCTET STRING,
       pmLspPPrev1hUnitType  INTEGER,
       pmLspPPrev1hEastInPkts    Counter64,
       pmLspPPrev1hEastInBytes    Counter64,
       pmLspPPrev1hWestInPkts    Counter64,
       pmLspPPrev1hWestInBytes    Counter64,
       pmLspPPrev1hStartTime  DateAndTime,
       pmLspPPrev1hStopTime  DateAndTime
    }

pmLspPPrev1hIndex         OBJECT-TYPE
    SYNTAX          Integer32
    MAX-ACCESS      not-accessible
    STATUS          current
    DESCRIPTION
        "An index of units."
    ::= { pmLspPPrev1hEntry 1 }

pmLspPPrev1hId         OBJECT-TYPE
    SYNTAX          OCTET STRING
    MAX-ACCESS      read-only
    STATUS          current
    DESCRIPTION
        "Lsp-p name."
    ::= { pmLspPPrev1hEntry 2 }

pmLspPPrev1hUnitType         OBJECT-TYPE
    SYNTAX          INTEGER
    {
       mcu(0)
    }
    MAX-ACCESS      read-only
    STATUS          current
    DESCRIPTION
        "Unit type."
    ::= { pmLspPPrev1hEntry 3 }

pmLspPPrev1hEastInPkts         OBJECT-TYPE
    SYNTAX          Counter64
    MAX-ACCESS      read-only
    STATUS          current
    DESCRIPTION
        "Previous 1hour counter of lsp-p east ingress packets."
    ::= { pmLspPPrev1hEntry 4 }

pmLspPPrev1hEastInBytes         OBJECT-TYPE
    SYNTAX          Counter64
    MAX-ACCESS      read-only
    STATUS          current
    DESCRIPTION
        "Previous 1hour counter of lsp-p east ingress bytes."
    ::= { pmLspPPrev1hEntry 5 }

pmLspPPrev1hWestInPkts         OBJECT-TYPE
    SYNTAX          Counter64
    MAX-ACCESS      read-only
    STATUS          current
    DESCRIPTION
        "Previous 1hour counter of lsp-p west ingress packets."
    ::= { pmLspPPrev1hEntry 6 }

pmLspPPrev1hWestInBytes         OBJECT-TYPE
    SYNTAX          Counter64
    MAX-ACCESS      read-only
    STATUS          current
    DESCRIPTION
        "Previous 1hour counter of lsp-p west ingress bytes."
    ::= { pmLspPPrev1hEntry 7 }

pmLspPPrev1hStartTime         OBJECT-TYPE
    SYNTAX          DateAndTime
    MAX-ACCESS      read-only
    STATUS          current
    DESCRIPTION
        "Previous 1hour start time."
    ::= { pmLspPPrev1hEntry 100 }

pmLspPPrev1hStopTime         OBJECT-TYPE
    SYNTAX          DateAndTime
    MAX-ACCESS      read-only
    STATUS          current
    DESCRIPTION
        "Previous 1hour stop time."
    ::= { pmLspPPrev1hEntry 101 }

pmLspPCurr1dTable     OBJECT-TYPE
    SYNTAX          SEQUENCE OF PMLspPCurr1dEntry
    MAX-ACCESS      not-accessible
    STATUS          current
    DESCRIPTION
        "A table that contains lsp-p information of all units."
    ::= { pmLspP 5 }

pmLspPCurr1dEntry     OBJECT-TYPE
    SYNTAX          PMLspPCurr1dEntry
    MAX-ACCESS      not-accessible
    STATUS          current
    DESCRIPTION
        "A list of ls-p information of all units."
    INDEX     { pmLspPCurr1dIndex  }
    ::= { pmLspPCurr1dTable 1 }

PMLspPCurr1dEntry    ::=
    SEQUENCE
    {
       pmLspPCurr1dIndex     Integer32,
       pmLspPCurr1dId    OCTET STRING,
       pmLspPCurr1dUnitType  INTEGER,
       pmLspPCurr1dEastInPkts    Counter64,
       pmLspPCurr1dEastInBytes    Counter64,
       pmLspPCurr1dWestInPkts    Counter64,
       pmLspPCurr1dWestInBytes    Counter64,
       pmLspPCurr1dStartTime  DateAndTime,
       pmLspPCurr1dStopTime  DateAndTime
    }

pmLspPCurr1dIndex         OBJECT-TYPE
    SYNTAX          Integer32
    MAX-ACCESS      not-accessible
    STATUS          current
    DESCRIPTION
        "An index of units."
    ::= { pmLspPCurr1dEntry 1 }

pmLspPCurr1dId         OBJECT-TYPE
    SYNTAX          OCTET STRING
    MAX-ACCESS      read-only
    STATUS          current
    DESCRIPTION
        "Lsp-p name."
    ::= { pmLspPCurr1dEntry 2 }

pmLspPCurr1dUnitType         OBJECT-TYPE
    SYNTAX          INTEGER
    {
       mcu(0)
    }
    MAX-ACCESS      read-only
    STATUS          current
    DESCRIPTION
        "Unit type."
    ::= { pmLspPCurr1dEntry 3 }

pmLspPCurr1dEastInPkts         OBJECT-TYPE
    SYNTAX          Counter64
    MAX-ACCESS      read-only
    STATUS          current
    DESCRIPTION
        "Current 1d counter of lsp-p east ingress packets."
    ::= { pmLspPCurr1dEntry 4 }

pmLspPCurr1dEastInBytes         OBJECT-TYPE
    SYNTAX          Counter64
    MAX-ACCESS      read-only
    STATUS          current
    DESCRIPTION
        "Current 1d counter of lsp-p east ingress bytes."
    ::= { pmLspPCurr1dEntry 5 }

pmLspPCurr1dWestInPkts         OBJECT-TYPE
    SYNTAX          Counter64
    MAX-ACCESS      read-only
    STATUS          current
    DESCRIPTION
        "Current 1d counter of lsp-p west ingress packets."
    ::= { pmLspPCurr1dEntry 6 }

pmLspPCurr1dWestInBytes         OBJECT-TYPE
    SYNTAX          Counter64
    MAX-ACCESS      read-only
    STATUS          current
    DESCRIPTION
        "Current 1d counter of lsp-p west ingress bytes."
    ::= { pmLspPCurr1dEntry 7 }

pmLspPCurr1dStartTime         OBJECT-TYPE
    SYNTAX          DateAndTime
    MAX-ACCESS      read-only
    STATUS          current
    DESCRIPTION
        "Current 1d start time."
    ::= { pmLspPCurr1dEntry 100 }

pmLspPCurr1dStopTime         OBJECT-TYPE
    SYNTAX          DateAndTime
    MAX-ACCESS      read-only
    STATUS          current
    DESCRIPTION
        "Current 1d stop time."
    ::= { pmLspPCurr1dEntry 101 }


pmLspPPrev1dTable     OBJECT-TYPE
    SYNTAX          SEQUENCE OF PMLspPPrev1dEntry
    MAX-ACCESS      not-accessible
    STATUS          current
    DESCRIPTION
        "A table that contains lsp-p information of all units."
    ::= { pmLspP 6 }

pmLspPPrev1dEntry     OBJECT-TYPE
    SYNTAX          PMLspPPrev1dEntry
    MAX-ACCESS      not-accessible
    STATUS          current
    DESCRIPTION
        "A list of ls-p information of all units."
    INDEX     { pmLspPPrev1dIndex  }
    ::= { pmLspPPrev1dTable 1 }

PMLspPPrev1dEntry    ::=
    SEQUENCE
    {
       pmLspPPrev1dIndex     Integer32,
       pmLspPPrev1dId    OCTET STRING,
       pmLspPPrev1dUnitType  INTEGER,
       pmLspPPrev1dEastInPkts    Counter64,
       pmLspPPrev1dEastInBytes    Counter64,
       pmLspPPrev1dWestInPkts    Counter64,
       pmLspPPrev1dWestInBytes    Counter64,
       pmLspPPrev1dStartTime  DateAndTime,
       pmLspPPrev1dStopTime  DateAndTime
    }

pmLspPPrev1dIndex         OBJECT-TYPE
    SYNTAX          Integer32
    MAX-ACCESS      not-accessible
    STATUS          current
    DESCRIPTION
        "An index of units."
    ::= { pmLspPPrev1dEntry 1 }

pmLspPPrev1dId         OBJECT-TYPE
    SYNTAX          OCTET STRING
    MAX-ACCESS      read-only
    STATUS          current
    DESCRIPTION
        "Lsp-p name."
    ::= { pmLspPPrev1dEntry 2 }

pmLspPPrev1dUnitType         OBJECT-TYPE
    SYNTAX          INTEGER
    {
       mcu(0)
    }
    MAX-ACCESS      read-only
    STATUS          current
    DESCRIPTION
        "Unit type."
    ::= { pmLspPPrev1dEntry 3 }

pmLspPPrev1dEastInPkts         OBJECT-TYPE
    SYNTAX          Counter64
    MAX-ACCESS      read-only
    STATUS          current
    DESCRIPTION
        "Previous 1d counter of lsp-p east ingress packets."
    ::= { pmLspPPrev1dEntry 4 }

pmLspPPrev1dEastInBytes         OBJECT-TYPE
    SYNTAX          Counter64
    MAX-ACCESS      read-only
    STATUS          current
    DESCRIPTION
        "Previous 1d counter of lsp-p east ingress bytes."
    ::= { pmLspPPrev1dEntry 5 }

pmLspPPrev1dWestInPkts         OBJECT-TYPE
    SYNTAX          Counter64
    MAX-ACCESS      read-only
    STATUS          current
    DESCRIPTION
        "Previous 1d counter of lsp-p west ingress packets."
    ::= { pmLspPPrev1dEntry 6 }

pmLspPPrev1dWestInBytes         OBJECT-TYPE
    SYNTAX          Counter64
    MAX-ACCESS      read-only
    STATUS          current
    DESCRIPTION
        "Previous 1d counter of lsp-p west ingress bytes."
    ::= { pmLspPPrev1dEntry 7 }

pmLspPPrev1dStartTime         OBJECT-TYPE
    SYNTAX          DateAndTime
    MAX-ACCESS      read-only
    STATUS          current
    DESCRIPTION
        "Previous 1d start time."
    ::= { pmLspPPrev1dEntry 100 }

pmLspPPrev1dStopTime         OBJECT-TYPE
    SYNTAX          DateAndTime
    MAX-ACCESS      read-only
    STATUS          current
    DESCRIPTION
        "Previous 1d stop time."
    ::= { pmLspPPrev1dEntry 101 }

pmTcaLspPEastInPkts15mTable     OBJECT-TYPE
    SYNTAX          SEQUENCE OF PMTcaLspPEastInPkts15mEntry
    MAX-ACCESS      not-accessible
    STATUS          current
    DESCRIPTION
        "A table that contains lsp-p information of all units."
    ::= { pmLspP 7 }

pmTcaLspPEastInPkts15mEntry     OBJECT-TYPE
    SYNTAX          PMTcaLspPEastInPkts15mEntry
    MAX-ACCESS      not-accessible
    STATUS          current
    DESCRIPTION
        "A list of lsp-p information of all units."
    INDEX     { pmTcaLspPEastInPkts15mIndex  }
    ::= { pmTcaLspPEastInPkts15mTable 1 }

PMTcaLspPEastInPkts15mEntry    ::=
    SEQUENCE
    {
       pmTcaLspPEastInPkts15mIndex      Integer32,
       pmTcaLspPEastInPkts15mId     OCTET STRING,
       pmTcaLspPEastInPkts15mUnitType   INTEGER,
       pmTcaLspPEastInPkts15mCnt     Counter64,
       pmTcaLspPEastInPkts15mThreshold   Counter64,
       pmTcaLspPEastInPkts15mOccurTime   DateAndTime
    }

pmTcaLspPEastInPkts15mIndex         OBJECT-TYPE
    SYNTAX          Integer32
    MAX-ACCESS      not-accessible
    STATUS          current
    DESCRIPTION
        "An index of units."
    ::= { pmTcaLspPEastInPkts15mEntry 1 }

pmTcaLspPEastInPkts15mId         OBJECT-TYPE
    SYNTAX          OCTET STRING
    MAX-ACCESS      read-only
    STATUS          current
    DESCRIPTION
        "Lsp-p name."
    ::= { pmTcaLspPEastInPkts15mEntry 2 }

pmTcaLspPEastInPkts15mUnitType         OBJECT-TYPE
    SYNTAX          INTEGER
    {
       mcu(0)
    }
    MAX-ACCESS      read-only
    STATUS          current
    DESCRIPTION
        "Unit type."
    ::= { pmTcaLspPEastInPkts15mEntry 3 }

pmTcaLspPEastInPkts15mCnt         OBJECT-TYPE
    SYNTAX          Counter64
    MAX-ACCESS      read-only
    STATUS          current
    DESCRIPTION
        "15min counter of lsp-p east ingress packets."
    ::= { pmTcaLspPEastInPkts15mEntry 4 }

pmTcaLspPEastInPkts15mThreshold         OBJECT-TYPE
    SYNTAX          Counter64
    MAX-ACCESS      read-only
    STATUS          current
    DESCRIPTION
        "15min threshold of lsp-p east ingress packets."
    ::= { pmTcaLspPEastInPkts15mEntry 5 }

pmTcaLspPEastInPkts15mOccurTime         OBJECT-TYPE
    SYNTAX          DateAndTime
    MAX-ACCESS      read-only
    STATUS          current
    DESCRIPTION
        "Time of the occurrence of the tca."
    ::= { pmTcaLspPEastInPkts15mEntry 6 }

pmTcaLspPEastInPkts1hTable     OBJECT-TYPE
    SYNTAX          SEQUENCE OF PMTcaLspPEastInPkts1hEntry
    MAX-ACCESS      not-accessible
    STATUS          current
    DESCRIPTION
        "A table that contains lsp-p information of all units."
    ::= { pmLspP 8 }

pmTcaLspPEastInPkts1hEntry     OBJECT-TYPE
    SYNTAX          PMTcaLspPEastInPkts1hEntry
    MAX-ACCESS      not-accessible
    STATUS          current
    DESCRIPTION
        "A list of lsp-p information of all units."
    INDEX     { pmTcaLspPEastInPkts1hIndex  }
    ::= { pmTcaLspPEastInPkts1hTable 1 }

PMTcaLspPEastInPkts1hEntry    ::=
    SEQUENCE
    {
       pmTcaLspPEastInPkts1hIndex      Integer32,
       pmTcaLspPEastInPkts1hId     OCTET STRING,
       pmTcaLspPEastInPkts1hUnitType   INTEGER,
       pmTcaLspPEastInPkts1hCnt     Counter64,
       pmTcaLspPEastInPkts1hThreshold   Counter64,
       pmTcaLspPEastInPkts1hOccurTime   DateAndTime
    }

pmTcaLspPEastInPkts1hIndex         OBJECT-TYPE
    SYNTAX          Integer32
    MAX-ACCESS      not-accessible
    STATUS          current
    DESCRIPTION
        "An index of units."
    ::= { pmTcaLspPEastInPkts1hEntry 1 }

pmTcaLspPEastInPkts1hId         OBJECT-TYPE
    SYNTAX          OCTET STRING
    MAX-ACCESS      read-only
    STATUS          current
    DESCRIPTION
        "Lsp-p name."
    ::= { pmTcaLspPEastInPkts1hEntry 2 }

pmTcaLspPEastInPkts1hUnitType         OBJECT-TYPE
    SYNTAX          INTEGER
    {
       mcu(0)
    }
    MAX-ACCESS      read-only
    STATUS          current
    DESCRIPTION
        "Unit type."
    ::= { pmTcaLspPEastInPkts1hEntry 3 }

pmTcaLspPEastInPkts1hCnt         OBJECT-TYPE
    SYNTAX          Counter64
    MAX-ACCESS      read-only
    STATUS          current
    DESCRIPTION
        "1hour counter of lsp-p east ingress packets."
    ::= { pmTcaLspPEastInPkts1hEntry 4 }

pmTcaLspPEastInPkts1hThreshold         OBJECT-TYPE
    SYNTAX          Counter64
    MAX-ACCESS      read-only
    STATUS          current
    DESCRIPTION
        "1hour threshold of lsp-p east ingress packets."
    ::= { pmTcaLspPEastInPkts1hEntry 5 }

pmTcaLspPEastInPkts1hOccurTime         OBJECT-TYPE
    SYNTAX          DateAndTime
    MAX-ACCESS      read-only
    STATUS          current
    DESCRIPTION
        "Time of the occurrence of the tca."
    ::= { pmTcaLspPEastInPkts1hEntry 6 }

pmTcaLspPEastInPkts1dTable     OBJECT-TYPE
    SYNTAX          SEQUENCE OF PMTcaLspPEastInPkts1dEntry
    MAX-ACCESS      not-accessible
    STATUS          current
    DESCRIPTION
        "A table that contains lsp-p information of all units."
    ::= { pmLspP 9 }

pmTcaLspPEastInPkts1dEntry     OBJECT-TYPE
    SYNTAX          PMTcaLspPEastInPkts1dEntry
    MAX-ACCESS      not-accessible
    STATUS          current
    DESCRIPTION
        "A list of lsp-p information of all units."
    INDEX     { pmTcaLspPEastInPkts1dIndex  }
    ::= { pmTcaLspPEastInPkts1dTable 1 }

PMTcaLspPEastInPkts1dEntry    ::=
    SEQUENCE
    {
       pmTcaLspPEastInPkts1dIndex      Integer32,
       pmTcaLspPEastInPkts1dId     OCTET STRING,
       pmTcaLspPEastInPkts1dUnitType  INTEGER,
       pmTcaLspPEastInPkts1dCnt     Counter64,
       pmTcaLspPEastInPkts1dThreshold   Counter64,
       pmTcaLspPEastInPkts1dOccurTime   DateAndTime
    }

pmTcaLspPEastInPkts1dIndex         OBJECT-TYPE
    SYNTAX          Integer32
    MAX-ACCESS      not-accessible
    STATUS          current
    DESCRIPTION
        "An index of units."
    ::= { pmTcaLspPEastInPkts1dEntry 1 }

pmTcaLspPEastInPkts1dId         OBJECT-TYPE
    SYNTAX          OCTET STRING
    MAX-ACCESS      read-only
    STATUS          current
    DESCRIPTION
        "Lsp-p name."
    ::= { pmTcaLspPEastInPkts1dEntry 2 }

pmTcaLspPEastInPkts1dUnitType         OBJECT-TYPE
    SYNTAX          INTEGER
    {
       mcu(0)
    }
    MAX-ACCESS      read-only
    STATUS          current
    DESCRIPTION
        "Unit type."
    ::= { pmTcaLspPEastInPkts1dEntry 3 }

pmTcaLspPEastInPkts1dCnt         OBJECT-TYPE
    SYNTAX          Counter64
    MAX-ACCESS      read-only
    STATUS          current
    DESCRIPTION
        "1day counter of lsp-p east ingress packets."
    ::= { pmTcaLspPEastInPkts1dEntry 4 }

pmTcaLspPEastInPkts1dThreshold         OBJECT-TYPE
    SYNTAX          Counter64
    MAX-ACCESS      read-only
    STATUS          current
    DESCRIPTION
        "1day threshold of lsp-p east ingress packets."
    ::= { pmTcaLspPEastInPkts1dEntry 5 }

pmTcaLspPEastInPkts1dOccurTime         OBJECT-TYPE
    SYNTAX          DateAndTime
    MAX-ACCESS      read-only
    STATUS          current
    DESCRIPTION
        "Time of the occurrence of the tca."
    ::= { pmTcaLspPEastInPkts1dEntry 6 }


pmTcaLspPEastInBytes15mTable     OBJECT-TYPE
    SYNTAX          SEQUENCE OF PMTcaLspPEastInBytes15mEntry
    MAX-ACCESS      not-accessible
    STATUS          current
    DESCRIPTION
        "A table that contains lsp-p information of all units."
    ::= { pmLspP 10 }

pmTcaLspPEastInBytes15mEntry     OBJECT-TYPE
    SYNTAX          PMTcaLspPEastInBytes15mEntry
    MAX-ACCESS      not-accessible
    STATUS          current
    DESCRIPTION
        "A list of lsp-p information of all units."
    INDEX     { pmTcaLspPEastInBytes15mIndex  }
    ::= { pmTcaLspPEastInBytes15mTable 1 }

PMTcaLspPEastInBytes15mEntry    ::=
    SEQUENCE
    {
       pmTcaLspPEastInBytes15mIndex      Integer32,
       pmTcaLspPEastInBytes15mId     OCTET STRING,
       pmTcaLspPEastInBytes15mUnitType   INTEGER,
       pmTcaLspPEastInBytes15mCnt     Counter64,
       pmTcaLspPEastInBytes15mThreshold   Counter64,
       pmTcaLspPEastInBytes15mOccurTime   DateAndTime
    }

pmTcaLspPEastInBytes15mIndex         OBJECT-TYPE
    SYNTAX          Integer32
    MAX-ACCESS      not-accessible
    STATUS          current
    DESCRIPTION
        "An index of units."
    ::= { pmTcaLspPEastInBytes15mEntry 1 }

pmTcaLspPEastInBytes15mId         OBJECT-TYPE
    SYNTAX          OCTET STRING
    MAX-ACCESS      read-only
    STATUS          current
    DESCRIPTION
        "Lsp-p name."
    ::= { pmTcaLspPEastInBytes15mEntry 2 }

pmTcaLspPEastInBytes15mUnitType         OBJECT-TYPE
    SYNTAX          INTEGER
    {
       mcu(0)
    }
    MAX-ACCESS      read-only
    STATUS          current
    DESCRIPTION
        "Unit type."
    ::= { pmTcaLspPEastInBytes15mEntry 3 }

pmTcaLspPEastInBytes15mCnt         OBJECT-TYPE
    SYNTAX          Counter64
    MAX-ACCESS      read-only
    STATUS          current
    DESCRIPTION
        "15min counter of lsp-p east ingress bytes."
    ::= { pmTcaLspPEastInBytes15mEntry 4 }

pmTcaLspPEastInBytes15mThreshold         OBJECT-TYPE
    SYNTAX          Counter64
    MAX-ACCESS      read-only
    STATUS          current
    DESCRIPTION
        "15min threshold of lsp-p east ingress bytes."
    ::= { pmTcaLspPEastInBytes15mEntry 5 }

pmTcaLspPEastInBytes15mOccurTime         OBJECT-TYPE
    SYNTAX          DateAndTime
    MAX-ACCESS      read-only
    STATUS          current
    DESCRIPTION
        "Time of the occurrence of the tca."
    ::= { pmTcaLspPEastInBytes15mEntry 6 }

pmTcaLspPEastInBytes1hTable     OBJECT-TYPE
    SYNTAX          SEQUENCE OF PMTcaLspPEastInBytes1hEntry
    MAX-ACCESS      not-accessible
    STATUS          current
    DESCRIPTION
        "A table that contains lsp-p information of all units."
    ::= { pmLspP 11 }

pmTcaLspPEastInBytes1hEntry     OBJECT-TYPE
    SYNTAX          PMTcaLspPEastInBytes1hEntry
    MAX-ACCESS      not-accessible
    STATUS          current
    DESCRIPTION
        "A list of lsp-p information of all units."
    INDEX     { pmTcaLspPEastInBytes1hIndex  }
    ::= { pmTcaLspPEastInBytes1hTable 1 }

PMTcaLspPEastInBytes1hEntry    ::=
    SEQUENCE
    {
       pmTcaLspPEastInBytes1hIndex      Integer32,
       pmTcaLspPEastInBytes1hId     OCTET STRING,
       pmTcaLspPEastInBytes1hUnitType   INTEGER,
       pmTcaLspPEastInBytes1hCnt     Counter64,
       pmTcaLspPEastInBytes1hThreshold   Counter64,
       pmTcaLspPEastInBytes1hOccurTime   DateAndTime
    }

pmTcaLspPEastInBytes1hIndex         OBJECT-TYPE
    SYNTAX          Integer32
    MAX-ACCESS      not-accessible
    STATUS          current
    DESCRIPTION
        "An index of units."
    ::= { pmTcaLspPEastInBytes1hEntry 1 }

pmTcaLspPEastInBytes1hId         OBJECT-TYPE
    SYNTAX          OCTET STRING
    MAX-ACCESS      read-only
    STATUS          current
    DESCRIPTION
        "Lsp-p name."
    ::= { pmTcaLspPEastInBytes1hEntry 2 }

pmTcaLspPEastInBytes1hUnitType         OBJECT-TYPE
    SYNTAX          INTEGER
    {
       mcu(0)
    }
    MAX-ACCESS      read-only
    STATUS          current
    DESCRIPTION
        "Unit type."
    ::= { pmTcaLspPEastInBytes1hEntry 3 }

pmTcaLspPEastInBytes1hCnt         OBJECT-TYPE
    SYNTAX          Counter64
    MAX-ACCESS      read-only
    STATUS          current
    DESCRIPTION
        "1hour counter of lsp-p east ingress bytes."
    ::= { pmTcaLspPEastInBytes1hEntry 4 }

pmTcaLspPEastInBytes1hThreshold         OBJECT-TYPE
    SYNTAX          Counter64
    MAX-ACCESS      read-only
    STATUS          current
    DESCRIPTION
        "1hour threshold of lsp-p east ingress bytes."
    ::= { pmTcaLspPEastInBytes1hEntry 5 }

pmTcaLspPEastInBytes1hOccurTime         OBJECT-TYPE
    SYNTAX          DateAndTime
    MAX-ACCESS      read-only
    STATUS          current
    DESCRIPTION
        "Time of the occurrence of the tca."
    ::= { pmTcaLspPEastInBytes1hEntry 6 }

pmTcaLspPEastInBytes1dTable     OBJECT-TYPE
    SYNTAX          SEQUENCE OF PMTcaLspPEastInBytes1dEntry
    MAX-ACCESS      not-accessible
    STATUS          current
    DESCRIPTION
        "A table that contains lsp-p information of all units."
    ::= { pmLspP 12 }

pmTcaLspPEastInBytes1dEntry     OBJECT-TYPE
    SYNTAX          PMTcaLspPEastInBytes1dEntry
    MAX-ACCESS      not-accessible
    STATUS          current
    DESCRIPTION
        "A list of lsp-p information of all units."
    INDEX     { pmTcaLspPEastInBytes1dIndex  }
    ::= { pmTcaLspPEastInBytes1dTable 1 }

PMTcaLspPEastInBytes1dEntry    ::=
    SEQUENCE
    {
       pmTcaLspPEastInBytes1dIndex      Integer32,
       pmTcaLspPEastInBytes1dId     OCTET STRING,
       pmTcaLspPEastInBytes1dUnitType  INTEGER,
       pmTcaLspPEastInBytes1dCnt     Counter64,
       pmTcaLspPEastInBytes1dThreshold   Counter64,
       pmTcaLspPEastInBytes1dOccurTime   DateAndTime
    }

pmTcaLspPEastInBytes1dIndex         OBJECT-TYPE
    SYNTAX          Integer32
    MAX-ACCESS      not-accessible
    STATUS          current
    DESCRIPTION
        "An index of units."
    ::= { pmTcaLspPEastInBytes1dEntry 1 }

pmTcaLspPEastInBytes1dId         OBJECT-TYPE
    SYNTAX          OCTET STRING
    MAX-ACCESS      read-only
    STATUS          current
    DESCRIPTION
        "Lsp-p name."
    ::= { pmTcaLspPEastInBytes1dEntry 2 }

pmTcaLspPEastInBytes1dUnitType         OBJECT-TYPE
    SYNTAX          INTEGER
    {
       mcu(0)
    }
    MAX-ACCESS      read-only
    STATUS          current
    DESCRIPTION
        "Unit type."
    ::= { pmTcaLspPEastInBytes1dEntry 3 }

pmTcaLspPEastInBytes1dCnt         OBJECT-TYPE
    SYNTAX          Counter64
    MAX-ACCESS      read-only
    STATUS          current
    DESCRIPTION
        "1day counter of lsp-p east ingress bytes."
    ::= { pmTcaLspPEastInBytes1dEntry 4 }

pmTcaLspPEastInBytes1dThreshold         OBJECT-TYPE
    SYNTAX          Counter64
    MAX-ACCESS      read-only
    STATUS          current
    DESCRIPTION
        "1day threshold of lsp-p east ingress bytes."
    ::= { pmTcaLspPEastInBytes1dEntry 5 }

pmTcaLspPEastInBytes1dOccurTime         OBJECT-TYPE
    SYNTAX          DateAndTime
    MAX-ACCESS      read-only
    STATUS          current
    DESCRIPTION
        "Time of the occurrence of the tca."
    ::= { pmTcaLspPEastInBytes1dEntry 6 }


pmTcaLspPWestInPkts15mTable     OBJECT-TYPE
    SYNTAX          SEQUENCE OF PMTcaLspPWestInPkts15mEntry
    MAX-ACCESS      not-accessible
    STATUS          current
    DESCRIPTION
        "A table that contains lsp-p information of all units."
    ::= { pmLspP 13 }

pmTcaLspPWestInPkts15mEntry     OBJECT-TYPE
    SYNTAX          PMTcaLspPWestInPkts15mEntry
    MAX-ACCESS      not-accessible
    STATUS          current
    DESCRIPTION
        "A list of lsp-p information of all units."
    INDEX     { pmTcaLspPWestInPkts15mIndex  }
    ::= { pmTcaLspPWestInPkts15mTable 1 }

PMTcaLspPWestInPkts15mEntry    ::=
    SEQUENCE
    {
       pmTcaLspPWestInPkts15mIndex      Integer32,
       pmTcaLspPWestInPkts15mId     OCTET STRING,
       pmTcaLspPWestInPkts15mUnitType   INTEGER,
       pmTcaLspPWestInPkts15mCnt     Counter64,
       pmTcaLspPWestInPkts15mThreshold   Counter64,
       pmTcaLspPWestInPkts15mOccurTime   DateAndTime
    }

pmTcaLspPWestInPkts15mIndex         OBJECT-TYPE
    SYNTAX          Integer32
    MAX-ACCESS      not-accessible
    STATUS          current
    DESCRIPTION
        "An index of units."
    ::= { pmTcaLspPWestInPkts15mEntry 1 }

pmTcaLspPWestInPkts15mId         OBJECT-TYPE
    SYNTAX          OCTET STRING
    MAX-ACCESS      read-only
    STATUS          current
    DESCRIPTION
        "Lsp-p name."
    ::= { pmTcaLspPWestInPkts15mEntry 2 }

pmTcaLspPWestInPkts15mUnitType         OBJECT-TYPE
    SYNTAX          INTEGER
    {
       mcu(0)
    }
    MAX-ACCESS      read-only
    STATUS          current
    DESCRIPTION
        "Unit type."
    ::= { pmTcaLspPWestInPkts15mEntry 3 }

pmTcaLspPWestInPkts15mCnt         OBJECT-TYPE
    SYNTAX          Counter64
    MAX-ACCESS      read-only
    STATUS          current
    DESCRIPTION
        "15min counter of lsp-p west ingress packets."
    ::= { pmTcaLspPWestInPkts15mEntry 4 }

pmTcaLspPWestInPkts15mThreshold         OBJECT-TYPE
    SYNTAX          Counter64
    MAX-ACCESS      read-only
    STATUS          current
    DESCRIPTION
        "15min threshold of lsp-p west ingress packets."
    ::= { pmTcaLspPWestInPkts15mEntry 5 }

pmTcaLspPWestInPkts15mOccurTime         OBJECT-TYPE
    SYNTAX          DateAndTime
    MAX-ACCESS      read-only
    STATUS          current
    DESCRIPTION
        "Time of the occurrence of the tca."
    ::= { pmTcaLspPWestInPkts15mEntry 6 }

pmTcaLspPWestInPkts1hTable     OBJECT-TYPE
    SYNTAX          SEQUENCE OF PMTcaLspPWestInPkts1hEntry
    MAX-ACCESS      not-accessible
    STATUS          current
    DESCRIPTION
        "A table that contains lsp-p information of all units."
    ::= { pmLspP 14 }

pmTcaLspPWestInPkts1hEntry     OBJECT-TYPE
    SYNTAX          PMTcaLspPWestInPkts1hEntry
    MAX-ACCESS      not-accessible
    STATUS          current
    DESCRIPTION
        "A list of lsp-p information of all units."
    INDEX     { pmTcaLspPWestInPkts1hIndex  }
    ::= { pmTcaLspPWestInPkts1hTable 1 }

PMTcaLspPWestInPkts1hEntry    ::=
    SEQUENCE
    {
       pmTcaLspPWestInPkts1hIndex      Integer32,
       pmTcaLspPWestInPkts1hId     OCTET STRING,
       pmTcaLspPWestInPkts1hUnitType   INTEGER,
       pmTcaLspPWestInPkts1hCnt     Counter64,
       pmTcaLspPWestInPkts1hThreshold   Counter64,
       pmTcaLspPWestInPkts1hOccurTime   DateAndTime
    }

pmTcaLspPWestInPkts1hIndex         OBJECT-TYPE
    SYNTAX          Integer32
    MAX-ACCESS      not-accessible
    STATUS          current
    DESCRIPTION
        "An index of units."
    ::= { pmTcaLspPWestInPkts1hEntry 1 }

pmTcaLspPWestInPkts1hId         OBJECT-TYPE
    SYNTAX          OCTET STRING
    MAX-ACCESS      read-only
    STATUS          current
    DESCRIPTION
        "Lsp-p name."
    ::= { pmTcaLspPWestInPkts1hEntry 2 }

pmTcaLspPWestInPkts1hUnitType         OBJECT-TYPE
    SYNTAX          INTEGER
    {
       mcu(0)
    }
    MAX-ACCESS      read-only
    STATUS          current
    DESCRIPTION
        "Unit type."
    ::= { pmTcaLspPWestInPkts1hEntry 3 }

pmTcaLspPWestInPkts1hCnt         OBJECT-TYPE
    SYNTAX          Counter64
    MAX-ACCESS      read-only
    STATUS          current
    DESCRIPTION
        "1hour counter of lsp-p west ingress packets."
    ::= { pmTcaLspPWestInPkts1hEntry 4 }

pmTcaLspPWestInPkts1hThreshold         OBJECT-TYPE
    SYNTAX          Counter64
    MAX-ACCESS      read-only
    STATUS          current
    DESCRIPTION
        "1hour threshold of lsp-p west ingress packets."
    ::= { pmTcaLspPWestInPkts1hEntry 5 }

pmTcaLspPWestInPkts1hOccurTime         OBJECT-TYPE
    SYNTAX          DateAndTime
    MAX-ACCESS      read-only
    STATUS          current
    DESCRIPTION
        "Time of the occurrence of the tca."
    ::= { pmTcaLspPWestInPkts1hEntry 6 }

pmTcaLspPWestInPkts1dTable     OBJECT-TYPE
    SYNTAX          SEQUENCE OF PMTcaLspPWestInPkts1dEntry
    MAX-ACCESS      not-accessible
    STATUS          current
    DESCRIPTION
        "A table that contains lsp-p information of all units."
    ::= { pmLspP 15 }

pmTcaLspPWestInPkts1dEntry     OBJECT-TYPE
    SYNTAX          PMTcaLspPWestInPkts1dEntry
    MAX-ACCESS      not-accessible
    STATUS          current
    DESCRIPTION
        "A list of lsp-p information of all units."
    INDEX     { pmTcaLspPWestInPkts1dIndex  }
    ::= { pmTcaLspPWestInPkts1dTable 1 }

PMTcaLspPWestInPkts1dEntry    ::=
    SEQUENCE
    {
       pmTcaLspPWestInPkts1dIndex      Integer32,
       pmTcaLspPWestInPkts1dId     OCTET STRING,
       pmTcaLspPWestInPkts1dUnitType  INTEGER,
       pmTcaLspPWestInPkts1dCnt     Counter64,
       pmTcaLspPWestInPkts1dThreshold   Counter64,
       pmTcaLspPWestInPkts1dOccurTime   DateAndTime
    }

pmTcaLspPWestInPkts1dIndex         OBJECT-TYPE
    SYNTAX          Integer32
    MAX-ACCESS      not-accessible
    STATUS          current
    DESCRIPTION
        "An index of units."
    ::= { pmTcaLspPWestInPkts1dEntry 1 }

pmTcaLspPWestInPkts1dId         OBJECT-TYPE
    SYNTAX          OCTET STRING
    MAX-ACCESS      read-only
    STATUS          current
    DESCRIPTION
        "Lsp-p name."
    ::= { pmTcaLspPWestInPkts1dEntry 2 }

pmTcaLspPWestInPkts1dUnitType         OBJECT-TYPE
    SYNTAX          INTEGER
    {
       mcu(0)
    }
    MAX-ACCESS      read-only
    STATUS          current
    DESCRIPTION
        "Unit type."
    ::= { pmTcaLspPWestInPkts1dEntry 3 }

pmTcaLspPWestInPkts1dCnt         OBJECT-TYPE
    SYNTAX          Counter64
    MAX-ACCESS      read-only
    STATUS          current
    DESCRIPTION
        "1day counter of lsp-p west ingress packets."
    ::= { pmTcaLspPWestInPkts1dEntry 4 }

pmTcaLspPWestInPkts1dThreshold         OBJECT-TYPE
    SYNTAX          Counter64
    MAX-ACCESS      read-only
    STATUS          current
    DESCRIPTION
        "1day threshold of lsp-p west ingress packets."
    ::= { pmTcaLspPWestInPkts1dEntry 5 }

pmTcaLspPWestInPkts1dOccurTime         OBJECT-TYPE
    SYNTAX          DateAndTime
    MAX-ACCESS      read-only
    STATUS          current
    DESCRIPTION
        "Time of the occurrence of the tca."
    ::= { pmTcaLspPWestInPkts1dEntry 6 }


pmTcaLspPWestInBytes15mTable     OBJECT-TYPE
    SYNTAX          SEQUENCE OF PMTcaLspPWestInBytes15mEntry
    MAX-ACCESS      not-accessible
    STATUS          current
    DESCRIPTION
        "A table that contains lsp-p information of all units."
    ::= { pmLspP 16 }

pmTcaLspPWestInBytes15mEntry     OBJECT-TYPE
    SYNTAX          PMTcaLspPWestInBytes15mEntry
    MAX-ACCESS      not-accessible
    STATUS          current
    DESCRIPTION
        "A list of lsp-p information of all units."
    INDEX     { pmTcaLspPWestInBytes15mIndex  }
    ::= { pmTcaLspPWestInBytes15mTable 1 }

PMTcaLspPWestInBytes15mEntry    ::=
    SEQUENCE
    {
       pmTcaLspPWestInBytes15mIndex      Integer32,
       pmTcaLspPWestInBytes15mId     OCTET STRING,
       pmTcaLspPWestInBytes15mUnitType   INTEGER,
       pmTcaLspPWestInBytes15mCnt     Counter64,
       pmTcaLspPWestInBytes15mThreshold   Counter64,
       pmTcaLspPWestInBytes15mOccurTime   DateAndTime
    }

pmTcaLspPWestInBytes15mIndex         OBJECT-TYPE
    SYNTAX          Integer32
    MAX-ACCESS      not-accessible
    STATUS          current
    DESCRIPTION
        "An index of units."
    ::= { pmTcaLspPWestInBytes15mEntry 1 }

pmTcaLspPWestInBytes15mId         OBJECT-TYPE
    SYNTAX          OCTET STRING
    MAX-ACCESS      read-only
    STATUS          current
    DESCRIPTION
        "Lsp-p name."
    ::= { pmTcaLspPWestInBytes15mEntry 2 }

pmTcaLspPWestInBytes15mUnitType         OBJECT-TYPE
    SYNTAX          INTEGER
    {
       mcu(0)
    }
    MAX-ACCESS      read-only
    STATUS          current
    DESCRIPTION
        "Unit type."
    ::= { pmTcaLspPWestInBytes15mEntry 3 }

pmTcaLspPWestInBytes15mCnt         OBJECT-TYPE
    SYNTAX          Counter64
    MAX-ACCESS      read-only
    STATUS          current
    DESCRIPTION
        "15min counter of lsp-p west ingress bytes."
    ::= { pmTcaLspPWestInBytes15mEntry 4 }

pmTcaLspPWestInBytes15mThreshold         OBJECT-TYPE
    SYNTAX          Counter64
    MAX-ACCESS      read-only
    STATUS          current
    DESCRIPTION
        "15min threshold of lsp-p west ingress bytes."
    ::= { pmTcaLspPWestInBytes15mEntry 5 }

pmTcaLspPWestInBytes15mOccurTime         OBJECT-TYPE
    SYNTAX          DateAndTime
    MAX-ACCESS      read-only
    STATUS          current
    DESCRIPTION
        "Time of the occurrence of the tca."
    ::= { pmTcaLspPWestInBytes15mEntry 6 }

pmTcaLspPWestInBytes1hTable     OBJECT-TYPE
    SYNTAX          SEQUENCE OF PMTcaLspPWestInBytes1hEntry
    MAX-ACCESS      not-accessible
    STATUS          current
    DESCRIPTION
        "A table that contains lsp-p information of all units."
    ::= { pmLspP 17 }

pmTcaLspPWestInBytes1hEntry     OBJECT-TYPE
    SYNTAX          PMTcaLspPWestInBytes1hEntry
    MAX-ACCESS      not-accessible
    STATUS          current
    DESCRIPTION
        "A list of lsp-p information of all units."
    INDEX     { pmTcaLspPWestInBytes1hIndex  }
    ::= { pmTcaLspPWestInBytes1hTable 1 }

PMTcaLspPWestInBytes1hEntry    ::=
    SEQUENCE
    {
       pmTcaLspPWestInBytes1hIndex      Integer32,
       pmTcaLspPWestInBytes1hId     OCTET STRING,
       pmTcaLspPWestInBytes1hUnitType   INTEGER,
       pmTcaLspPWestInBytes1hCnt     Counter64,
       pmTcaLspPWestInBytes1hThreshold   Counter64,
       pmTcaLspPWestInBytes1hOccurTime   DateAndTime
    }

pmTcaLspPWestInBytes1hIndex         OBJECT-TYPE
    SYNTAX          Integer32
    MAX-ACCESS      not-accessible
    STATUS          current
    DESCRIPTION
        "An index of units."
    ::= { pmTcaLspPWestInBytes1hEntry 1 }

pmTcaLspPWestInBytes1hId         OBJECT-TYPE
    SYNTAX          OCTET STRING
    MAX-ACCESS      read-only
    STATUS          current
    DESCRIPTION
        "Lsp-p name."
    ::= { pmTcaLspPWestInBytes1hEntry 2 }

pmTcaLspPWestInBytes1hUnitType         OBJECT-TYPE
    SYNTAX          INTEGER
    {
       mcu(0)
    }
    MAX-ACCESS      read-only
    STATUS          current
    DESCRIPTION
        "Unit type."
    ::= { pmTcaLspPWestInBytes1hEntry 3 }

pmTcaLspPWestInBytes1hCnt         OBJECT-TYPE
    SYNTAX          Counter64
    MAX-ACCESS      read-only
    STATUS          current
    DESCRIPTION
        "1hour counter of lsp-p west ingress bytes."
    ::= { pmTcaLspPWestInBytes1hEntry 4 }

pmTcaLspPWestInBytes1hThreshold         OBJECT-TYPE
    SYNTAX          Counter64
    MAX-ACCESS      read-only
    STATUS          current
    DESCRIPTION
        "1hour threshold of lsp-p west ingress bytes."
    ::= { pmTcaLspPWestInBytes1hEntry 5 }

pmTcaLspPWestInBytes1hOccurTime         OBJECT-TYPE
    SYNTAX          DateAndTime
    MAX-ACCESS      read-only
    STATUS          current
    DESCRIPTION
        "Time of the occurrence of the tca."
    ::= { pmTcaLspPWestInBytes1hEntry 6 }

pmTcaLspPWestInBytes1dTable     OBJECT-TYPE
    SYNTAX          SEQUENCE OF PMTcaLspPWestInBytes1dEntry
    MAX-ACCESS      not-accessible
    STATUS          current
    DESCRIPTION
        "A table that contains lsp-p information of all units."
    ::= { pmLspP 18 }

pmTcaLspPWestInBytes1dEntry     OBJECT-TYPE
    SYNTAX          PMTcaLspPWestInBytes1dEntry
    MAX-ACCESS      not-accessible
    STATUS          current
    DESCRIPTION
        "A list of temperature lsp-p of all units."
    INDEX     { pmTcaLspPWestInBytes1dIndex  }
    ::= { pmTcaLspPWestInBytes1dTable 1 }

PMTcaLspPWestInBytes1dEntry    ::=
    SEQUENCE
    {
       pmTcaLspPWestInBytes1dIndex      Integer32,
       pmTcaLspPWestInBytes1dId     OCTET STRING,
       pmTcaLspPWestInBytes1dUnitType  INTEGER,
       pmTcaLspPWestInBytes1dCnt     Counter64,
       pmTcaLspPWestInBytes1dThreshold   Counter64,
       pmTcaLspPWestInBytes1dOccurTime   DateAndTime
    }

pmTcaLspPWestInBytes1dIndex         OBJECT-TYPE
    SYNTAX          Integer32
    MAX-ACCESS      not-accessible
    STATUS          current
    DESCRIPTION
        "An index of units."
    ::= { pmTcaLspPWestInBytes1dEntry 1 }

pmTcaLspPWestInBytes1dId         OBJECT-TYPE
    SYNTAX          OCTET STRING
    MAX-ACCESS      read-only
    STATUS          current
    DESCRIPTION
        "Lsp-p name."
    ::= { pmTcaLspPWestInBytes1dEntry 2 }

pmTcaLspPWestInBytes1dUnitType         OBJECT-TYPE
    SYNTAX          INTEGER
    {
       mcu(0)
    }
    MAX-ACCESS      read-only
    STATUS          current
    DESCRIPTION
        "Unit type."
    ::= { pmTcaLspPWestInBytes1dEntry 3 }

pmTcaLspPWestInBytes1dCnt         OBJECT-TYPE
    SYNTAX          Counter64
    MAX-ACCESS      read-only
    STATUS          current
    DESCRIPTION
        "1day counter of lsp-p west ingress bytes."
    ::= { pmTcaLspPWestInBytes1dEntry 4 }

pmTcaLspPWestInBytes1dThreshold         OBJECT-TYPE
    SYNTAX          Counter64
    MAX-ACCESS      read-only
    STATUS          current
    DESCRIPTION
        "1day threshold of lsp-p west ingress bytes."
    ::= { pmTcaLspPWestInBytes1dEntry 5 }

pmTcaLspPWestInBytes1dOccurTime         OBJECT-TYPE
    SYNTAX          DateAndTime
    MAX-ACCESS      read-only
    STATUS          current
    DESCRIPTION
        "Time of the occurrence of the tca."
    ::= { pmTcaLspPWestInBytes1dEntry 6 }


pmVpws        OBJECT IDENTIFIER ::= { pm 105 }

pmVpwsCurr15mTable     OBJECT-TYPE
    SYNTAX          SEQUENCE OF PMVpwsCurr15mEntry
    MAX-ACCESS      not-accessible
    STATUS          current
    DESCRIPTION
        "A table that contains vpws information of all units."
    ::= { pmVpws 1 }

pmVpwsCurr15mEntry     OBJECT-TYPE
    SYNTAX          PMVpwsCurr15mEntry
    MAX-ACCESS      not-accessible
    STATUS          current
    DESCRIPTION
        "A list of vpws information of all units."
    INDEX     { pmVpwsCurr15mIndex  }
    ::= { pmVpwsCurr15mTable 1 }

PMVpwsCurr15mEntry    ::=
    SEQUENCE
    {
       pmVpwsCurr15mIndex     Integer32,
       pmVpwsCurr15mId    OCTET STRING,
       pmVpwsCurr15mUnitType  INTEGER,
       pmVpwsCurr15mIngressPkts    Counter64,
       pmVpwsCurr15mIngressBytes    Counter64,
       pmVpwsCurr15mEgressPkts    Counter64,
       pmVpwsCurr15mEgressBytes    Counter64,
       pmVpwsCurr15mStartTime  DateAndTime,
       pmVpwsCurr15mStopTime  DateAndTime
    }

pmVpwsCurr15mIndex         OBJECT-TYPE
    SYNTAX          Integer32
    MAX-ACCESS      not-accessible
    STATUS          current
    DESCRIPTION
        "An index of units."
    ::= { pmVpwsCurr15mEntry 1 }

pmVpwsCurr15mId         OBJECT-TYPE
    SYNTAX          OCTET STRING
    MAX-ACCESS      read-only
    STATUS          current
    DESCRIPTION
        "Vpws name."
    ::= { pmVpwsCurr15mEntry 2 }

pmVpwsCurr15mUnitType         OBJECT-TYPE
    SYNTAX          INTEGER
    {
       mcu(0)
    }
    MAX-ACCESS      read-only
    STATUS          current
    DESCRIPTION
        "Unit type."
    ::= { pmVpwsCurr15mEntry 3 }

pmVpwsCurr15mIngressPkts         OBJECT-TYPE
    SYNTAX          Counter64
    MAX-ACCESS      read-only
    STATUS          current
    DESCRIPTION
        "Current 15min counter of vpws ingress packets."
    ::= { pmVpwsCurr15mEntry 4 }

pmVpwsCurr15mIngressBytes         OBJECT-TYPE
    SYNTAX          Counter64
    MAX-ACCESS      read-only
    STATUS          current
    DESCRIPTION
        "Current 15min counter of vpws ingress bytes."
    ::= { pmVpwsCurr15mEntry 5 }

pmVpwsCurr15mEgressPkts         OBJECT-TYPE
    SYNTAX          Counter64
    MAX-ACCESS      read-only
    STATUS          current
    DESCRIPTION
        "Current 15min counter of vpws egress packets."
    ::= { pmVpwsCurr15mEntry 6 }

pmVpwsCurr15mEgressBytes         OBJECT-TYPE
    SYNTAX          Counter64
    MAX-ACCESS      read-only
    STATUS          current
    DESCRIPTION
        "Current 15min counter of vpws egress bytes."
    ::= { pmVpwsCurr15mEntry 7 }

pmVpwsCurr15mStartTime         OBJECT-TYPE
    SYNTAX          DateAndTime
    MAX-ACCESS      read-only
    STATUS          current
    DESCRIPTION
        "Current 15min start time."
    ::= { pmVpwsCurr15mEntry 100 }

pmVpwsCurr15mStopTime         OBJECT-TYPE
    SYNTAX          DateAndTime
    MAX-ACCESS      read-only
    STATUS          current
    DESCRIPTION
        "Current 15min stop time."
    ::= { pmVpwsCurr15mEntry 101 }


pmVpwsPrev15mTable     OBJECT-TYPE
    SYNTAX          SEQUENCE OF PMVpwsPrev15mEntry
    MAX-ACCESS      not-accessible
    STATUS          current
    DESCRIPTION
        "A table that contains vpws information of all units."
    ::= { pmVpws 2 }

pmVpwsPrev15mEntry     OBJECT-TYPE
    SYNTAX          PMVpwsPrev15mEntry
    MAX-ACCESS      not-accessible
    STATUS          current
    DESCRIPTION
        "A list of vpws information of all units."
    INDEX     { pmVpwsPrev15mIndex  }
    ::= { pmVpwsPrev15mTable 1 }

PMVpwsPrev15mEntry    ::=
    SEQUENCE
    {
       pmVpwsPrev15mIndex     Integer32,
       pmVpwsPrev15mId    OCTET STRING,
       pmVpwsPrev15mUnitType  INTEGER,
       pmVpwsPrev15mIngressPkts    Counter64,
       pmVpwsPrev15mIngressBytes    Counter64,
       pmVpwsPrev15mEgressPkts    Counter64,
       pmVpwsPrev15mEgressBytes    Counter64,
       pmVpwsPrev15mStartTime  DateAndTime,
       pmVpwsPrev15mStopTime  DateAndTime
    }

pmVpwsPrev15mIndex         OBJECT-TYPE
    SYNTAX          Integer32
    MAX-ACCESS      not-accessible
    STATUS          current
    DESCRIPTION
        "An index of units."
    ::= { pmVpwsPrev15mEntry 1 }

pmVpwsPrev15mId         OBJECT-TYPE
    SYNTAX          OCTET STRING
    MAX-ACCESS      read-only
    STATUS          current
    DESCRIPTION
        "Vpws name."
    ::= { pmVpwsPrev15mEntry 2 }

pmVpwsPrev15mUnitType         OBJECT-TYPE
    SYNTAX          INTEGER
    {
       mcu(0)
    }
    MAX-ACCESS      read-only
    STATUS          current
    DESCRIPTION
        "Unit type."
    ::= { pmVpwsPrev15mEntry 3 }

pmVpwsPrev15mIngressPkts         OBJECT-TYPE
    SYNTAX          Counter64
    MAX-ACCESS      read-only
    STATUS          current
    DESCRIPTION
        "Previous 15min counter of vpws ingress packets."
    ::= { pmVpwsPrev15mEntry 4 }

pmVpwsPrev15mIngressBytes         OBJECT-TYPE
    SYNTAX          Counter64
    MAX-ACCESS      read-only
    STATUS          current
    DESCRIPTION
        "Previous 15min counter of vpws ingress bytes."
    ::= { pmVpwsPrev15mEntry 5 }

pmVpwsPrev15mEgressPkts         OBJECT-TYPE
    SYNTAX          Counter64
    MAX-ACCESS      read-only
    STATUS          current
    DESCRIPTION
        "Previous 15min counter of vpws egress packets."
    ::= { pmVpwsPrev15mEntry 6 }

pmVpwsPrev15mEgressBytes         OBJECT-TYPE
    SYNTAX          Counter64
    MAX-ACCESS      read-only
    STATUS          current
    DESCRIPTION
        "Previous 15min counter of vpws egress bytes."
    ::= { pmVpwsPrev15mEntry 7 }

pmVpwsPrev15mStartTime         OBJECT-TYPE
    SYNTAX          DateAndTime
    MAX-ACCESS      read-only
    STATUS          current
    DESCRIPTION
        "Previous 15min start time."
    ::= { pmVpwsPrev15mEntry 100 }

pmVpwsPrev15mStopTime         OBJECT-TYPE
    SYNTAX          DateAndTime
    MAX-ACCESS      read-only
    STATUS          current
    DESCRIPTION
        "Previous 15min stop time."
    ::= { pmVpwsPrev15mEntry 101 }


pmVpwsCurr1hTable     OBJECT-TYPE
    SYNTAX          SEQUENCE OF PMVpwsCurr1hEntry
    MAX-ACCESS      not-accessible
    STATUS          current
    DESCRIPTION
        "A table that contains vpws information of all units."
    ::= { pmVpws 3 }

pmVpwsCurr1hEntry     OBJECT-TYPE
    SYNTAX          PMVpwsCurr1hEntry
    MAX-ACCESS      not-accessible
    STATUS          current
    DESCRIPTION
        "A list of vpws information of all units."
    INDEX     { pmVpwsCurr1hIndex  }
    ::= { pmVpwsCurr1hTable 1 }

PMVpwsCurr1hEntry    ::=
    SEQUENCE
    {
       pmVpwsCurr1hIndex     Integer32,
       pmVpwsCurr1hId    OCTET STRING,
       pmVpwsCurr1hUnitType  INTEGER,
       pmVpwsCurr1hIngressPkts    Counter64,
       pmVpwsCurr1hIngressBytes    Counter64,
       pmVpwsCurr1hEgressPkts    Counter64,
       pmVpwsCurr1hEgressBytes    Counter64,
       pmVpwsCurr1hStartTime  DateAndTime,
       pmVpwsCurr1hStopTime  DateAndTime
    }

pmVpwsCurr1hIndex         OBJECT-TYPE
    SYNTAX          Integer32
    MAX-ACCESS      not-accessible
    STATUS          current
    DESCRIPTION
        "An index of units."
    ::= { pmVpwsCurr1hEntry 1 }

pmVpwsCurr1hId         OBJECT-TYPE
    SYNTAX          OCTET STRING
    MAX-ACCESS      read-only
    STATUS          current
    DESCRIPTION
        "Vpws name."
    ::= { pmVpwsCurr1hEntry 2 }

pmVpwsCurr1hUnitType         OBJECT-TYPE
    SYNTAX          INTEGER
    {
       mcu(0)
    }
    MAX-ACCESS      read-only
    STATUS          current
    DESCRIPTION
        "Unit type."
    ::= { pmVpwsCurr1hEntry 3 }

pmVpwsCurr1hIngressPkts         OBJECT-TYPE
    SYNTAX          Counter64
    MAX-ACCESS      read-only
    STATUS          current
    DESCRIPTION
        "Current 1hour counter of vpws ingress packets."
    ::= { pmVpwsCurr1hEntry 4 }

pmVpwsCurr1hIngressBytes         OBJECT-TYPE
    SYNTAX          Counter64
    MAX-ACCESS      read-only
    STATUS          current
    DESCRIPTION
        "Current 1hour counter of vpws ingress bytes."
    ::= { pmVpwsCurr1hEntry 5 }

pmVpwsCurr1hEgressPkts         OBJECT-TYPE
    SYNTAX          Counter64
    MAX-ACCESS      read-only
    STATUS          current
    DESCRIPTION
        "Current 1hour counter of vpws egress packets."
    ::= { pmVpwsCurr1hEntry 6 }

pmVpwsCurr1hEgressBytes         OBJECT-TYPE
    SYNTAX          Counter64
    MAX-ACCESS      read-only
    STATUS          current
    DESCRIPTION
        "Current 1hour counter of vpws egress bytes."
    ::= { pmVpwsCurr1hEntry 7 }

pmVpwsCurr1hStartTime         OBJECT-TYPE
    SYNTAX          DateAndTime
    MAX-ACCESS      read-only
    STATUS          current
    DESCRIPTION
        "Current 1hour start time."
    ::= { pmVpwsCurr1hEntry 100 }

pmVpwsCurr1hStopTime         OBJECT-TYPE
    SYNTAX          DateAndTime
    MAX-ACCESS      read-only
    STATUS          current
    DESCRIPTION
        "Current 1hour stop time."
    ::= { pmVpwsCurr1hEntry 101 }


pmVpwsPrev1hTable     OBJECT-TYPE
    SYNTAX          SEQUENCE OF PMVpwsPrev1hEntry
    MAX-ACCESS      not-accessible
    STATUS          current
    DESCRIPTION
        "A table that contains vpws information of all units."
    ::= { pmVpws 4 }

pmVpwsPrev1hEntry     OBJECT-TYPE
    SYNTAX          PMVpwsPrev1hEntry
    MAX-ACCESS      not-accessible
    STATUS          current
    DESCRIPTION
        "A list of vpws information of all units."
    INDEX     { pmVpwsPrev1hIndex  }
    ::= { pmVpwsPrev1hTable 1 }

PMVpwsPrev1hEntry    ::=
    SEQUENCE
    {
       pmVpwsPrev1hIndex     Integer32,
       pmVpwsPrev1hId    OCTET STRING,
       pmVpwsPrev1hUnitType  INTEGER,
       pmVpwsPrev1hIngressPkts    Counter64,
       pmVpwsPrev1hIngressBytes    Counter64,
       pmVpwsPrev1hEgressPkts    Counter64,
       pmVpwsPrev1hEgressBytes    Counter64,
       pmVpwsPrev1hStartTime  DateAndTime,
       pmVpwsPrev1hStopTime  DateAndTime
    }

pmVpwsPrev1hIndex         OBJECT-TYPE
    SYNTAX          Integer32
    MAX-ACCESS      not-accessible
    STATUS          current
    DESCRIPTION
        "An index of units."
    ::= { pmVpwsPrev1hEntry 1 }

pmVpwsPrev1hId         OBJECT-TYPE
    SYNTAX          OCTET STRING
    MAX-ACCESS      read-only
    STATUS          current
    DESCRIPTION
        "Vpws name."
    ::= { pmVpwsPrev1hEntry 2 }

pmVpwsPrev1hUnitType         OBJECT-TYPE
    SYNTAX          INTEGER
    {
       mcu(0)
    }
    MAX-ACCESS      read-only
    STATUS          current
    DESCRIPTION
        "Unit type."
    ::= { pmVpwsPrev1hEntry 3 }

pmVpwsPrev1hIngressPkts         OBJECT-TYPE
    SYNTAX          Counter64
    MAX-ACCESS      read-only
    STATUS          current
    DESCRIPTION
        "Previous 1hour counter of vpws ingress packets."
    ::= { pmVpwsPrev1hEntry 4 }

pmVpwsPrev1hIngressBytes         OBJECT-TYPE
    SYNTAX          Counter64
    MAX-ACCESS      read-only
    STATUS          current
    DESCRIPTION
        "Previous 1hour counter of vpws ingress bytes."
    ::= { pmVpwsPrev1hEntry 5 }

pmVpwsPrev1hEgressPkts         OBJECT-TYPE
    SYNTAX          Counter64
    MAX-ACCESS      read-only
    STATUS          current
    DESCRIPTION
        "Previous 1hour counter of vpws egress packets."
    ::= { pmVpwsPrev1hEntry 6 }

pmVpwsPrev1hEgressBytes         OBJECT-TYPE
    SYNTAX          Counter64
    MAX-ACCESS      read-only
    STATUS          current
    DESCRIPTION
        "Previous 1hour counter of vpws egress bytes."
    ::= { pmVpwsPrev1hEntry 7 }

pmVpwsPrev1hStartTime         OBJECT-TYPE
    SYNTAX          DateAndTime
    MAX-ACCESS      read-only
    STATUS          current
    DESCRIPTION
        "Previous 1hour start time."
    ::= { pmVpwsPrev1hEntry 100 }

pmVpwsPrev1hStopTime         OBJECT-TYPE
    SYNTAX          DateAndTime
    MAX-ACCESS      read-only
    STATUS          current
    DESCRIPTION
        "Previous 1hour stop time."
    ::= { pmVpwsPrev1hEntry 101 }

pmVpwsCurr1dTable     OBJECT-TYPE
    SYNTAX          SEQUENCE OF PMVpwsCurr1dEntry
    MAX-ACCESS      not-accessible
    STATUS          current
    DESCRIPTION
        "A table that contains vpws information of all units."
    ::= { pmVpws 5 }

pmVpwsCurr1dEntry     OBJECT-TYPE
    SYNTAX          PMVpwsCurr1dEntry
    MAX-ACCESS      not-accessible
    STATUS          current
    DESCRIPTION
        "A list of vpws information of all units."
    INDEX     { pmVpwsCurr1dIndex  }
    ::= { pmVpwsCurr1dTable 1 }

PMVpwsCurr1dEntry    ::=
    SEQUENCE
    {
       pmVpwsCurr1dIndex     Integer32,
       pmVpwsCurr1dId    OCTET STRING,
       pmVpwsCurr1dUnitType  INTEGER,
       pmVpwsCurr1dIngressPkts    Counter64,
       pmVpwsCurr1dIngressBytes    Counter64,
       pmVpwsCurr1dEgressPkts    Counter64,
       pmVpwsCurr1dEgressBytes    Counter64,
       pmVpwsCurr1dStartTime  DateAndTime,
       pmVpwsCurr1dStopTime  DateAndTime
    }

pmVpwsCurr1dIndex         OBJECT-TYPE
    SYNTAX          Integer32
    MAX-ACCESS      not-accessible
    STATUS          current
    DESCRIPTION
        "An index of units."
    ::= { pmVpwsCurr1dEntry 1 }

pmVpwsCurr1dId         OBJECT-TYPE
    SYNTAX          OCTET STRING
    MAX-ACCESS      read-only
    STATUS          current
    DESCRIPTION
        "Vpws name."
    ::= { pmVpwsCurr1dEntry 2 }

pmVpwsCurr1dUnitType         OBJECT-TYPE
    SYNTAX          INTEGER
    {
       mcu(0)
    }
    MAX-ACCESS      read-only
    STATUS          current
    DESCRIPTION
        "Unit type."
    ::= { pmVpwsCurr1dEntry 3 }

pmVpwsCurr1dIngressPkts         OBJECT-TYPE
    SYNTAX          Counter64
    MAX-ACCESS      read-only
    STATUS          current
    DESCRIPTION
        "Current 1day counter of vpws ingress packets."
    ::= { pmVpwsCurr1dEntry 4 }

pmVpwsCurr1dIngressBytes         OBJECT-TYPE
    SYNTAX          Counter64
    MAX-ACCESS      read-only
    STATUS          current
    DESCRIPTION
        "Current 1day counter of vpws ingress bytes."
    ::= { pmVpwsCurr1dEntry 5 }

pmVpwsCurr1dEgressPkts         OBJECT-TYPE
    SYNTAX          Counter64
    MAX-ACCESS      read-only
    STATUS          current
    DESCRIPTION
        "Current 1day counter of vpws egress packets."
    ::= { pmVpwsCurr1dEntry 6 }

pmVpwsCurr1dEgressBytes         OBJECT-TYPE
    SYNTAX          Counter64
    MAX-ACCESS      read-only
    STATUS          current
    DESCRIPTION
        "Current 1day counter of vpws egress bytes."
    ::= { pmVpwsCurr1dEntry 7 }

pmVpwsCurr1dStartTime         OBJECT-TYPE
    SYNTAX          DateAndTime
    MAX-ACCESS      read-only
    STATUS          current
    DESCRIPTION
        "Current 1day start time."
    ::= { pmVpwsCurr1dEntry 100 }

pmVpwsCurr1dStopTime         OBJECT-TYPE
    SYNTAX          DateAndTime
    MAX-ACCESS      read-only
    STATUS          current
    DESCRIPTION
        "Current 1day stop time."
    ::= { pmVpwsCurr1dEntry 101 }


pmVpwsPrev1dTable     OBJECT-TYPE
    SYNTAX          SEQUENCE OF PMVpwsPrev1dEntry
    MAX-ACCESS      not-accessible
    STATUS          current
    DESCRIPTION
        "A table that contains vpws information of all units."
    ::= { pmVpws 6 }

pmVpwsPrev1dEntry     OBJECT-TYPE
    SYNTAX          PMVpwsPrev1dEntry
    MAX-ACCESS      not-accessible
    STATUS          current
    DESCRIPTION
        "A list of vpws information of all units."
    INDEX     { pmVpwsPrev1dIndex  }
    ::= { pmVpwsPrev1dTable 1 }

PMVpwsPrev1dEntry    ::=
    SEQUENCE
    {
       pmVpwsPrev1dIndex     Integer32,
       pmVpwsPrev1dId    OCTET STRING,
       pmVpwsPrev1dUnitType  INTEGER,
       pmVpwsPrev1dIngressPkts    Counter64,
       pmVpwsPrev1dIngressBytes    Counter64,
       pmVpwsPrev1dEgressPkts    Counter64,
       pmVpwsPrev1dEgressBytes    Counter64,
       pmVpwsPrev1dStartTime  DateAndTime,
       pmVpwsPrev1dStopTime  DateAndTime
    }

pmVpwsPrev1dIndex         OBJECT-TYPE
    SYNTAX          Integer32
    MAX-ACCESS      not-accessible
    STATUS          current
    DESCRIPTION
        "An index of units."
    ::= { pmVpwsPrev1dEntry 1 }

pmVpwsPrev1dId         OBJECT-TYPE
    SYNTAX          OCTET STRING
    MAX-ACCESS      read-only
    STATUS          current
    DESCRIPTION
        "Vpws name."
    ::= { pmVpwsPrev1dEntry 2 }

pmVpwsPrev1dUnitType         OBJECT-TYPE
    SYNTAX          INTEGER
    {
       mcu(0)
    }
    MAX-ACCESS      read-only
    STATUS          current
    DESCRIPTION
        "Unit type."
    ::= { pmVpwsPrev1dEntry 3 }

pmVpwsPrev1dIngressPkts         OBJECT-TYPE
    SYNTAX          Counter64
    MAX-ACCESS      read-only
    STATUS          current
    DESCRIPTION
        "Previous 1day counter of vpws ingress packets."
    ::= { pmVpwsPrev1dEntry 4 }

pmVpwsPrev1dIngressBytes         OBJECT-TYPE
    SYNTAX          Counter64
    MAX-ACCESS      read-only
    STATUS          current
    DESCRIPTION
        "Previous 1day counter of vpws ingress bytes."
    ::= { pmVpwsPrev1dEntry 5 }

pmVpwsPrev1dEgressPkts         OBJECT-TYPE
    SYNTAX          Counter64
    MAX-ACCESS      read-only
    STATUS          current
    DESCRIPTION
        "Previous 1day counter of vpws egress packets."
    ::= { pmVpwsPrev1dEntry 6 }

pmVpwsPrev1dEgressBytes         OBJECT-TYPE
    SYNTAX          Counter64
    MAX-ACCESS      read-only
    STATUS          current
    DESCRIPTION
        "Previous 1day counter of vpws egress bytes."
    ::= { pmVpwsPrev1dEntry 7 }

pmVpwsPrev1dStartTime         OBJECT-TYPE
    SYNTAX          DateAndTime
    MAX-ACCESS      read-only
    STATUS          current
    DESCRIPTION
        "Previous 1day start time."
    ::= { pmVpwsPrev1dEntry 100 }

pmVpwsPrev1dStopTime         OBJECT-TYPE
    SYNTAX          DateAndTime
    MAX-ACCESS      read-only
    STATUS          current
    DESCRIPTION
        "Previous 1day stop time."
    ::= { pmVpwsPrev1dEntry 101 }

pmTcaVpwsIngressPkts15mTable     OBJECT-TYPE
    SYNTAX          SEQUENCE OF PMTcaVpwsIngressPkts15mEntry
    MAX-ACCESS      not-accessible
    STATUS          current
    DESCRIPTION
        "A table that contains vpws information of all units."
    ::= { pmVpws 7 }

pmTcaVpwsIngressPkts15mEntry     OBJECT-TYPE
    SYNTAX          PMTcaVpwsIngressPkts15mEntry
    MAX-ACCESS      not-accessible
    STATUS          current
    DESCRIPTION
        "A list of vpws information of all units."
    INDEX     { pmTcaVpwsIngressPkts15mIndex  }
    ::= { pmTcaVpwsIngressPkts15mTable 1 }

PMTcaVpwsIngressPkts15mEntry    ::=
    SEQUENCE
    {
       pmTcaVpwsIngressPkts15mIndex      Integer32,
       pmTcaVpwsIngressPkts15mId     OCTET STRING,
       pmTcaVpwsIngressPkts15mUnitType   INTEGER,
       pmTcaVpwsIngressPkts15mCnt     Counter64,
       pmTcaVpwsIngressPkts15mThreshold   Counter64,
       pmTcaVpwsIngressPkts15mOccurTime   DateAndTime
    }

pmTcaVpwsIngressPkts15mIndex         OBJECT-TYPE
    SYNTAX          Integer32
    MAX-ACCESS      not-accessible
    STATUS          current
    DESCRIPTION
        "An index of units."
    ::= { pmTcaVpwsIngressPkts15mEntry 1 }

pmTcaVpwsIngressPkts15mId         OBJECT-TYPE
    SYNTAX          OCTET STRING
    MAX-ACCESS      read-only
    STATUS          current
    DESCRIPTION
        "Vpws name."
    ::= { pmTcaVpwsIngressPkts15mEntry 2 }

pmTcaVpwsIngressPkts15mUnitType         OBJECT-TYPE
    SYNTAX          INTEGER
    {
       mcu(0)
    }
    MAX-ACCESS      read-only
    STATUS          current
    DESCRIPTION
        "Unit type."
    ::= { pmTcaVpwsIngressPkts15mEntry 3 }

pmTcaVpwsIngressPkts15mCnt         OBJECT-TYPE
    SYNTAX          Counter64
    MAX-ACCESS      read-only
    STATUS          current
    DESCRIPTION
        "15min counter of vpws ingress packets."
    ::= { pmTcaVpwsIngressPkts15mEntry 4 }

pmTcaVpwsIngressPkts15mThreshold         OBJECT-TYPE
    SYNTAX          Counter64
    MAX-ACCESS      read-only
    STATUS          current
    DESCRIPTION
        "15min threshold of vpws ingress packets."
    ::= { pmTcaVpwsIngressPkts15mEntry 5 }

pmTcaVpwsIngressPkts15mOccurTime         OBJECT-TYPE
    SYNTAX          DateAndTime
    MAX-ACCESS      read-only
    STATUS          current
    DESCRIPTION
        "Time of the occurrence of the tca."
    ::= { pmTcaVpwsIngressPkts15mEntry 6 }

pmTcaVpwsIngressPkts1hTable     OBJECT-TYPE
    SYNTAX          SEQUENCE OF PMTcaVpwsIngressPkts1hEntry
    MAX-ACCESS      not-accessible
    STATUS          current
    DESCRIPTION
        "A table that contains vpws information of all units."
    ::= { pmVpws 8 }

pmTcaVpwsIngressPkts1hEntry     OBJECT-TYPE
    SYNTAX          PMTcaVpwsIngressPkts1hEntry
    MAX-ACCESS      not-accessible
    STATUS          current
    DESCRIPTION
        "A list of vpws information of all units."
    INDEX     { pmTcaVpwsIngressPkts1hIndex  }
    ::= { pmTcaVpwsIngressPkts1hTable 1 }

PMTcaVpwsIngressPkts1hEntry    ::=
    SEQUENCE
    {
       pmTcaVpwsIngressPkts1hIndex      Integer32,
       pmTcaVpwsIngressPkts1hId     OCTET STRING,
       pmTcaVpwsIngressPkts1hUnitType   INTEGER,
       pmTcaVpwsIngressPkts1hCnt     Counter64,
       pmTcaVpwsIngressPkts1hThreshold   Counter64,
       pmTcaVpwsIngressPkts1hOccurTime   DateAndTime
    }

pmTcaVpwsIngressPkts1hIndex         OBJECT-TYPE
    SYNTAX          Integer32
    MAX-ACCESS      not-accessible
    STATUS          current
    DESCRIPTION
        "An index of units."
    ::= { pmTcaVpwsIngressPkts1hEntry 1 }

pmTcaVpwsIngressPkts1hId         OBJECT-TYPE
    SYNTAX          OCTET STRING
    MAX-ACCESS      read-only
    STATUS          current
    DESCRIPTION
        "Vpws name."
    ::= { pmTcaVpwsIngressPkts1hEntry 2 }

pmTcaVpwsIngressPkts1hUnitType         OBJECT-TYPE
    SYNTAX          INTEGER
    {
       mcu(0)
    }
    MAX-ACCESS      read-only
    STATUS          current
    DESCRIPTION
        "Unit type."
    ::= { pmTcaVpwsIngressPkts1hEntry 3 }

pmTcaVpwsIngressPkts1hCnt         OBJECT-TYPE
    SYNTAX          Counter64
    MAX-ACCESS      read-only
    STATUS          current
    DESCRIPTION
        "1hour counter of vpws ingress packets."
    ::= { pmTcaVpwsIngressPkts1hEntry 4 }

pmTcaVpwsIngressPkts1hThreshold         OBJECT-TYPE
    SYNTAX          Counter64
    MAX-ACCESS      read-only
    STATUS          current
    DESCRIPTION
        "1hour threshold of vpws ingress packets."
    ::= { pmTcaVpwsIngressPkts1hEntry 5 }

pmTcaVpwsIngressPkts1hOccurTime         OBJECT-TYPE
    SYNTAX          DateAndTime
    MAX-ACCESS      read-only
    STATUS          current
    DESCRIPTION
        "Time of the occurrence of the tca."
    ::= { pmTcaVpwsIngressPkts1hEntry 6 }

pmTcaVpwsIngressPkts1dTable     OBJECT-TYPE
    SYNTAX          SEQUENCE OF PMTcaVpwsIngressPkts1dEntry
    MAX-ACCESS      not-accessible
    STATUS          current
    DESCRIPTION
        "A table that contains vpws information of all units."
    ::= { pmVpws 9 }

pmTcaVpwsIngressPkts1dEntry     OBJECT-TYPE
    SYNTAX          PMTcaVpwsIngressPkts1dEntry
    MAX-ACCESS      not-accessible
    STATUS          current
    DESCRIPTION
        "A list of vpws information of all units."
    INDEX     { pmTcaVpwsIngressPkts1dIndex  }
    ::= { pmTcaVpwsIngressPkts1dTable 1 }

PMTcaVpwsIngressPkts1dEntry    ::=
    SEQUENCE
    {
       pmTcaVpwsIngressPkts1dIndex      Integer32,
       pmTcaVpwsIngressPkts1dId     OCTET STRING,
       pmTcaVpwsIngressPkts1dUnitType  INTEGER,
       pmTcaVpwsIngressPkts1dCnt     Counter64,
       pmTcaVpwsIngressPkts1dThreshold   Counter64,
       pmTcaVpwsIngressPkts1dOccurTime   DateAndTime
    }

pmTcaVpwsIngressPkts1dIndex         OBJECT-TYPE
    SYNTAX          Integer32
    MAX-ACCESS      not-accessible
    STATUS          current
    DESCRIPTION
        "An index of units."
    ::= { pmTcaVpwsIngressPkts1dEntry 1 }

pmTcaVpwsIngressPkts1dId         OBJECT-TYPE
    SYNTAX          OCTET STRING
    MAX-ACCESS      read-only
    STATUS          current
    DESCRIPTION
        "Vpws name."
    ::= { pmTcaVpwsIngressPkts1dEntry 2 }

pmTcaVpwsIngressPkts1dUnitType         OBJECT-TYPE
    SYNTAX          INTEGER
    {
       mcu(0)
    }
    MAX-ACCESS      read-only
    STATUS          current
    DESCRIPTION
        "Unit type."
    ::= { pmTcaVpwsIngressPkts1dEntry 3 }

pmTcaVpwsIngressPkts1dCnt         OBJECT-TYPE
    SYNTAX          Counter64
    MAX-ACCESS      read-only
    STATUS          current
    DESCRIPTION
        "1day counter of vpws ingress packets."
    ::= { pmTcaVpwsIngressPkts1dEntry 4 }

pmTcaVpwsIngressPkts1dThreshold         OBJECT-TYPE
    SYNTAX          Counter64
    MAX-ACCESS      read-only
    STATUS          current
    DESCRIPTION
        "1day threshold of vpws ingress packets."
    ::= { pmTcaVpwsIngressPkts1dEntry 5 }

pmTcaVpwsIngressPkts1dOccurTime         OBJECT-TYPE
    SYNTAX          DateAndTime
    MAX-ACCESS      read-only
    STATUS          current
    DESCRIPTION
        "Time of the occurrence of the tca."
    ::= { pmTcaVpwsIngressPkts1dEntry 6 }


pmTcaVpwsIngressBytes15mTable     OBJECT-TYPE
    SYNTAX          SEQUENCE OF PMTcaVpwsIngressBytes15mEntry
    MAX-ACCESS      not-accessible
    STATUS          current
    DESCRIPTION
        "A table that contains vpws information of all units."
    ::= { pmVpws 10 }

pmTcaVpwsIngressBytes15mEntry     OBJECT-TYPE
    SYNTAX          PMTcaVpwsIngressBytes15mEntry
    MAX-ACCESS      not-accessible
    STATUS          current
    DESCRIPTION
        "A list of vpws information of all units."
    INDEX     { pmTcaVpwsIngressBytes15mIndex  }
    ::= { pmTcaVpwsIngressBytes15mTable 1 }

PMTcaVpwsIngressBytes15mEntry    ::=
    SEQUENCE
    {
       pmTcaVpwsIngressBytes15mIndex      Integer32,
       pmTcaVpwsIngressBytes15mId     OCTET STRING,
       pmTcaVpwsIngressBytes15mUnitType   INTEGER,
       pmTcaVpwsIngressBytes15mCnt     Counter64,
       pmTcaVpwsIngressBytes15mThreshold   Counter64,
       pmTcaVpwsIngressBytes15mOccurTime   DateAndTime
    }

pmTcaVpwsIngressBytes15mIndex         OBJECT-TYPE
    SYNTAX          Integer32
    MAX-ACCESS      not-accessible
    STATUS          current
    DESCRIPTION
        "An index of units."
    ::= { pmTcaVpwsIngressBytes15mEntry 1 }

pmTcaVpwsIngressBytes15mId         OBJECT-TYPE
    SYNTAX          OCTET STRING
    MAX-ACCESS      read-only
    STATUS          current
    DESCRIPTION
        "Vpws name."
    ::= { pmTcaVpwsIngressBytes15mEntry 2 }

pmTcaVpwsIngressBytes15mUnitType         OBJECT-TYPE
    SYNTAX          INTEGER
    {
       mcu(0)
    }
    MAX-ACCESS      read-only
    STATUS          current
    DESCRIPTION
        "Unit type."
    ::= { pmTcaVpwsIngressBytes15mEntry 3 }

pmTcaVpwsIngressBytes15mCnt         OBJECT-TYPE
    SYNTAX          Counter64
    MAX-ACCESS      read-only
    STATUS          current
    DESCRIPTION
        "15min counter of vpws ingress bytes."
    ::= { pmTcaVpwsIngressBytes15mEntry 4 }

pmTcaVpwsIngressBytes15mThreshold         OBJECT-TYPE
    SYNTAX          Counter64
    MAX-ACCESS      read-only
    STATUS          current
    DESCRIPTION
        "15min threshold of vpws ingress bytes."
    ::= { pmTcaVpwsIngressBytes15mEntry 5 }

pmTcaVpwsIngressBytes15mOccurTime         OBJECT-TYPE
    SYNTAX          DateAndTime
    MAX-ACCESS      read-only
    STATUS          current
    DESCRIPTION
        "Time of the occurrence of the tca."
    ::= { pmTcaVpwsIngressBytes15mEntry 6 }

pmTcaVpwsIngressBytes1hTable     OBJECT-TYPE
    SYNTAX          SEQUENCE OF PMTcaVpwsIngressBytes1hEntry
    MAX-ACCESS      not-accessible
    STATUS          current
    DESCRIPTION
        "A table that contains vpws information of all units."
    ::= { pmVpws 11 }

pmTcaVpwsIngressBytes1hEntry     OBJECT-TYPE
    SYNTAX          PMTcaVpwsIngressBytes1hEntry
    MAX-ACCESS      not-accessible
    STATUS          current
    DESCRIPTION
        "A list of vpws information of all units."
    INDEX     { pmTcaVpwsIngressBytes1hIndex  }
    ::= { pmTcaVpwsIngressBytes1hTable 1 }

PMTcaVpwsIngressBytes1hEntry    ::=
    SEQUENCE
    {
       pmTcaVpwsIngressBytes1hIndex      Integer32,
       pmTcaVpwsIngressBytes1hId     OCTET STRING,
       pmTcaVpwsIngressBytes1hUnitType   INTEGER,
       pmTcaVpwsIngressBytes1hCnt     Counter64,
       pmTcaVpwsIngressBytes1hThreshold   Counter64,
       pmTcaVpwsIngressBytes1hOccurTime   DateAndTime
    }

pmTcaVpwsIngressBytes1hIndex         OBJECT-TYPE
    SYNTAX          Integer32
    MAX-ACCESS      not-accessible
    STATUS          current
    DESCRIPTION
        "An index of units."
    ::= { pmTcaVpwsIngressBytes1hEntry 1 }

pmTcaVpwsIngressBytes1hId         OBJECT-TYPE
    SYNTAX          OCTET STRING
    MAX-ACCESS      read-only
    STATUS          current
    DESCRIPTION
        "Vpws name."
    ::= { pmTcaVpwsIngressBytes1hEntry 2 }

pmTcaVpwsIngressBytes1hUnitType         OBJECT-TYPE
    SYNTAX          INTEGER
    {
       mcu(0)
    }
    MAX-ACCESS      read-only
    STATUS          current
    DESCRIPTION
        "Unit type."
    ::= { pmTcaVpwsIngressBytes1hEntry 3 }

pmTcaVpwsIngressBytes1hCnt         OBJECT-TYPE
    SYNTAX          Counter64
    MAX-ACCESS      read-only
    STATUS          current
    DESCRIPTION
        "1hour counter of vpws ingress bytes."
    ::= { pmTcaVpwsIngressBytes1hEntry 4 }

pmTcaVpwsIngressBytes1hThreshold         OBJECT-TYPE
    SYNTAX          Counter64
    MAX-ACCESS      read-only
    STATUS          current
    DESCRIPTION
        "1hour threshold of vpws ingress bytes."
    ::= { pmTcaVpwsIngressBytes1hEntry 5 }

pmTcaVpwsIngressBytes1hOccurTime         OBJECT-TYPE
    SYNTAX          DateAndTime
    MAX-ACCESS      read-only
    STATUS          current
    DESCRIPTION
        "Time of the occurrence of the tca."
    ::= { pmTcaVpwsIngressBytes1hEntry 6 }


pmTcaVpwsIngressBytes1dTable     OBJECT-TYPE
    SYNTAX          SEQUENCE OF PMTcaVpwsIngressBytes1dEntry
    MAX-ACCESS      not-accessible
    STATUS          current
    DESCRIPTION
        "A table that contains vpws information of all units."
    ::= { pmVpws 12 }

pmTcaVpwsIngressBytes1dEntry     OBJECT-TYPE
    SYNTAX          PMTcaVpwsIngressBytes1dEntry
    MAX-ACCESS      not-accessible
    STATUS          current
    DESCRIPTION
        "A list of vpws information of all units."
    INDEX     { pmTcaVpwsIngressBytes1dIndex  }
    ::= { pmTcaVpwsIngressBytes1dTable 1 }

PMTcaVpwsIngressBytes1dEntry    ::=
    SEQUENCE
    {
       pmTcaVpwsIngressBytes1dIndex      Integer32,
       pmTcaVpwsIngressBytes1dId     OCTET STRING,
       pmTcaVpwsIngressBytes1dUnitType  INTEGER,
       pmTcaVpwsIngressBytes1dCnt     Counter64,
       pmTcaVpwsIngressBytes1dThreshold   Counter64,
       pmTcaVpwsIngressBytes1dOccurTime   DateAndTime
    }

pmTcaVpwsIngressBytes1dIndex         OBJECT-TYPE
    SYNTAX          Integer32
    MAX-ACCESS      not-accessible
    STATUS          current
    DESCRIPTION
        "An index of units."
    ::= { pmTcaVpwsIngressBytes1dEntry 1 }

pmTcaVpwsIngressBytes1dId         OBJECT-TYPE
    SYNTAX          OCTET STRING
    MAX-ACCESS      read-only
    STATUS          current
    DESCRIPTION
        "Vpws name."
    ::= { pmTcaVpwsIngressBytes1dEntry 2 }

pmTcaVpwsIngressBytes1dUnitType         OBJECT-TYPE
    SYNTAX          INTEGER
    {
       mcu(0)
    }
    MAX-ACCESS      read-only
    STATUS          current
    DESCRIPTION
        "Unit type."
    ::= { pmTcaVpwsIngressBytes1dEntry 3 }

pmTcaVpwsIngressBytes1dCnt         OBJECT-TYPE
    SYNTAX          Counter64
    MAX-ACCESS      read-only
    STATUS          current
    DESCRIPTION
        "1day counter of vpws ingress bytes."
    ::= { pmTcaVpwsIngressBytes1dEntry 4 }

pmTcaVpwsIngressBytes1dThreshold         OBJECT-TYPE
    SYNTAX          Counter64
    MAX-ACCESS      read-only
    STATUS          current
    DESCRIPTION
        "1day threshold of vpws ingress bytes."
    ::= { pmTcaVpwsIngressBytes1dEntry 5 }

pmTcaVpwsIngressBytes1dOccurTime         OBJECT-TYPE
    SYNTAX          DateAndTime
    MAX-ACCESS      read-only
    STATUS          current
    DESCRIPTION
        "Time of the occurrence of the tca."
    ::= { pmTcaVpwsIngressBytes1dEntry 6 }


pmTcaVpwsEgressPkts15mTable     OBJECT-TYPE
    SYNTAX          SEQUENCE OF PMTcaVpwsEgressPkts15mEntry
    MAX-ACCESS      not-accessible
    STATUS          current
    DESCRIPTION
        "A table that contains vpws information of all units."
    ::= { pmVpws 13 }

pmTcaVpwsEgressPkts15mEntry     OBJECT-TYPE
    SYNTAX          PMTcaVpwsEgressPkts15mEntry
    MAX-ACCESS      not-accessible
    STATUS          current
    DESCRIPTION
        "A list of vpws information of all units."
    INDEX     { pmTcaVpwsEgressPkts15mIndex  }
    ::= { pmTcaVpwsEgressPkts15mTable 1 }

PMTcaVpwsEgressPkts15mEntry    ::=
    SEQUENCE
    {
       pmTcaVpwsEgressPkts15mIndex      Integer32,
       pmTcaVpwsEgressPkts15mId     OCTET STRING,
       pmTcaVpwsEgressPkts15mUnitType   INTEGER,
       pmTcaVpwsEgressPkts15mCnt     Counter64,
       pmTcaVpwsEgressPkts15mThreshold   Counter64,
       pmTcaVpwsEgressPkts15mOccurTime   DateAndTime
    }

pmTcaVpwsEgressPkts15mIndex         OBJECT-TYPE
    SYNTAX          Integer32
    MAX-ACCESS      not-accessible
    STATUS          current
    DESCRIPTION
        "An index of units."
    ::= { pmTcaVpwsEgressPkts15mEntry 1 }

pmTcaVpwsEgressPkts15mId         OBJECT-TYPE
    SYNTAX          OCTET STRING
    MAX-ACCESS      read-only
    STATUS          current
    DESCRIPTION
        "Vpws name."
    ::= { pmTcaVpwsEgressPkts15mEntry 2 }

pmTcaVpwsEgressPkts15mUnitType         OBJECT-TYPE
    SYNTAX          INTEGER
    {
       mcu(0)
    }
    MAX-ACCESS      read-only
    STATUS          current
    DESCRIPTION
        "Unit type."
    ::= { pmTcaVpwsEgressPkts15mEntry 3 }

pmTcaVpwsEgressPkts15mCnt         OBJECT-TYPE
    SYNTAX          Counter64
    MAX-ACCESS      read-only
    STATUS          current
    DESCRIPTION
        "15min counter of vpws egress packets."
    ::= { pmTcaVpwsEgressPkts15mEntry 4 }

pmTcaVpwsEgressPkts15mThreshold         OBJECT-TYPE
    SYNTAX          Counter64
    MAX-ACCESS      read-only
    STATUS          current
    DESCRIPTION
        "15min threshold of vpws egress packets."
    ::= { pmTcaVpwsEgressPkts15mEntry 5 }

pmTcaVpwsEgressPkts15mOccurTime         OBJECT-TYPE
    SYNTAX          DateAndTime
    MAX-ACCESS      read-only
    STATUS          current
    DESCRIPTION
        "Time of the occurrence of the tca."
    ::= { pmTcaVpwsEgressPkts15mEntry 6 }

pmTcaVpwsEgressPkts1hTable     OBJECT-TYPE
    SYNTAX          SEQUENCE OF PMTcaVpwsEgressPkts1hEntry
    MAX-ACCESS      not-accessible
    STATUS          current
    DESCRIPTION
        "A table that contains vpws information of all units."
    ::= { pmVpws 14 }

pmTcaVpwsEgressPkts1hEntry     OBJECT-TYPE
    SYNTAX          PMTcaVpwsEgressPkts1hEntry
    MAX-ACCESS      not-accessible
    STATUS          current
    DESCRIPTION
        "A list of vpws information of all units."
    INDEX     { pmTcaVpwsEgressPkts1hIndex  }
    ::= { pmTcaVpwsEgressPkts1hTable 1 }

PMTcaVpwsEgressPkts1hEntry    ::=
    SEQUENCE
    {
       pmTcaVpwsEgressPkts1hIndex      Integer32,
       pmTcaVpwsEgressPkts1hId     OCTET STRING,
       pmTcaVpwsEgressPkts1hUnitType   INTEGER,
       pmTcaVpwsEgressPkts1hCnt     Counter64,
       pmTcaVpwsEgressPkts1hThreshold   Counter64,
       pmTcaVpwsEgressPkts1hOccurTime   DateAndTime
    }

pmTcaVpwsEgressPkts1hIndex         OBJECT-TYPE
    SYNTAX          Integer32
    MAX-ACCESS      not-accessible
    STATUS          current
    DESCRIPTION
        "An index of units."
    ::= { pmTcaVpwsEgressPkts1hEntry 1 }

pmTcaVpwsEgressPkts1hId         OBJECT-TYPE
    SYNTAX          OCTET STRING
    MAX-ACCESS      read-only
    STATUS          current
    DESCRIPTION
        "Vpws name."
    ::= { pmTcaVpwsEgressPkts1hEntry 2 }

pmTcaVpwsEgressPkts1hUnitType         OBJECT-TYPE
    SYNTAX          INTEGER
    {
       mcu(0)
    }
    MAX-ACCESS      read-only
    STATUS          current
    DESCRIPTION
        "Unit type."
    ::= { pmTcaVpwsEgressPkts1hEntry 3 }

pmTcaVpwsEgressPkts1hCnt         OBJECT-TYPE
    SYNTAX          Counter64
    MAX-ACCESS      read-only
    STATUS          current
    DESCRIPTION
        "1hour counter of vpws egress packets."
    ::= { pmTcaVpwsEgressPkts1hEntry 4 }

pmTcaVpwsEgressPkts1hThreshold         OBJECT-TYPE
    SYNTAX          Counter64
    MAX-ACCESS      read-only
    STATUS          current
    DESCRIPTION
        "1hour threshold of vpws egress packets."
    ::= { pmTcaVpwsEgressPkts1hEntry 5 }

pmTcaVpwsEgressPkts1hOccurTime         OBJECT-TYPE
    SYNTAX          DateAndTime
    MAX-ACCESS      read-only
    STATUS          current
    DESCRIPTION
        "Time of the occurrence of the tca."
    ::= { pmTcaVpwsEgressPkts1hEntry 6 }

pmTcaVpwsEgressPkts1dTable     OBJECT-TYPE
    SYNTAX          SEQUENCE OF PMTcaVpwsEgressPkts1dEntry
    MAX-ACCESS      not-accessible
    STATUS          current
    DESCRIPTION
        "A table that contains vpws information of all units."
    ::= { pmVpws 15 }

pmTcaVpwsEgressPkts1dEntry     OBJECT-TYPE
    SYNTAX          PMTcaVpwsEgressPkts1dEntry
    MAX-ACCESS      not-accessible
    STATUS          current
    DESCRIPTION
        "A list of vpws information of all units."
    INDEX     { pmTcaVpwsEgressPkts1dIndex  }
    ::= { pmTcaVpwsEgressPkts1dTable 1 }

PMTcaVpwsEgressPkts1dEntry    ::=
    SEQUENCE
    {
       pmTcaVpwsEgressPkts1dIndex      Integer32,
       pmTcaVpwsEgressPkts1dId     OCTET STRING,
       pmTcaVpwsEgressPkts1dUnitType  INTEGER,
       pmTcaVpwsEgressPkts1dCnt     Counter64,
       pmTcaVpwsEgressPkts1dThreshold   Counter64,
       pmTcaVpwsEgressPkts1dOccurTime   DateAndTime
    }

pmTcaVpwsEgressPkts1dIndex         OBJECT-TYPE
    SYNTAX          Integer32
    MAX-ACCESS      not-accessible
    STATUS          current
    DESCRIPTION
        "An index of units."
    ::= { pmTcaVpwsEgressPkts1dEntry 1 }

pmTcaVpwsEgressPkts1dId         OBJECT-TYPE
    SYNTAX          OCTET STRING
    MAX-ACCESS      read-only
    STATUS          current
    DESCRIPTION
        "Vpws name."
    ::= { pmTcaVpwsEgressPkts1dEntry 2 }

pmTcaVpwsEgressPkts1dUnitType         OBJECT-TYPE
    SYNTAX          INTEGER
    {
       mcu(0)
    }
    MAX-ACCESS      read-only
    STATUS          current
    DESCRIPTION
        "Unit type."
    ::= { pmTcaVpwsEgressPkts1dEntry 3 }

pmTcaVpwsEgressPkts1dCnt         OBJECT-TYPE
    SYNTAX          Counter64
    MAX-ACCESS      read-only
    STATUS          current
    DESCRIPTION
        "1day counter of vpws egress packets."
    ::= { pmTcaVpwsEgressPkts1dEntry 4 }

pmTcaVpwsEgressPkts1dThreshold         OBJECT-TYPE
    SYNTAX          Counter64
    MAX-ACCESS      read-only
    STATUS          current
    DESCRIPTION
        "1day threshold of vpws egress packets."
    ::= { pmTcaVpwsEgressPkts1dEntry 5 }

pmTcaVpwsEgressPkts1dOccurTime         OBJECT-TYPE
    SYNTAX          DateAndTime
    MAX-ACCESS      read-only
    STATUS          current
    DESCRIPTION
        "Time of the occurrence of the tca."
    ::= { pmTcaVpwsEgressPkts1dEntry 6 }


pmTcaVpwsEgressBytes15mTable     OBJECT-TYPE
    SYNTAX          SEQUENCE OF PMTcaVpwsEgressBytes15mEntry
    MAX-ACCESS      not-accessible
    STATUS          current
    DESCRIPTION
        "A table that contains vpws information of all units."
    ::= { pmVpws 16 }

pmTcaVpwsEgressBytes15mEntry     OBJECT-TYPE
    SYNTAX          PMTcaVpwsEgressBytes15mEntry
    MAX-ACCESS      not-accessible
    STATUS          current
    DESCRIPTION
        "A list of vpws information of all units."
    INDEX     { pmTcaVpwsEgressBytes15mIndex  }
    ::= { pmTcaVpwsEgressBytes15mTable 1 }

PMTcaVpwsEgressBytes15mEntry    ::=
    SEQUENCE
    {
       pmTcaVpwsEgressBytes15mIndex      Integer32,
       pmTcaVpwsEgressBytes15mId     OCTET STRING,
       pmTcaVpwsEgressBytes15mUnitType   INTEGER,
       pmTcaVpwsEgressBytes15mCnt     Counter64,
       pmTcaVpwsEgressBytes15mThreshold   Counter64,
       pmTcaVpwsEgressBytes15mOccurTime   DateAndTime
    }

pmTcaVpwsEgressBytes15mIndex         OBJECT-TYPE
    SYNTAX          Integer32
    MAX-ACCESS      not-accessible
    STATUS          current
    DESCRIPTION
        "An index of units."
    ::= { pmTcaVpwsEgressBytes15mEntry 1 }

pmTcaVpwsEgressBytes15mId         OBJECT-TYPE
    SYNTAX          OCTET STRING
    MAX-ACCESS      read-only
    STATUS          current
    DESCRIPTION
        "Vpws name."
    ::= { pmTcaVpwsEgressBytes15mEntry 2 }

pmTcaVpwsEgressBytes15mUnitType         OBJECT-TYPE
    SYNTAX          INTEGER
    {
       mcu(0)
    }
    MAX-ACCESS      read-only
    STATUS          current
    DESCRIPTION
        "Unit type."
    ::= { pmTcaVpwsEgressBytes15mEntry 3 }

pmTcaVpwsEgressBytes15mCnt         OBJECT-TYPE
    SYNTAX          Counter64
    MAX-ACCESS      read-only
    STATUS          current
    DESCRIPTION
        "15min counter of vpws egress bytes."
    ::= { pmTcaVpwsEgressBytes15mEntry 4 }

pmTcaVpwsEgressBytes15mThreshold         OBJECT-TYPE
    SYNTAX          Counter64
    MAX-ACCESS      read-only
    STATUS          current
    DESCRIPTION
        "15min threshold of vpws egress bytes."
    ::= { pmTcaVpwsEgressBytes15mEntry 5 }

pmTcaVpwsEgressBytes15mOccurTime         OBJECT-TYPE
    SYNTAX          DateAndTime
    MAX-ACCESS      read-only
    STATUS          current
    DESCRIPTION
        "Time of the occurrence of the tca."
    ::= { pmTcaVpwsEgressBytes15mEntry 6 }

pmTcaVpwsEgressBytes1hTable     OBJECT-TYPE
    SYNTAX          SEQUENCE OF PMTcaVpwsEgressBytes1hEntry
    MAX-ACCESS      not-accessible
    STATUS          current
    DESCRIPTION
        "A table that contains vpws information of all units."
    ::= { pmVpws 17 }

pmTcaVpwsEgressBytes1hEntry     OBJECT-TYPE
    SYNTAX          PMTcaVpwsEgressBytes1hEntry
    MAX-ACCESS      not-accessible
    STATUS          current
    DESCRIPTION
        "A list of vpws information of all units."
    INDEX     { pmTcaVpwsEgressBytes1hIndex  }
    ::= { pmTcaVpwsEgressBytes1hTable 1 }

PMTcaVpwsEgressBytes1hEntry    ::=
    SEQUENCE
    {
       pmTcaVpwsEgressBytes1hIndex      Integer32,
       pmTcaVpwsEgressBytes1hId     OCTET STRING,
       pmTcaVpwsEgressBytes1hUnitType   INTEGER,
       pmTcaVpwsEgressBytes1hCnt     Counter64,
       pmTcaVpwsEgressBytes1hThreshold   Counter64,
       pmTcaVpwsEgressBytes1hOccurTime   DateAndTime
    }

pmTcaVpwsEgressBytes1hIndex         OBJECT-TYPE
    SYNTAX          Integer32
    MAX-ACCESS      not-accessible
    STATUS          current
    DESCRIPTION
        "An index of units."
    ::= { pmTcaVpwsEgressBytes1hEntry 1 }

pmTcaVpwsEgressBytes1hId         OBJECT-TYPE
    SYNTAX          OCTET STRING
    MAX-ACCESS      read-only
    STATUS          current
    DESCRIPTION
        "Vpws name."
    ::= { pmTcaVpwsEgressBytes1hEntry 2 }

pmTcaVpwsEgressBytes1hUnitType         OBJECT-TYPE
    SYNTAX          INTEGER
    {
       mcu(0)
    }
    MAX-ACCESS      read-only
    STATUS          current
    DESCRIPTION
        "Unit type."
    ::= { pmTcaVpwsEgressBytes1hEntry 3 }

pmTcaVpwsEgressBytes1hCnt         OBJECT-TYPE
    SYNTAX          Counter64
    MAX-ACCESS      read-only
    STATUS          current
    DESCRIPTION
        "1hour counter of vpws egress bytes."
    ::= { pmTcaVpwsEgressBytes1hEntry 4 }

pmTcaVpwsEgressBytes1hThreshold         OBJECT-TYPE
    SYNTAX          Counter64
    MAX-ACCESS      read-only
    STATUS          current
    DESCRIPTION
        "1hour threshold of vpws egress bytes."
    ::= { pmTcaVpwsEgressBytes1hEntry 5 }

pmTcaVpwsEgressBytes1hOccurTime         OBJECT-TYPE
    SYNTAX          DateAndTime
    MAX-ACCESS      read-only
    STATUS          current
    DESCRIPTION
        "Time of the occurrence of the tca."
    ::= { pmTcaVpwsEgressBytes1hEntry 6 }

pmTcaVpwsEgressBytes1dTable     OBJECT-TYPE
    SYNTAX          SEQUENCE OF PMTcaVpwsEgressBytes1dEntry
    MAX-ACCESS      not-accessible
    STATUS          current
    DESCRIPTION
        "A table that contains vpws information of all units."
    ::= { pmVpws 18 }

pmTcaVpwsEgressBytes1dEntry     OBJECT-TYPE
    SYNTAX          PMTcaVpwsEgressBytes1dEntry
    MAX-ACCESS      not-accessible
    STATUS          current
    DESCRIPTION
        "A list of vpws information of all units."
    INDEX     { pmTcaVpwsEgressBytes1dIndex  }
    ::= { pmTcaVpwsEgressBytes1dTable 1 }

PMTcaVpwsEgressBytes1dEntry    ::=
    SEQUENCE
    {
       pmTcaVpwsEgressBytes1dIndex      Integer32,
       pmTcaVpwsEgressBytes1dId     OCTET STRING,
       pmTcaVpwsEgressBytes1dUnitType  INTEGER,
       pmTcaVpwsEgressBytes1dCnt     Counter64,
       pmTcaVpwsEgressBytes1dThreshold   Counter64,
       pmTcaVpwsEgressBytes1dOccurTime   DateAndTime
    }

pmTcaVpwsEgressBytes1dIndex         OBJECT-TYPE
    SYNTAX          Integer32
    MAX-ACCESS      not-accessible
    STATUS          current
    DESCRIPTION
        "An index of units."
    ::= { pmTcaVpwsEgressBytes1dEntry 1 }

pmTcaVpwsEgressBytes1dId         OBJECT-TYPE
    SYNTAX          OCTET STRING
    MAX-ACCESS      read-only
    STATUS          current
    DESCRIPTION
        "Vpws name."
    ::= { pmTcaVpwsEgressBytes1dEntry 2 }

pmTcaVpwsEgressBytes1dUnitType         OBJECT-TYPE
    SYNTAX          INTEGER
    {
       mcu(0)
    }
    MAX-ACCESS      read-only
    STATUS          current
    DESCRIPTION
        "Unit type."
    ::= { pmTcaVpwsEgressBytes1dEntry 3 }

pmTcaVpwsEgressBytes1dCnt         OBJECT-TYPE
    SYNTAX          Counter64
    MAX-ACCESS      read-only
    STATUS          current
    DESCRIPTION
        "1day counter of vpws egress bytes."
    ::= { pmTcaVpwsEgressBytes1dEntry 4 }

pmTcaVpwsEgressBytes1dThreshold         OBJECT-TYPE
    SYNTAX          Counter64
    MAX-ACCESS      read-only
    STATUS          current
    DESCRIPTION
        "1day threshold of vpws egress bytes."
    ::= { pmTcaVpwsEgressBytes1dEntry 5 }

pmTcaVpwsEgressBytes1dOccurTime         OBJECT-TYPE
    SYNTAX          DateAndTime
    MAX-ACCESS      read-only
    STATUS          current
    DESCRIPTION
        "Time of the occurrence of the tca."
    ::= { pmTcaVpwsEgressBytes1dEntry 6 }


pmVpls        OBJECT IDENTIFIER ::= { pm 106 }

pmVplsCurr15mTable     OBJECT-TYPE
    SYNTAX          SEQUENCE OF PMVplsCurr15mEntry
    MAX-ACCESS      not-accessible
    STATUS          current
    DESCRIPTION
        "A table that contains vpls information of all units."
    ::= { pmVpls 1 }

pmVplsCurr15mEntry     OBJECT-TYPE
    SYNTAX          PMVplsCurr15mEntry
    MAX-ACCESS      not-accessible
    STATUS          current
    DESCRIPTION
        "A list of vpls information of all units."
    INDEX     { pmVplsCurr15mIndex  }
    ::= { pmVplsCurr15mTable 1 }

PMVplsCurr15mEntry    ::=
    SEQUENCE
    {
       pmVplsCurr15mIndex     Integer32,
       pmVplsCurr15mId    OCTET STRING,
       pmVplsCurr15mUnitType  INTEGER,
       pmVplsCurr15mIngressPkts    Counter64,
       pmVplsCurr15mIngressBytes    Counter64,
       pmVplsCurr15mEgressPkts    Counter64,
       pmVplsCurr15mEgressBytes    Counter64,
       pmVplsCurr15mStartTime  DateAndTime,
       pmVplsCurr15mStopTime  DateAndTime
    }

pmVplsCurr15mIndex         OBJECT-TYPE
    SYNTAX          Integer32
    MAX-ACCESS      not-accessible
    STATUS          current
    DESCRIPTION
        "An index of units."
    ::= { pmVplsCurr15mEntry 1 }

pmVplsCurr15mId         OBJECT-TYPE
    SYNTAX          OCTET STRING
    MAX-ACCESS      read-only
    STATUS          current
    DESCRIPTION
        "Vpls name."
    ::= { pmVplsCurr15mEntry 2 }

pmVplsCurr15mUnitType         OBJECT-TYPE
    SYNTAX          INTEGER
    {
       mcu(0)
    }
    MAX-ACCESS      read-only
    STATUS          current
    DESCRIPTION
        "Unit type."
    ::= { pmVplsCurr15mEntry 3 }

pmVplsCurr15mIngressPkts         OBJECT-TYPE
    SYNTAX          Counter64
    MAX-ACCESS      read-only
    STATUS          current
    DESCRIPTION
        "Current 15min counter of vpls ingress packets."
    ::= { pmVplsCurr15mEntry 4 }

pmVplsCurr15mIngressBytes         OBJECT-TYPE
    SYNTAX          Counter64
    MAX-ACCESS      read-only
    STATUS          current
    DESCRIPTION
        "Current 15min counter of vpls ingress bytes."
    ::= { pmVplsCurr15mEntry 5 }

pmVplsCurr15mEgressPkts         OBJECT-TYPE
    SYNTAX          Counter64
    MAX-ACCESS      read-only
    STATUS          current
    DESCRIPTION
        "Current 15min counter of vpls egress packets."
    ::= { pmVplsCurr15mEntry 6 }

pmVplsCurr15mEgressBytes         OBJECT-TYPE
    SYNTAX          Counter64
    MAX-ACCESS      read-only
    STATUS          current
    DESCRIPTION
        "Current 15min counter of vpls egress bytes."
    ::= { pmVplsCurr15mEntry 7 }

pmVplsCurr15mStartTime         OBJECT-TYPE
    SYNTAX          DateAndTime
    MAX-ACCESS      read-only
    STATUS          current
    DESCRIPTION
        "Current 15min start time."
    ::= { pmVplsCurr15mEntry 100 }

pmVplsCurr15mStopTime         OBJECT-TYPE
    SYNTAX          DateAndTime
    MAX-ACCESS      read-only
    STATUS          current
    DESCRIPTION
        "Current 15min stop time."
    ::= { pmVplsCurr15mEntry 101 }

pmVplsPrev15mTable     OBJECT-TYPE
    SYNTAX          SEQUENCE OF PMVplsPrev15mEntry
    MAX-ACCESS      not-accessible
    STATUS          current
    DESCRIPTION
        "A table that contains vpls information of all units."
    ::= { pmVpls 2 }

pmVplsPrev15mEntry     OBJECT-TYPE
    SYNTAX          PMVplsPrev15mEntry
    MAX-ACCESS      not-accessible
    STATUS          current
    DESCRIPTION
        "A list of vpls information of all units."
    INDEX     { pmVplsPrev15mIndex  }
    ::= { pmVplsPrev15mTable 1 }

PMVplsPrev15mEntry    ::=
    SEQUENCE
    {
       pmVplsPrev15mIndex     Integer32,
       pmVplsPrev15mId    OCTET STRING,
       pmVplsPrev15mUnitType  INTEGER,
       pmVplsPrev15mIngressPkts    Counter64,
       pmVplsPrev15mIngressBytes    Counter64,
       pmVplsPrev15mEgressPkts    Counter64,
       pmVplsPrev15mEgressBytes    Counter64,
       pmVplsPrev15mStartTime  DateAndTime,
       pmVplsPrev15mStopTime  DateAndTime
    }

pmVplsPrev15mIndex         OBJECT-TYPE
    SYNTAX          Integer32
    MAX-ACCESS      not-accessible
    STATUS          current
    DESCRIPTION
        "An index of units."
    ::= { pmVplsPrev15mEntry 1 }

pmVplsPrev15mId         OBJECT-TYPE
    SYNTAX          OCTET STRING
    MAX-ACCESS      read-only
    STATUS          current
    DESCRIPTION
        "Vpls name."
    ::= { pmVplsPrev15mEntry 2 }

pmVplsPrev15mUnitType         OBJECT-TYPE
    SYNTAX          INTEGER
    {
       mcu(0)
    }
    MAX-ACCESS      read-only
    STATUS          current
    DESCRIPTION
        "Unit type."
    ::= { pmVplsPrev15mEntry 3 }

pmVplsPrev15mIngressPkts         OBJECT-TYPE
    SYNTAX          Counter64
    MAX-ACCESS      read-only
    STATUS          current
    DESCRIPTION
        "Previous 15min counter of vpls ingress packets."
    ::= { pmVplsPrev15mEntry 4 }

pmVplsPrev15mIngressBytes         OBJECT-TYPE
    SYNTAX          Counter64
    MAX-ACCESS      read-only
    STATUS          current
    DESCRIPTION
        "Previous 15min counter of vpls ingress bytes."
    ::= { pmVplsPrev15mEntry 5 }

pmVplsPrev15mEgressPkts         OBJECT-TYPE
    SYNTAX          Counter64
    MAX-ACCESS      read-only
    STATUS          current
    DESCRIPTION
        "Previous 15min counter of vpls egress packets."
    ::= { pmVplsPrev15mEntry 6 }

pmVplsPrev15mEgressBytes         OBJECT-TYPE
    SYNTAX          Counter64
    MAX-ACCESS      read-only
    STATUS          current
    DESCRIPTION
        "Previous 15min counter of vpls egress bytes."
    ::= { pmVplsPrev15mEntry 7 }

pmVplsPrev15mStartTime         OBJECT-TYPE
    SYNTAX          DateAndTime
    MAX-ACCESS      read-only
    STATUS          current
    DESCRIPTION
        "Previous 15min start time."
    ::= { pmVplsPrev15mEntry 100 }

pmVplsPrev15mStopTime         OBJECT-TYPE
    SYNTAX          DateAndTime
    MAX-ACCESS      read-only
    STATUS          current
    DESCRIPTION
        "Previous 15min stop time."
    ::= { pmVplsPrev15mEntry 101 }

pmVplsCurr1hTable     OBJECT-TYPE
    SYNTAX          SEQUENCE OF PMVplsCurr1hEntry
    MAX-ACCESS      not-accessible
    STATUS          current
    DESCRIPTION
        "A table that contains vpls information of all units."
    ::= { pmVpls 3 }

pmVplsCurr1hEntry     OBJECT-TYPE
    SYNTAX          PMVplsCurr1hEntry
    MAX-ACCESS      not-accessible
    STATUS          current
    DESCRIPTION
        "A list of vpls information of all units."
    INDEX     { pmVplsCurr1hIndex  }
    ::= { pmVplsCurr1hTable 1 }

PMVplsCurr1hEntry    ::=
    SEQUENCE
    {
       pmVplsCurr1hIndex     Integer32,
       pmVplsCurr1hId    OCTET STRING,
       pmVplsCurr1hUnitType  INTEGER,
       pmVplsCurr1hIngressPkts    Counter64,
       pmVplsCurr1hIngressBytes    Counter64,
       pmVplsCurr1hEgressPkts    Counter64,
       pmVplsCurr1hEgressBytes    Counter64,
       pmVplsCurr1hStartTime  DateAndTime,
       pmVplsCurr1hStopTime  DateAndTime
    }

pmVplsCurr1hIndex         OBJECT-TYPE
    SYNTAX          Integer32
    MAX-ACCESS      not-accessible
    STATUS          current
    DESCRIPTION
        "An index of units."
    ::= { pmVplsCurr1hEntry 1 }

pmVplsCurr1hId         OBJECT-TYPE
    SYNTAX          OCTET STRING
    MAX-ACCESS      read-only
    STATUS          current
    DESCRIPTION
        "Vpls name."
    ::= { pmVplsCurr1hEntry 2 }

pmVplsCurr1hUnitType         OBJECT-TYPE
    SYNTAX          INTEGER
    {
       mcu(0)
    }
    MAX-ACCESS      read-only
    STATUS          current
    DESCRIPTION
        "Unit type."
    ::= { pmVplsCurr1hEntry 3 }

pmVplsCurr1hIngressPkts         OBJECT-TYPE
    SYNTAX          Counter64
    MAX-ACCESS      read-only
    STATUS          current
    DESCRIPTION
        "Current 1hour counter of vpls ingress packets."
    ::= { pmVplsCurr1hEntry 4 }

pmVplsCurr1hIngressBytes         OBJECT-TYPE
    SYNTAX          Counter64
    MAX-ACCESS      read-only
    STATUS          current
    DESCRIPTION
        "Current 1hour counter of vpls ingress bytes."
    ::= { pmVplsCurr1hEntry 5 }

pmVplsCurr1hEgressPkts         OBJECT-TYPE
    SYNTAX          Counter64
    MAX-ACCESS      read-only
    STATUS          current
    DESCRIPTION
        "Current 1hour counter of vpls egress packets."
    ::= { pmVplsCurr1hEntry 6 }

pmVplsCurr1hEgressBytes         OBJECT-TYPE
    SYNTAX          Counter64
    MAX-ACCESS      read-only
    STATUS          current
    DESCRIPTION
        "Current 1hour counter of vpls egress bytes."
    ::= { pmVplsCurr1hEntry 7 }

pmVplsCurr1hStartTime         OBJECT-TYPE
    SYNTAX          DateAndTime
    MAX-ACCESS      read-only
    STATUS          current
    DESCRIPTION
        "Current 1hour start time."
    ::= { pmVplsCurr1hEntry 100 }

pmVplsCurr1hStopTime         OBJECT-TYPE
    SYNTAX          DateAndTime
    MAX-ACCESS      read-only
    STATUS          current
    DESCRIPTION
        "Current 1hour stop time."
    ::= { pmVplsCurr1hEntry 101 }

pmVplsPrev1hTable     OBJECT-TYPE
    SYNTAX          SEQUENCE OF PMVplsPrev1hEntry
    MAX-ACCESS      not-accessible
    STATUS          current
    DESCRIPTION
        "A table that contains vpls information of all units."
    ::= { pmVpls 4 }

pmVplsPrev1hEntry     OBJECT-TYPE
    SYNTAX          PMVplsPrev1hEntry
    MAX-ACCESS      not-accessible
    STATUS          current
    DESCRIPTION
        "A list of vpls information of all units."
    INDEX     { pmVplsPrev1hIndex  }
    ::= { pmVplsPrev1hTable 1 }

PMVplsPrev1hEntry    ::=
    SEQUENCE
    {
       pmVplsPrev1hIndex     Integer32,
       pmVplsPrev1hId    OCTET STRING,
       pmVplsPrev1hUnitType  INTEGER,
       pmVplsPrev1hIngressPkts    Counter64,
       pmVplsPrev1hIngressBytes    Counter64,
       pmVplsPrev1hEgressPkts    Counter64,
       pmVplsPrev1hEgressBytes    Counter64,
       pmVplsPrev1hStartTime  DateAndTime,
       pmVplsPrev1hStopTime  DateAndTime
    }

pmVplsPrev1hIndex         OBJECT-TYPE
    SYNTAX          Integer32
    MAX-ACCESS      not-accessible
    STATUS          current
    DESCRIPTION
        "An index of units."
    ::= { pmVplsPrev1hEntry 1 }

pmVplsPrev1hId         OBJECT-TYPE
    SYNTAX          OCTET STRING
    MAX-ACCESS      read-only
    STATUS          current
    DESCRIPTION
        "Vpls name."
    ::= { pmVplsPrev1hEntry 2 }

pmVplsPrev1hUnitType         OBJECT-TYPE
    SYNTAX          INTEGER
    {
       mcu(0)
    }
    MAX-ACCESS      read-only
    STATUS          current
    DESCRIPTION
        "Unit type."
    ::= { pmVplsPrev1hEntry 3 }

pmVplsPrev1hIngressPkts         OBJECT-TYPE
    SYNTAX          Counter64
    MAX-ACCESS      read-only
    STATUS          current
    DESCRIPTION
        "Previous 1hour counter of vpls ingress packets."
    ::= { pmVplsPrev1hEntry 4 }

pmVplsPrev1hIngressBytes         OBJECT-TYPE
    SYNTAX          Counter64
    MAX-ACCESS      read-only
    STATUS          current
    DESCRIPTION
        "Previous 1hour counter of vpls ingress bytes."
    ::= { pmVplsPrev1hEntry 5 }

pmVplsPrev1hEgressPkts         OBJECT-TYPE
    SYNTAX          Counter64
    MAX-ACCESS      read-only
    STATUS          current
    DESCRIPTION
        "Previous 1hour counter of vpls egress packets."
    ::= { pmVplsPrev1hEntry 6 }

pmVplsPrev1hEgressBytes         OBJECT-TYPE
    SYNTAX          Counter64
    MAX-ACCESS      read-only
    STATUS          current
    DESCRIPTION
        "Previous 1hour counter of vpls egress bytes."
    ::= { pmVplsPrev1hEntry 7 }

pmVplsPrev1hStartTime         OBJECT-TYPE
    SYNTAX          DateAndTime
    MAX-ACCESS      read-only
    STATUS          current
    DESCRIPTION
        "Previous 1hour start time."
    ::= { pmVplsPrev1hEntry 100 }

pmVplsPrev1hStopTime         OBJECT-TYPE
    SYNTAX          DateAndTime
    MAX-ACCESS      read-only
    STATUS          current
    DESCRIPTION
        "Previous 1hour stop time."
    ::= { pmVplsPrev1hEntry 101 }

pmVplsCurr1dTable     OBJECT-TYPE
    SYNTAX          SEQUENCE OF PMVplsCurr1dEntry
    MAX-ACCESS      not-accessible
    STATUS          current
    DESCRIPTION
        "A table that contains vpls information of all units."
    ::= { pmVpls 5 }

pmVplsCurr1dEntry     OBJECT-TYPE
    SYNTAX          PMVplsCurr1dEntry
    MAX-ACCESS      not-accessible
    STATUS          current
    DESCRIPTION
        "A list of vpls information of all units."
    INDEX     { pmVplsCurr1dIndex  }
    ::= { pmVplsCurr1dTable 1 }

PMVplsCurr1dEntry    ::=
    SEQUENCE
    {
       pmVplsCurr1dIndex     Integer32,
       pmVplsCurr1dId    OCTET STRING,
       pmVplsCurr1dUnitType  INTEGER,
       pmVplsCurr1dIngressPkts    Counter64,
       pmVplsCurr1dIngressBytes    Counter64,
       pmVplsCurr1dEgressPkts    Counter64,
       pmVplsCurr1dEgressBytes    Counter64,
       pmVplsCurr1dStartTime  DateAndTime,
       pmVplsCurr1dStopTime  DateAndTime
    }

pmVplsCurr1dIndex         OBJECT-TYPE
    SYNTAX          Integer32
    MAX-ACCESS      not-accessible
    STATUS          current
    DESCRIPTION
        "An index of units."
    ::= { pmVplsCurr1dEntry 1 }

pmVplsCurr1dId         OBJECT-TYPE
    SYNTAX          OCTET STRING
    MAX-ACCESS      read-only
    STATUS          current
    DESCRIPTION
        "Vpls name."
    ::= { pmVplsCurr1dEntry 2 }

pmVplsCurr1dUnitType         OBJECT-TYPE
    SYNTAX          INTEGER
    {
       mcu(0)
    }
    MAX-ACCESS      read-only
    STATUS          current
    DESCRIPTION
        "Unit type."
    ::= { pmVplsCurr1dEntry 3 }

pmVplsCurr1dIngressPkts         OBJECT-TYPE
    SYNTAX          Counter64
    MAX-ACCESS      read-only
    STATUS          current
    DESCRIPTION
        "Current 1day counter of vpls ingress packets."
    ::= { pmVplsCurr1dEntry 4 }

pmVplsCurr1dIngressBytes         OBJECT-TYPE
    SYNTAX          Counter64
    MAX-ACCESS      read-only
    STATUS          current
    DESCRIPTION
        "Current 1day counter of vpls ingress bytes."
    ::= { pmVplsCurr1dEntry 5 }

pmVplsCurr1dEgressPkts         OBJECT-TYPE
    SYNTAX          Counter64
    MAX-ACCESS      read-only
    STATUS          current
    DESCRIPTION
        "Current 1day counter of vpls egress packets."
    ::= { pmVplsCurr1dEntry 6 }

pmVplsCurr1dEgressBytes         OBJECT-TYPE
    SYNTAX          Counter64
    MAX-ACCESS      read-only
    STATUS          current
    DESCRIPTION
        "Current 1day counter of vpls egress bytes."
    ::= { pmVplsCurr1dEntry 7 }

pmVplsCurr1dStartTime         OBJECT-TYPE
    SYNTAX          DateAndTime
    MAX-ACCESS      read-only
    STATUS          current
    DESCRIPTION
        "Current 1day start time."
    ::= { pmVplsCurr1dEntry 100 }

pmVplsCurr1dStopTime         OBJECT-TYPE
    SYNTAX          DateAndTime
    MAX-ACCESS      read-only
    STATUS          current
    DESCRIPTION
        "Current 1day stop time."
    ::= { pmVplsCurr1dEntry 101 }

pmVplsPrev1dTable     OBJECT-TYPE
    SYNTAX          SEQUENCE OF PMVplsPrev1dEntry
    MAX-ACCESS      not-accessible
    STATUS          current
    DESCRIPTION
        "A table that contains vpls information of all units."
    ::= { pmVpls 6 }

pmVplsPrev1dEntry     OBJECT-TYPE
    SYNTAX          PMVplsPrev1dEntry
    MAX-ACCESS      not-accessible
    STATUS          current
    DESCRIPTION
        "A list of vpls information of all units."
    INDEX     { pmVplsPrev1dIndex  }
    ::= { pmVplsPrev1dTable 1 }

PMVplsPrev1dEntry    ::=
    SEQUENCE
    {
       pmVplsPrev1dIndex     Integer32,
       pmVplsPrev1dId    OCTET STRING,
       pmVplsPrev1dUnitType  INTEGER,
       pmVplsPrev1dIngressPkts    Counter64,
       pmVplsPrev1dIngressBytes    Counter64,
       pmVplsPrev1dEgressPkts    Counter64,
       pmVplsPrev1dEgressBytes    Counter64,
       pmVplsPrev1dStartTime  DateAndTime,
       pmVplsPrev1dStopTime  DateAndTime
    }

pmVplsPrev1dIndex         OBJECT-TYPE
    SYNTAX          Integer32
    MAX-ACCESS      not-accessible
    STATUS          current
    DESCRIPTION
        "An index of units."
    ::= { pmVplsPrev1dEntry 1 }

pmVplsPrev1dId         OBJECT-TYPE
    SYNTAX          OCTET STRING
    MAX-ACCESS      read-only
    STATUS          current
    DESCRIPTION
        "Vpls name."
    ::= { pmVplsPrev1dEntry 2 }

pmVplsPrev1dUnitType         OBJECT-TYPE
    SYNTAX          INTEGER
    {
       mcu(0)
    }
    MAX-ACCESS      read-only
    STATUS          current
    DESCRIPTION
        "Unit type."
    ::= { pmVplsPrev1dEntry 3 }

pmVplsPrev1dIngressPkts         OBJECT-TYPE
    SYNTAX          Counter64
    MAX-ACCESS      read-only
    STATUS          current
    DESCRIPTION
        "Previous 1day counter of vpls ingress packets."
    ::= { pmVplsPrev1dEntry 4 }

pmVplsPrev1dIngressBytes         OBJECT-TYPE
    SYNTAX          Counter64
    MAX-ACCESS      read-only
    STATUS          current
    DESCRIPTION
        "Previous 1day counter of vpls ingress bytes."
    ::= { pmVplsPrev1dEntry 5 }

pmVplsPrev1dEgressPkts         OBJECT-TYPE
    SYNTAX          Counter64
    MAX-ACCESS      read-only
    STATUS          current
    DESCRIPTION
        "Previous 1day counter of vpls egress packets."
    ::= { pmVplsPrev1dEntry 6 }

pmVplsPrev1dEgressBytes         OBJECT-TYPE
    SYNTAX          Counter64
    MAX-ACCESS      read-only
    STATUS          current
    DESCRIPTION
        "Previous 1day counter of vpls egress bytes."
    ::= { pmVplsPrev1dEntry 7 }

pmVplsPrev1dStartTime         OBJECT-TYPE
    SYNTAX          DateAndTime
    MAX-ACCESS      read-only
    STATUS          current
    DESCRIPTION
        "Previous 1day start time."
    ::= { pmVplsPrev1dEntry 100 }

pmVplsPrev1dStopTime         OBJECT-TYPE
    SYNTAX          DateAndTime
    MAX-ACCESS      read-only
    STATUS          current
    DESCRIPTION
        "Previous 1day stop time."
    ::= { pmVplsPrev1dEntry 101 }

pmTcaVplsIngressPkts15mTable     OBJECT-TYPE
    SYNTAX          SEQUENCE OF PMTcaVplsIngressPkts15mEntry
    MAX-ACCESS      not-accessible
    STATUS          current
    DESCRIPTION
        "A table that contains vpls information of all units."
    ::= { pmVpls 7 }

pmTcaVplsIngressPkts15mEntry     OBJECT-TYPE
    SYNTAX          PMTcaVplsIngressPkts15mEntry
    MAX-ACCESS      not-accessible
    STATUS          current
    DESCRIPTION
        "A list of vpls information of all units."
    INDEX     { pmTcaVplsIngressPkts15mIndex  }
    ::= { pmTcaVplsIngressPkts15mTable 1 }

PMTcaVplsIngressPkts15mEntry    ::=
    SEQUENCE
    {
       pmTcaVplsIngressPkts15mIndex      Integer32,
       pmTcaVplsIngressPkts15mId     OCTET STRING,
       pmTcaVplsIngressPkts15mUnitType   INTEGER,
       pmTcaVplsIngressPkts15mCnt     Counter64,
       pmTcaVplsIngressPkts15mThreshold   Counter64,
       pmTcaVplsIngressPkts15mOccurTime   DateAndTime
    }

pmTcaVplsIngressPkts15mIndex         OBJECT-TYPE
    SYNTAX          Integer32
    MAX-ACCESS      not-accessible
    STATUS          current
    DESCRIPTION
        "An index of units."
    ::= { pmTcaVplsIngressPkts15mEntry 1 }

pmTcaVplsIngressPkts15mId         OBJECT-TYPE
    SYNTAX          OCTET STRING
    MAX-ACCESS      read-only
    STATUS          current
    DESCRIPTION
        "Unit name."
    ::= { pmTcaVplsIngressPkts15mEntry 2 }

pmTcaVplsIngressPkts15mUnitType         OBJECT-TYPE
    SYNTAX          INTEGER
    {
       mcu(0)
    }
    MAX-ACCESS      read-only
    STATUS          current
    DESCRIPTION
        "Unit type."
    ::= { pmTcaVplsIngressPkts15mEntry 3 }

pmTcaVplsIngressPkts15mCnt         OBJECT-TYPE
    SYNTAX          Counter64
    MAX-ACCESS      read-only
    STATUS          current
    DESCRIPTION
        "15min counter of vpls ingress packets."
    ::= { pmTcaVplsIngressPkts15mEntry 4 }

pmTcaVplsIngressPkts15mThreshold         OBJECT-TYPE
    SYNTAX          Counter64
    MAX-ACCESS      read-only
    STATUS          current
    DESCRIPTION
        "15min threshold of vpls ingress packets."
    ::= { pmTcaVplsIngressPkts15mEntry 5 }

pmTcaVplsIngressPkts15mOccurTime         OBJECT-TYPE
    SYNTAX          DateAndTime
    MAX-ACCESS      read-only
    STATUS          current
    DESCRIPTION
        "Time of the occurrence of the tca."
    ::= { pmTcaVplsIngressPkts15mEntry 6 }

pmTcaVplsIngressPkts1hTable     OBJECT-TYPE
    SYNTAX          SEQUENCE OF PMTcaVplsIngressPkts1hEntry
    MAX-ACCESS      not-accessible
    STATUS          current
    DESCRIPTION
        "A table that contains vpls information of all units."
    ::= { pmVpls 8 }

pmTcaVplsIngressPkts1hEntry     OBJECT-TYPE
    SYNTAX          PMTcaVplsIngressPkts1hEntry
    MAX-ACCESS      not-accessible
    STATUS          current
    DESCRIPTION
        "A list of vpls information of all units."
    INDEX     { pmTcaVplsIngressPkts1hIndex  }
    ::= { pmTcaVplsIngressPkts1hTable 1 }

PMTcaVplsIngressPkts1hEntry    ::=
    SEQUENCE
    {
       pmTcaVplsIngressPkts1hIndex      Integer32,
       pmTcaVplsIngressPkts1hId     OCTET STRING,
       pmTcaVplsIngressPkts1hUnitType   INTEGER,
       pmTcaVplsIngressPkts1hCnt     Counter64,
       pmTcaVplsIngressPkts1hThreshold   Counter64,
       pmTcaVplsIngressPkts1hOccurTime   DateAndTime
    }

pmTcaVplsIngressPkts1hIndex         OBJECT-TYPE
    SYNTAX          Integer32
    MAX-ACCESS      not-accessible
    STATUS          current
    DESCRIPTION
        "An index of units."
    ::= { pmTcaVplsIngressPkts1hEntry 1 }

pmTcaVplsIngressPkts1hId         OBJECT-TYPE
    SYNTAX          OCTET STRING
    MAX-ACCESS      read-only
    STATUS          current
    DESCRIPTION
        "Unit name."
    ::= { pmTcaVplsIngressPkts1hEntry 2 }

pmTcaVplsIngressPkts1hUnitType         OBJECT-TYPE
    SYNTAX          INTEGER
    {
       mcu(0)
    }
    MAX-ACCESS      read-only
    STATUS          current
    DESCRIPTION
        "Unit type."
    ::= { pmTcaVplsIngressPkts1hEntry 3 }

pmTcaVplsIngressPkts1hCnt         OBJECT-TYPE
    SYNTAX          Counter64
    MAX-ACCESS      read-only
    STATUS          current
    DESCRIPTION
        "1hour counter of vpls ingress packets."
    ::= { pmTcaVplsIngressPkts1hEntry 4 }

pmTcaVplsIngressPkts1hThreshold         OBJECT-TYPE
    SYNTAX          Counter64
    MAX-ACCESS      read-only
    STATUS          current
    DESCRIPTION
        "1hour threshold of vpls ingress packets."
    ::= { pmTcaVplsIngressPkts1hEntry 5 }

pmTcaVplsIngressPkts1hOccurTime         OBJECT-TYPE
    SYNTAX          DateAndTime
    MAX-ACCESS      read-only
    STATUS          current
    DESCRIPTION
        "Time of the occurrence of the tca."
    ::= { pmTcaVplsIngressPkts1hEntry 6 }

pmTcaVplsIngressPkts1dTable     OBJECT-TYPE
    SYNTAX          SEQUENCE OF PMTcaVplsIngressPkts1dEntry
    MAX-ACCESS      not-accessible
    STATUS          current
    DESCRIPTION
        "A table that contains vpls information of all units."
    ::= { pmVpls 9 }

pmTcaVplsIngressPkts1dEntry     OBJECT-TYPE
    SYNTAX          PMTcaVplsIngressPkts1dEntry
    MAX-ACCESS      not-accessible
    STATUS          current
    DESCRIPTION
        "A list of vpls information of all units."
    INDEX     { pmTcaVplsIngressPkts1dIndex  }
    ::= { pmTcaVplsIngressPkts1dTable 1 }

PMTcaVplsIngressPkts1dEntry    ::=
    SEQUENCE
    {
       pmTcaVplsIngressPkts1dIndex      Integer32,
       pmTcaVplsIngressPkts1dId     OCTET STRING,
       pmTcaVplsIngressPkts1dUnitType  INTEGER,
       pmTcaVplsIngressPkts1dCnt     Counter64,
       pmTcaVplsIngressPkts1dThreshold   Counter64,
       pmTcaVplsIngressPkts1dOccurTime   DateAndTime
    }

pmTcaVplsIngressPkts1dIndex         OBJECT-TYPE
    SYNTAX          Integer32
    MAX-ACCESS      not-accessible
    STATUS          current
    DESCRIPTION
        "An index of units."
    ::= { pmTcaVplsIngressPkts1dEntry 1 }

pmTcaVplsIngressPkts1dId         OBJECT-TYPE
    SYNTAX          OCTET STRING
    MAX-ACCESS      read-only
    STATUS          current
    DESCRIPTION
        "Unit name."
    ::= { pmTcaVplsIngressPkts1dEntry 2 }

pmTcaVplsIngressPkts1dUnitType         OBJECT-TYPE
    SYNTAX          INTEGER
    {
       mcu(0)
    }
    MAX-ACCESS      read-only
    STATUS          current
    DESCRIPTION
        "Unit type."
    ::= { pmTcaVplsIngressPkts1dEntry 3 }

pmTcaVplsIngressPkts1dCnt         OBJECT-TYPE
    SYNTAX          Counter64
    MAX-ACCESS      read-only
    STATUS          current
    DESCRIPTION
        "1day counter of vpls ingress packets."
    ::= { pmTcaVplsIngressPkts1dEntry 4 }

pmTcaVplsIngressPkts1dThreshold         OBJECT-TYPE
    SYNTAX          Counter64
    MAX-ACCESS      read-only
    STATUS          current
    DESCRIPTION
        "1day threshold of vpls ingress packets."
    ::= { pmTcaVplsIngressPkts1dEntry 5 }

pmTcaVplsIngressPkts1dOccurTime         OBJECT-TYPE
    SYNTAX          DateAndTime
    MAX-ACCESS      read-only
    STATUS          current
    DESCRIPTION
        "Time of the occurrence of the tca."
    ::= { pmTcaVplsIngressPkts1dEntry 6 }

pmTcaVplsIngressBytes15mTable     OBJECT-TYPE
    SYNTAX          SEQUENCE OF PMTcaVplsIngressBytes15mEntry
    MAX-ACCESS      not-accessible
    STATUS          current
    DESCRIPTION
        "A table that contains vpls information of all units."
    ::= { pmVpls 10 }

pmTcaVplsIngressBytes15mEntry     OBJECT-TYPE
    SYNTAX          PMTcaVplsIngressBytes15mEntry
    MAX-ACCESS      not-accessible
    STATUS          current
    DESCRIPTION
        "A list of vpls information of all units."
    INDEX     { pmTcaVplsIngressBytes15mIndex  }
    ::= { pmTcaVplsIngressBytes15mTable 1 }

PMTcaVplsIngressBytes15mEntry    ::=
    SEQUENCE
    {
       pmTcaVplsIngressBytes15mIndex      Integer32,
       pmTcaVplsIngressBytes15mId     OCTET STRING,
       pmTcaVplsIngressBytes15mUnitType   INTEGER,
       pmTcaVplsIngressBytes15mCnt     Counter64,
       pmTcaVplsIngressBytes15mThreshold   Counter64,
       pmTcaVplsIngressBytes15mOccurTime   DateAndTime
    }

pmTcaVplsIngressBytes15mIndex         OBJECT-TYPE
    SYNTAX          Integer32
    MAX-ACCESS      not-accessible
    STATUS          current
    DESCRIPTION
        "An index of units."
    ::= { pmTcaVplsIngressBytes15mEntry 1 }

pmTcaVplsIngressBytes15mId         OBJECT-TYPE
    SYNTAX          OCTET STRING
    MAX-ACCESS      read-only
    STATUS          current
    DESCRIPTION
        "Unit name."
    ::= { pmTcaVplsIngressBytes15mEntry 2 }

pmTcaVplsIngressBytes15mUnitType         OBJECT-TYPE
    SYNTAX          INTEGER
    {
       mcu(0)
    }
    MAX-ACCESS      read-only
    STATUS          current
    DESCRIPTION
        "Unit type."
    ::= { pmTcaVplsIngressBytes15mEntry 3 }

pmTcaVplsIngressBytes15mCnt         OBJECT-TYPE
    SYNTAX          Counter64
    MAX-ACCESS      read-only
    STATUS          current
    DESCRIPTION
        "15min counter of vpls ingress bytes."
    ::= { pmTcaVplsIngressBytes15mEntry 4 }

pmTcaVplsIngressBytes15mThreshold         OBJECT-TYPE
    SYNTAX          Counter64
    MAX-ACCESS      read-only
    STATUS          current
    DESCRIPTION
        "15min threshold of vpls ingress bytes."
    ::= { pmTcaVplsIngressBytes15mEntry 5 }

pmTcaVplsIngressBytes15mOccurTime         OBJECT-TYPE
    SYNTAX          DateAndTime
    MAX-ACCESS      read-only
    STATUS          current
    DESCRIPTION
        "Time of the occurrence of the tca."
    ::= { pmTcaVplsIngressBytes15mEntry 6 }

pmTcaVplsIngressBytes1hTable     OBJECT-TYPE
    SYNTAX          SEQUENCE OF PMTcaVplsIngressBytes1hEntry
    MAX-ACCESS      not-accessible
    STATUS          current
    DESCRIPTION
        "A table that contains vpls information of all units."
    ::= { pmVpls 11 }

pmTcaVplsIngressBytes1hEntry     OBJECT-TYPE
    SYNTAX          PMTcaVplsIngressBytes1hEntry
    MAX-ACCESS      not-accessible
    STATUS          current
    DESCRIPTION
        "A list of vpls information of all units."
    INDEX     { pmTcaVplsIngressBytes1hIndex  }
    ::= { pmTcaVplsIngressBytes1hTable 1 }

PMTcaVplsIngressBytes1hEntry    ::=
    SEQUENCE
    {
       pmTcaVplsIngressBytes1hIndex      Integer32,
       pmTcaVplsIngressBytes1hId     OCTET STRING,
       pmTcaVplsIngressBytes1hUnitType   INTEGER,
       pmTcaVplsIngressBytes1hCnt     Counter64,
       pmTcaVplsIngressBytes1hThreshold   Counter64,
       pmTcaVplsIngressBytes1hOccurTime   DateAndTime
    }

pmTcaVplsIngressBytes1hIndex         OBJECT-TYPE
    SYNTAX          Integer32
    MAX-ACCESS      not-accessible
    STATUS          current
    DESCRIPTION
        "An index of units."
    ::= { pmTcaVplsIngressBytes1hEntry 1 }

pmTcaVplsIngressBytes1hId         OBJECT-TYPE
    SYNTAX          OCTET STRING
    MAX-ACCESS      read-only
    STATUS          current
    DESCRIPTION
        "Unit name."
    ::= { pmTcaVplsIngressBytes1hEntry 2 }

pmTcaVplsIngressBytes1hUnitType         OBJECT-TYPE
    SYNTAX          INTEGER
    {
       mcu(0)
    }
    MAX-ACCESS      read-only
    STATUS          current
    DESCRIPTION
        "Unit type."
    ::= { pmTcaVplsIngressBytes1hEntry 3 }

pmTcaVplsIngressBytes1hCnt         OBJECT-TYPE
    SYNTAX          Counter64
    MAX-ACCESS      read-only
    STATUS          current
    DESCRIPTION
        "1hour counter of vpls ingress bytes."
    ::= { pmTcaVplsIngressBytes1hEntry 4 }

pmTcaVplsIngressBytes1hThreshold         OBJECT-TYPE
    SYNTAX          Counter64
    MAX-ACCESS      read-only
    STATUS          current
    DESCRIPTION
        "1hour threshold of vpls ingress bytes."
    ::= { pmTcaVplsIngressBytes1hEntry 5 }

pmTcaVplsIngressBytes1hOccurTime         OBJECT-TYPE
    SYNTAX          DateAndTime
    MAX-ACCESS      read-only
    STATUS          current
    DESCRIPTION
        "Time of the occurrence of the tca."
    ::= { pmTcaVplsIngressBytes1hEntry 6 }

pmTcaVplsIngressBytes1dTable     OBJECT-TYPE
    SYNTAX          SEQUENCE OF PMTcaVplsIngressBytes1dEntry
    MAX-ACCESS      not-accessible
    STATUS          current
    DESCRIPTION
        "A table that contains vpls information of all units."
    ::= { pmVpls 12 }

pmTcaVplsIngressBytes1dEntry     OBJECT-TYPE
    SYNTAX          PMTcaVplsIngressBytes1dEntry
    MAX-ACCESS      not-accessible
    STATUS          current
    DESCRIPTION
        "A list of vpls information of all units."
    INDEX     { pmTcaVplsIngressBytes1dIndex  }
    ::= { pmTcaVplsIngressBytes1dTable 1 }

PMTcaVplsIngressBytes1dEntry    ::=
    SEQUENCE
    {
       pmTcaVplsIngressBytes1dIndex      Integer32,
       pmTcaVplsIngressBytes1dId     OCTET STRING,
       pmTcaVplsIngressBytes1dUnitType  INTEGER,
       pmTcaVplsIngressBytes1dCnt     Counter64,
       pmTcaVplsIngressBytes1dThreshold   Counter64,
       pmTcaVplsIngressBytes1dOccurTime   DateAndTime
    }

pmTcaVplsIngressBytes1dIndex         OBJECT-TYPE
    SYNTAX          Integer32
    MAX-ACCESS      not-accessible
    STATUS          current
    DESCRIPTION
        "An index of units."
    ::= { pmTcaVplsIngressBytes1dEntry 1 }

pmTcaVplsIngressBytes1dId         OBJECT-TYPE
    SYNTAX          OCTET STRING
    MAX-ACCESS      read-only
    STATUS          current
    DESCRIPTION
        "Unit name."
    ::= { pmTcaVplsIngressBytes1dEntry 2 }

pmTcaVplsIngressBytes1dUnitType         OBJECT-TYPE
    SYNTAX          INTEGER
    {
       mcu(0)
    }
    MAX-ACCESS      read-only
    STATUS          current
    DESCRIPTION
        "Unit type."
    ::= { pmTcaVplsIngressBytes1dEntry 3 }

pmTcaVplsIngressBytes1dCnt         OBJECT-TYPE
    SYNTAX          Counter64
    MAX-ACCESS      read-only
    STATUS          current
    DESCRIPTION
        "1day counter of vpls ingress bytes."
    ::= { pmTcaVplsIngressBytes1dEntry 4 }

pmTcaVplsIngressBytes1dThreshold         OBJECT-TYPE
    SYNTAX          Counter64
    MAX-ACCESS      read-only
    STATUS          current
    DESCRIPTION
        "1day threshold of vpls ingress bytes."
    ::= { pmTcaVplsIngressBytes1dEntry 5 }

pmTcaVplsIngressBytes1dOccurTime         OBJECT-TYPE
    SYNTAX          DateAndTime
    MAX-ACCESS      read-only
    STATUS          current
    DESCRIPTION
        "Time of the occurrence of the tca."
    ::= { pmTcaVplsIngressBytes1dEntry 6 }

pmTcaVplsEgressPkts15mTable     OBJECT-TYPE
    SYNTAX          SEQUENCE OF PMTcaVplsEgressPkts15mEntry
    MAX-ACCESS      not-accessible
    STATUS          current
    DESCRIPTION
        "A table that contains vpls information of all units."
    ::= { pmVpls 13 }

pmTcaVplsEgressPkts15mEntry     OBJECT-TYPE
    SYNTAX          PMTcaVplsEgressPkts15mEntry
    MAX-ACCESS      not-accessible
    STATUS          current
    DESCRIPTION
        "A list of vpls information of all units."
    INDEX     { pmTcaVplsEgressPkts15mIndex  }
    ::= { pmTcaVplsEgressPkts15mTable 1 }

PMTcaVplsEgressPkts15mEntry    ::=
    SEQUENCE
    {
       pmTcaVplsEgressPkts15mIndex      Integer32,
       pmTcaVplsEgressPkts15mId     OCTET STRING,
       pmTcaVplsEgressPkts15mUnitType   INTEGER,
       pmTcaVplsEgressPkts15mCnt     Counter64,
       pmTcaVplsEgressPkts15mThreshold   Counter64,
       pmTcaVplsEgressPkts15mOccurTime   DateAndTime
    }

pmTcaVplsEgressPkts15mIndex         OBJECT-TYPE
    SYNTAX          Integer32
    MAX-ACCESS      not-accessible
    STATUS          current
    DESCRIPTION
        "An index of units."
    ::= { pmTcaVplsEgressPkts15mEntry 1 }

pmTcaVplsEgressPkts15mId         OBJECT-TYPE
    SYNTAX          OCTET STRING
    MAX-ACCESS      read-only
    STATUS          current
    DESCRIPTION
        "Unit name."
    ::= { pmTcaVplsEgressPkts15mEntry 2 }

pmTcaVplsEgressPkts15mUnitType         OBJECT-TYPE
    SYNTAX          INTEGER
    {
       mcu(0)
    }
    MAX-ACCESS      read-only
    STATUS          current
    DESCRIPTION
        "Unit type."
    ::= { pmTcaVplsEgressPkts15mEntry 3 }

pmTcaVplsEgressPkts15mCnt         OBJECT-TYPE
    SYNTAX          Counter64
    MAX-ACCESS      read-only
    STATUS          current
    DESCRIPTION
        "15min counter of vpls egress packets."
    ::= { pmTcaVplsEgressPkts15mEntry 4 }

pmTcaVplsEgressPkts15mThreshold         OBJECT-TYPE
    SYNTAX          Counter64
    MAX-ACCESS      read-only
    STATUS          current
    DESCRIPTION
        "15min threshold of vpls egress packets."
    ::= { pmTcaVplsEgressPkts15mEntry 5 }

pmTcaVplsEgressPkts15mOccurTime         OBJECT-TYPE
    SYNTAX          DateAndTime
    MAX-ACCESS      read-only
    STATUS          current
    DESCRIPTION
        "Time of the occurrence of the tca."
    ::= { pmTcaVplsEgressPkts15mEntry 6 }

pmTcaVplsEgressPkts1hTable     OBJECT-TYPE
    SYNTAX          SEQUENCE OF PMTcaVplsEgressPkts1hEntry
    MAX-ACCESS      not-accessible
    STATUS          current
    DESCRIPTION
        "A table that contains vpls information of all units."
    ::= { pmVpls 14 }

pmTcaVplsEgressPkts1hEntry     OBJECT-TYPE
    SYNTAX          PMTcaVplsEgressPkts1hEntry
    MAX-ACCESS      not-accessible
    STATUS          current
    DESCRIPTION
        "A list of vpls information of all units."
    INDEX     { pmTcaVplsEgressPkts1hIndex  }
    ::= { pmTcaVplsEgressPkts1hTable 1 }

PMTcaVplsEgressPkts1hEntry    ::=
    SEQUENCE
    {
       pmTcaVplsEgressPkts1hIndex      Integer32,
       pmTcaVplsEgressPkts1hId     OCTET STRING,
       pmTcaVplsEgressPkts1hUnitType   INTEGER,
       pmTcaVplsEgressPkts1hCnt     Counter64,
       pmTcaVplsEgressPkts1hThreshold   Counter64,
       pmTcaVplsEgressPkts1hOccurTime   DateAndTime
    }

pmTcaVplsEgressPkts1hIndex         OBJECT-TYPE
    SYNTAX          Integer32
    MAX-ACCESS      not-accessible
    STATUS          current
    DESCRIPTION
        "An index of units."
    ::= { pmTcaVplsEgressPkts1hEntry 1 }

pmTcaVplsEgressPkts1hId         OBJECT-TYPE
    SYNTAX          OCTET STRING
    MAX-ACCESS      read-only
    STATUS          current
    DESCRIPTION
        "Unit name."
    ::= { pmTcaVplsEgressPkts1hEntry 2 }

pmTcaVplsEgressPkts1hUnitType         OBJECT-TYPE
    SYNTAX          INTEGER
    {
       mcu(0)
    }
    MAX-ACCESS      read-only
    STATUS          current
    DESCRIPTION
        "Unit type."
    ::= { pmTcaVplsEgressPkts1hEntry 3 }

pmTcaVplsEgressPkts1hCnt         OBJECT-TYPE
    SYNTAX          Counter64
    MAX-ACCESS      read-only
    STATUS          current
    DESCRIPTION
        "1hour counter of vpls egress packets."
    ::= { pmTcaVplsEgressPkts1hEntry 4 }

pmTcaVplsEgressPkts1hThreshold         OBJECT-TYPE
    SYNTAX          Counter64
    MAX-ACCESS      read-only
    STATUS          current
    DESCRIPTION
        "1hour threshold of vpls egress packets."
    ::= { pmTcaVplsEgressPkts1hEntry 5 }

pmTcaVplsEgressPkts1hOccurTime         OBJECT-TYPE
    SYNTAX          DateAndTime
    MAX-ACCESS      read-only
    STATUS          current
    DESCRIPTION
        "Time of the occurrence of the tca."
    ::= { pmTcaVplsEgressPkts1hEntry 6 }

pmTcaVplsEgressPkts1dTable     OBJECT-TYPE
    SYNTAX          SEQUENCE OF PMTcaVplsEgressPkts1dEntry
    MAX-ACCESS      not-accessible
    STATUS          current
    DESCRIPTION
        "A table that contains vpls information of all units."
    ::= { pmVpls 15 }

pmTcaVplsEgressPkts1dEntry     OBJECT-TYPE
    SYNTAX          PMTcaVplsEgressPkts1dEntry
    MAX-ACCESS      not-accessible
    STATUS          current
    DESCRIPTION
        "A list of vpls information of all units."
    INDEX     { pmTcaVplsEgressPkts1dIndex  }
    ::= { pmTcaVplsEgressPkts1dTable 1 }

PMTcaVplsEgressPkts1dEntry    ::=
    SEQUENCE
    {
       pmTcaVplsEgressPkts1dIndex      Integer32,
       pmTcaVplsEgressPkts1dId     OCTET STRING,
       pmTcaVplsEgressPkts1dUnitType  INTEGER,
       pmTcaVplsEgressPkts1dCnt     Counter64,
       pmTcaVplsEgressPkts1dThreshold   Counter64,
       pmTcaVplsEgressPkts1dOccurTime   DateAndTime
    }

pmTcaVplsEgressPkts1dIndex         OBJECT-TYPE
    SYNTAX          Integer32
    MAX-ACCESS      not-accessible
    STATUS          current
    DESCRIPTION
        "An index of units."
    ::= { pmTcaVplsEgressPkts1dEntry 1 }

pmTcaVplsEgressPkts1dId         OBJECT-TYPE
    SYNTAX          OCTET STRING
    MAX-ACCESS      read-only
    STATUS          current
    DESCRIPTION
        "Unit name."
    ::= { pmTcaVplsEgressPkts1dEntry 2 }

pmTcaVplsEgressPkts1dUnitType         OBJECT-TYPE
    SYNTAX          INTEGER
    {
       mcu(0)
    }
    MAX-ACCESS      read-only
    STATUS          current
    DESCRIPTION
        "Unit type."
    ::= { pmTcaVplsEgressPkts1dEntry 3 }

pmTcaVplsEgressPkts1dCnt         OBJECT-TYPE
    SYNTAX          Counter64
    MAX-ACCESS      read-only
    STATUS          current
    DESCRIPTION
        "1day counter of vpls egress packets."
    ::= { pmTcaVplsEgressPkts1dEntry 4 }

pmTcaVplsEgressPkts1dThreshold         OBJECT-TYPE
    SYNTAX          Counter64
    MAX-ACCESS      read-only
    STATUS          current
    DESCRIPTION
        "1day threshold of vpls egress packets."
    ::= { pmTcaVplsEgressPkts1dEntry 5 }

pmTcaVplsEgressPkts1dOccurTime         OBJECT-TYPE
    SYNTAX          DateAndTime
    MAX-ACCESS      read-only
    STATUS          current
    DESCRIPTION
        "Time of the occurrence of the tca."
    ::= { pmTcaVplsEgressPkts1dEntry 6 }

pmTcaVplsEgressBytes15mTable     OBJECT-TYPE
    SYNTAX          SEQUENCE OF PMTcaVplsEgressBytes15mEntry
    MAX-ACCESS      not-accessible
    STATUS          current
    DESCRIPTION
        "A table that contains vpls information of all units."
    ::= { pmVpls 16 }

pmTcaVplsEgressBytes15mEntry     OBJECT-TYPE
    SYNTAX          PMTcaVplsEgressBytes15mEntry
    MAX-ACCESS      not-accessible
    STATUS          current
    DESCRIPTION
        "A list of vpls information of all units."
    INDEX     { pmTcaVplsEgressBytes15mIndex  }
    ::= { pmTcaVplsEgressBytes15mTable 1 }

PMTcaVplsEgressBytes15mEntry    ::=
    SEQUENCE
    {
       pmTcaVplsEgressBytes15mIndex      Integer32,
       pmTcaVplsEgressBytes15mId     OCTET STRING,
       pmTcaVplsEgressBytes15mUnitType   INTEGER,
       pmTcaVplsEgressBytes15mCnt     Counter64,
       pmTcaVplsEgressBytes15mThreshold   Counter64,
       pmTcaVplsEgressBytes15mOccurTime   DateAndTime
    }

pmTcaVplsEgressBytes15mIndex         OBJECT-TYPE
    SYNTAX          Integer32
    MAX-ACCESS      not-accessible
    STATUS          current
    DESCRIPTION
        "An index of units."
    ::= { pmTcaVplsEgressBytes15mEntry 1 }

pmTcaVplsEgressBytes15mId         OBJECT-TYPE
    SYNTAX          OCTET STRING
    MAX-ACCESS      read-only
    STATUS          current
    DESCRIPTION
        "Unit name."
    ::= { pmTcaVplsEgressBytes15mEntry 2 }

pmTcaVplsEgressBytes15mUnitType         OBJECT-TYPE
    SYNTAX          INTEGER
    {
       mcu(0)
    }
    MAX-ACCESS      read-only
    STATUS          current
    DESCRIPTION
        "Unit type."
    ::= { pmTcaVplsEgressBytes15mEntry 3 }

pmTcaVplsEgressBytes15mCnt         OBJECT-TYPE
    SYNTAX          Counter64
    MAX-ACCESS      read-only
    STATUS          current
    DESCRIPTION
        "15min counter of vpls egress bytes."
    ::= { pmTcaVplsEgressBytes15mEntry 4 }

pmTcaVplsEgressBytes15mThreshold         OBJECT-TYPE
    SYNTAX          Counter64
    MAX-ACCESS      read-only
    STATUS          current
    DESCRIPTION
        "15min threshold of vpls egress bytes."
    ::= { pmTcaVplsEgressBytes15mEntry 5 }

pmTcaVplsEgressBytes15mOccurTime         OBJECT-TYPE
    SYNTAX          DateAndTime
    MAX-ACCESS      read-only
    STATUS          current
    DESCRIPTION
        "Time of the occurrence of the tca."
    ::= { pmTcaVplsEgressBytes15mEntry 6 }

pmTcaVplsEgressBytes1hTable     OBJECT-TYPE
    SYNTAX          SEQUENCE OF PMTcaVplsEgressBytes1hEntry
    MAX-ACCESS      not-accessible
    STATUS          current
    DESCRIPTION
        "A table that contains vpls information of all units."
    ::= { pmVpls 17 }

pmTcaVplsEgressBytes1hEntry     OBJECT-TYPE
    SYNTAX          PMTcaVplsEgressBytes1hEntry
    MAX-ACCESS      not-accessible
    STATUS          current
    DESCRIPTION
        "A list of vpls information of all units."
    INDEX     { pmTcaVplsEgressBytes1hIndex  }
    ::= { pmTcaVplsEgressBytes1hTable 1 }

PMTcaVplsEgressBytes1hEntry    ::=
    SEQUENCE
    {
       pmTcaVplsEgressBytes1hIndex      Integer32,
       pmTcaVplsEgressBytes1hId     OCTET STRING,
       pmTcaVplsEgressBytes1hUnitType   INTEGER,
       pmTcaVplsEgressBytes1hCnt     Counter64,
       pmTcaVplsEgressBytes1hThreshold   Counter64,
       pmTcaVplsEgressBytes1hOccurTime   DateAndTime
    }

pmTcaVplsEgressBytes1hIndex         OBJECT-TYPE
    SYNTAX          Integer32
    MAX-ACCESS      not-accessible
    STATUS          current
    DESCRIPTION
        "An index of units."
    ::= { pmTcaVplsEgressBytes1hEntry 1 }

pmTcaVplsEgressBytes1hId         OBJECT-TYPE
    SYNTAX          OCTET STRING
    MAX-ACCESS      read-only
    STATUS          current
    DESCRIPTION
        "Unit name."
    ::= { pmTcaVplsEgressBytes1hEntry 2 }

pmTcaVplsEgressBytes1hUnitType         OBJECT-TYPE
    SYNTAX          INTEGER
    {
       mcu(0)
    }
    MAX-ACCESS      read-only
    STATUS          current
    DESCRIPTION
        "Unit type."
    ::= { pmTcaVplsEgressBytes1hEntry 3 }

pmTcaVplsEgressBytes1hCnt         OBJECT-TYPE
    SYNTAX          Counter64
    MAX-ACCESS      read-only
    STATUS          current
    DESCRIPTION
        "1hour counter of vpls egress bytes."
    ::= { pmTcaVplsEgressBytes1hEntry 4 }

pmTcaVplsEgressBytes1hThreshold         OBJECT-TYPE
    SYNTAX          Counter64
    MAX-ACCESS      read-only
    STATUS          current
    DESCRIPTION
        "1hour threshold of vpls egress bytes."
    ::= { pmTcaVplsEgressBytes1hEntry 5 }

pmTcaVplsEgressBytes1hOccurTime         OBJECT-TYPE
    SYNTAX          DateAndTime
    MAX-ACCESS      read-only
    STATUS          current
    DESCRIPTION
        "Time of the occurrence of the tca."
    ::= { pmTcaVplsEgressBytes1hEntry 6 }

pmTcaVplsEgressBytes1dTable     OBJECT-TYPE
    SYNTAX          SEQUENCE OF PMTcaVplsEgressBytes1dEntry
    MAX-ACCESS      not-accessible
    STATUS          current
    DESCRIPTION
        "A table that contains vpls information of all units."
    ::= { pmVpls 18 }

pmTcaVplsEgressBytes1dEntry     OBJECT-TYPE
    SYNTAX          PMTcaVplsEgressBytes1dEntry
    MAX-ACCESS      not-accessible
    STATUS          current
    DESCRIPTION
        "A list of vpls information of all units."
    INDEX     { pmTcaVplsEgressBytes1dIndex  }
    ::= { pmTcaVplsEgressBytes1dTable 1 }

PMTcaVplsEgressBytes1dEntry    ::=
    SEQUENCE
    {
       pmTcaVplsEgressBytes1dIndex      Integer32,
       pmTcaVplsEgressBytes1dId     OCTET STRING,
       pmTcaVplsEgressBytes1dUnitType  INTEGER,
       pmTcaVplsEgressBytes1dCnt     Counter64,
       pmTcaVplsEgressBytes1dThreshold   Counter64,
       pmTcaVplsEgressBytes1dOccurTime   DateAndTime
    }

pmTcaVplsEgressBytes1dIndex         OBJECT-TYPE
    SYNTAX          Integer32
    MAX-ACCESS      not-accessible
    STATUS          current
    DESCRIPTION
        "An index of units."
    ::= { pmTcaVplsEgressBytes1dEntry 1 }

pmTcaVplsEgressBytes1dId         OBJECT-TYPE
    SYNTAX          OCTET STRING
    MAX-ACCESS      read-only
    STATUS          current
    DESCRIPTION
        "Unit name."
    ::= { pmTcaVplsEgressBytes1dEntry 2 }

pmTcaVplsEgressBytes1dUnitType         OBJECT-TYPE
    SYNTAX          INTEGER
    {
       mcu(0)
    }
    MAX-ACCESS      read-only
    STATUS          current
    DESCRIPTION
        "Unit type."
    ::= { pmTcaVplsEgressBytes1dEntry 3 }

pmTcaVplsEgressBytes1dCnt         OBJECT-TYPE
    SYNTAX          Counter64
    MAX-ACCESS      read-only
    STATUS          current
    DESCRIPTION
        "1day counter of vpls egress bytes."
    ::= { pmTcaVplsEgressBytes1dEntry 4 }

pmTcaVplsEgressBytes1dThreshold         OBJECT-TYPE
    SYNTAX          Counter64
    MAX-ACCESS      read-only
    STATUS          current
    DESCRIPTION
        "1day threshold of vpls egress bytes."
    ::= { pmTcaVplsEgressBytes1dEntry 5 }

pmTcaVplsEgressBytes1dOccurTime         OBJECT-TYPE
    SYNTAX          DateAndTime
    MAX-ACCESS      read-only
    STATUS          current
    DESCRIPTION
        "Time of the occurrence of the tca."
    ::= { pmTcaVplsEgressBytes1dEntry 6 }


--alarm                       OBJECT IDENTIFIER ::= { OID 91 }

alarmOptionTable     OBJECT-TYPE
    SYNTAX          SEQUENCE OF AlarmOptionEntry
    MAX-ACCESS      not-accessible
    STATUS          current
    DESCRIPTION
        "A table that contains all alarm information."
    ::= { alarm 1 }

alarmOptionEntry     OBJECT-TYPE
    SYNTAX          AlarmOptionEntry
    MAX-ACCESS      not-accessible
    STATUS          current
    DESCRIPTION
        "A list of all alarm information."
    INDEX     { alarmOptionIndex  }
    ::= { alarmOptionTable 1 }

AlarmOptionEntry    ::=
    SEQUENCE
    {
       alarmOptionIndex           INTEGER,
       alarmOptionSeverity        INTEGER,
       alarmOptionServiceAffect   INTEGER
    }

alarmOptionIndex         OBJECT-TYPE
    SYNTAX          INTEGER
    {
        unit-out(0),
        sfp-out(1),
        link-down(2),
        vpws-down(3),
        vpls-down(4),
        lsp-down(5),
        mspw-down(6),
        mem-usage-high(7),
        mpls-tp-oam-loc(8),
        mpls-tp-oam-unexp-rmepid(9),
        mpls-tp-oam-unexp-interval(10),
        mpls-tp-oam-unexp-megid(11),
        mpls-tp-oam-unexp-level(12),
        mpls-tp-oam-rdi(13),
        mpls-tp-oam-rdi-tx(14),
        mpls-tp-oam-ais-defect(15),
        mpls-tp-oam-event-full(16),
        mpls-tp-oam-1dm-full(17),
        mpls-tp-oam-wait-1st-ccm(18),
        mpls-tp-oam-ais-rx(19),
        mpls-tp-oam-ais-tx(20),
        tca-unit-temperature-min-15min(21),
        tca-unit-temperature-min-1hour(22),
        tca-unit-temperature-min-1day(23),
        tca-unit-temperature-max-15min(24),
        tca-unit-temperature-max-1hour(25),
        tca-unit-temperature-max-1day(26),
        tca-sfp-rx-power-min-15min(27),
        tca-sfp-rx-power-min-1hour(28),
        tca-sfp-rx-power-min-1day(29),
        tca-sfp-rx-power-max-15min(30),
        tca-sfp-rx-power-max-1hour(31),
        tca-sfp-rx-power-max-1day(32),
        tca-sfp-tx-power-min-15min(33),
        tca-sfp-tx-power-min-1hour(34),
        tca-sfp-tx-power-min-1day(35),
        tca-sfp-tx-power-max-15min(36),
        tca-sfp-tx-power-max-1hourn(37),
        tca-sfp-tx-power-max-1day(38),
        tca-if-dropped-events-15min(39),
        tca-if-dropped-events-1hour(40),
        tca-if-dropped-events-1day(41),
        tca-if-input-packets-15min(42),
        tca-if-input-packets-1hour(43),
        tca-if-input-packets-1day(44),
        tca-if-input-bytes-15min(45),
        tca-if-input-bytes-1hour(46),
        tca-if-input-bytes-1day(47),
        tca-if-input-broadcasts-15min(48),
        tca-if-input-broadcasts-1hour(49),
        tca-if-input-broadcasts-1day(50),
        tca-if-input-multicasts-15min(51),
        tca-if-input-multicasts-1hour(52),
        tca-if-input-multicasts-1day(53),
        tca-if-crc-errors-15min(54),
        tca-if-crc-errors-1hour(55),
        tca-if-crc-errors-1day(56),
        tca-if-collisions-15min(57),
        tca-if-collisions-1hour(58),
        tca-if-collisions-1day(59),
        tca-if-undersized-packets-15min(60),
        tca-if-undersized-packets-1hour(61),
        tca-if-undersized-packets-1day(62),
        tca-if-oversized-packets-15min(63),
        tca-if-oversized-packets-1hour(64),
        tca-if-oversized-packets-1day(65),
        tca-if-fragments-15min(66),
        tca-if-fragments-1hour(67),
        tca-if-fragments-1day(68),
        tca-if-jabbers-15min(69),
        tca-if-jabbers-1hour(70),
        tca-if-jabbers-1day(71),
        tca-if-packet-64-15min(72),
        tca-if-packet-64-1hour(73),
        tca-if-packet-64-1day(74),
        tca-if-packet-65-127-15min(75),
        tca-if-packet-65-127-1hour(76),
        tca-if-packet-65-127-1day(77),
        tca-if-packet-128-255-15min(78),
        tca-if-packet-128-255-1hour(79),
        tca-if-packet-128-255-1day(80),
        tca-if-packet-256-511-15min(81),
        tca-if-packet-256-511-1hour(82),
        tca-if-packet-256-511-1day(83),
        tca-if-packet-512-1023-15min(84),
        tca-if-packet-512-1023-1hour(85),
        tca-if-packet-512-1023-1day(86),
        tca-if-packet-1024-15min(87),
        tca-if-packet-1024-1hour(88),
        tca-if-packet-1024-1day(89),
        tca-if-output-packets-15min(90),
        tca-if-output-packets-1hour(91),
        tca-if-output-packets-1day(92),
        tca-if-output-bytes-15min(93),
        tca-if-output-bytes-1hour(94),
        tca-if-output-bytes-1day(95),
        tca-lsp-pe-out-packets-15min(96),
        tca-lsp-pe-out-packets-1hour(97),
        tca-lsp-pe-out-packets-1day(98),
        tca-lsp-pe-out-bytes-15min(99),
        tca-lsp-pe-out-bytes-1hour(100),
        tca-lsp-pe-out-bytes-1day(101),
        tca-lsp-p-east-in-packets-15min(102),
        tca-lsp-p-east-in-packets-1hour(103),
        tca-lsp-p-east-in-packets-1day(104),
        tca-lsp-p-east-in-bytes-15min(105),
        tca-lsp-p-east-in-bytes-1hour(106),
        tca-lsp-p-east-in-bytes-1day(107),
        tca-lsp-p-west-in-packets-15min(108),
        tca-lsp-p-west-in-packets-1hour(109),
        tca-lsp-p-west-in-packets-1day(110),
        tca-lsp-p-west-in-bytes-15min(111),
        tca-lsp-p-west-in-bytes-1hour(112),
        tca-lsp-p-west-in-bytes-1day(113),
        tca-vpws-ingress-packets-15min(114),
        tca-vpws-ingress-packets-1hour(115),
        tca-vpws-ingress-packets-1day(116),
        tca-vpws-ingress-bytes-15min(117),
        tca-vpws-ingress-bytes-1hour(118),
        tca-vpws-ingress-bytes-1day(119),
        tca-vpws-egress-packets-15min(120),
        tca-vpws-egress-packets-1hour(121),
        tca-vpws-egress-packets-1day(122),
        tca-vpws-egress-bytes-15min(123),
        tca-vpws-egress-bytes-1hour(124),
        tca-vpws-egress-bytes-1day(125),
        tca-vpls-ingress-packets-15min(126),
        tca-vpls-ingress-packets-1hour(127),
        tca-vpls-ingress-packets-1day(128),
        tca-vpls-ingress-bytes-15min(129),
        tca-vpls-ingress-bytes-1hour(130),
        tca-vpls-ingress-bytes-1day(131),
        tca-vpls-egress-packets-15min(132),
        tca-vpls-egress-packets-1hour(133),
        tca-vpls-egress-packets-1day(134),
        tca-vpls-egress-bytes-15min(135),
        tca-vpls-egress-bytes-1hour(136),
        tca-vpls-egress-bytes-1day(137)
    }
    MAX-ACCESS      not-accessible
    STATUS          current
    DESCRIPTION
        "An index of pm types."
    ::= { alarmOptionEntry 1 }

alarmOptionSeverity         OBJECT-TYPE
    SYNTAX          INTEGER
    {
        warning(0),
        minor(1),
        major(2),
        critical(3)
    }
    MAX-ACCESS      read-write
    STATUS          current
    DESCRIPTION
        "Severity of the alarm."
    ::= { alarmOptionEntry 2 }

alarmOptionServiceAffect         OBJECT-TYPE
    SYNTAX          INTEGER
    {
        service-affected(0),
        non-service-affected(1)
    }
    MAX-ACCESS      read-only
    STATUS          current
    DESCRIPTION
        "Service affted of the alarm."
    ::= { alarmOptionEntry 3 }

alarmLogTable     OBJECT-TYPE
    SYNTAX          SEQUENCE OF AlarmLogEntry
    MAX-ACCESS      not-accessible
    STATUS          current
    DESCRIPTION
        "A table that contains all current alarms."
    ::= { alarm 2 }

alarmLogEntry     OBJECT-TYPE
    SYNTAX          AlarmLogEntry
    MAX-ACCESS      not-accessible
    STATUS          current
    DESCRIPTION
        "A list of temperature information of all units."
    INDEX     { alarmLogIndex  }
    ::= { alarmLogTable 1 }

AlarmLogEntry    ::=
    SEQUENCE
    {
       alarmLogIndex       Integer32,
       alarmLogType      INTEGER,
       alarmLogObject     OCTET STRING,
       alarmLogSeverity    INTEGER,
       alarmLogServiceAffect  INTEGER,
       alarmLogAddInfo      OCTET STRING,
       alarmLogOccurTime   DateAndTime
    }

alarmLogIndex         OBJECT-TYPE
    SYNTAX          Integer32
    MAX-ACCESS      not-accessible
    STATUS          current
    DESCRIPTION
        "An index of current alarm."
    ::= { alarmLogEntry 1 }

alarmLogType         OBJECT-TYPE
    SYNTAX          INTEGER
    {
        unit-out(0),
        sfp-out(1),
        link-down(2),
        vpws-down(3),
        vpls-down(4),
        lsp-down(5),
        mspw-down(6),
        mem-usage-high(7),
        mpls-tp-oam-loc(8),
        mpls-tp-oam-unexp-rmepid(9),
        mpls-tp-oam-unexp-interval(10),
        mpls-tp-oam-unexp-megid(11),
        mpls-tp-oam-unexp-level(12),
        mpls-tp-oam-rdi(13),
        mpls-tp-oam-rdi-tx(14),
        mpls-tp-oam-ais-defect(15),
        mpls-tp-oam-event-full(16),
        mpls-tp-oam-1dm-full(17),
        mpls-tp-oam-wait-1st-ccm(18),
        mpls-tp-oam-ais-rx(19),
        mpls-tp-oam-ais-tx(20),
        tca-unit-temperature-min-15min(21),
        tca-unit-temperature-min-1hour(22),
        tca-unit-temperature-min-1day(23),
        tca-unit-temperature-max-15min(24),
        tca-unit-temperature-max-1hour(25),
        tca-unit-temperature-max-1day(26),
        tca-sfp-rx-power-min-15min(27),
        tca-sfp-rx-power-min-1hour(28),
        tca-sfp-rx-power-min-1day(29),
        tca-sfp-rx-power-max-15min(30),
        tca-sfp-rx-power-max-1hour(31),
        tca-sfp-rx-power-max-1day(32),
        tca-sfp-tx-power-min-15min(33),
        tca-sfp-tx-power-min-1hour(34),
        tca-sfp-tx-power-min-1day(35),
        tca-sfp-tx-power-max-15min(36),
        tca-sfp-tx-power-max-1hourn(37),
        tca-sfp-tx-power-max-1day(38),
        tca-if-dropped-events-15min(39),
        tca-if-dropped-events-1hour(40),
        tca-if-dropped-events-1day(41),
        tca-if-input-packets-15min(42),
        tca-if-input-packets-1hour(43),
        tca-if-input-packets-1day(44),
        tca-if-input-bytes-15min(45),
        tca-if-input-bytes-1hour(46),
        tca-if-input-bytes-1day(47),
        tca-if-input-broadcasts-15min(48),
        tca-if-input-broadcasts-1hour(49),
        tca-if-input-broadcasts-1day(50),
        tca-if-input-multicasts-15min(51),
        tca-if-input-multicasts-1hour(52),
        tca-if-input-multicasts-1day(53),
        tca-if-crc-errors-15min(54),
        tca-if-crc-errors-1hour(55),
        tca-if-crc-errors-1day(56),
        tca-if-collisions-15min(57),
        tca-if-collisions-1hour(58),
        tca-if-collisions-1day(59),
        tca-if-undersized-packets-15min(60),
        tca-if-undersized-packets-1hour(61),
        tca-if-undersized-packets-1day(62),
        tca-if-oversized-packets-15min(63),
        tca-if-oversized-packets-1hour(64),
        tca-if-oversized-packets-1day(65),
        tca-if-fragments-15min(66),
        tca-if-fragments-1hour(67),
        tca-if-fragments-1day(68),
        tca-if-jabbers-15min(69),
        tca-if-jabbers-1hour(70),
        tca-if-jabbers-1day(71),
        tca-if-packet-64-15min(72),
        tca-if-packet-64-1hour(73),
        tca-if-packet-64-1day(74),
        tca-if-packet-65-127-15min(75),
        tca-if-packet-65-127-1hour(76),
        tca-if-packet-65-127-1day(77),
        tca-if-packet-128-255-15min(78),
        tca-if-packet-128-255-1hour(79),
        tca-if-packet-128-255-1day(80),
        tca-if-packet-256-511-15min(81),
        tca-if-packet-256-511-1hour(82),
        tca-if-packet-256-511-1day(83),
        tca-if-packet-512-1023-15min(84),
        tca-if-packet-512-1023-1hour(85),
        tca-if-packet-512-1023-1day(86),
        tca-if-packet-1024-15min(87),
        tca-if-packet-1024-1hour(88),
        tca-if-packet-1024-1day(89),
        tca-if-output-packets-15min(90),
        tca-if-output-packets-1hour(91),
        tca-if-output-packets-1day(92),
        tca-if-output-bytes-15min(93),
        tca-if-output-bytes-1hour(94),
        tca-if-output-bytes-1day(95),
        tca-lsp-pe-out-packets-15min(96),
        tca-lsp-pe-out-packets-1hour(97),
        tca-lsp-pe-out-packets-1day(98),
        tca-lsp-pe-out-bytes-15min(99),
        tca-lsp-pe-out-bytes-1hour(100),
        tca-lsp-pe-out-bytes-1day(101),
        tca-lsp-p-east-in-packets-15min(102),
        tca-lsp-p-east-in-packets-1hour(103),
        tca-lsp-p-east-in-packets-1day(104),
        tca-lsp-p-east-in-bytes-15min(105),
        tca-lsp-p-east-in-bytes-1hour(106),
        tca-lsp-p-east-in-bytes-1day(107),
        tca-lsp-p-west-in-packets-15min(108),
        tca-lsp-p-west-in-packets-1hour(109),
        tca-lsp-p-west-in-packets-1day(110),
        tca-lsp-p-west-in-bytes-15min(111),
        tca-lsp-p-west-in-bytes-1hour(112),
        tca-lsp-p-west-in-bytes-1day(113),
        tca-vpws-ingress-packets-15min(114),
        tca-vpws-ingress-packets-1hour(115),
        tca-vpws-ingress-packets-1day(116),
        tca-vpws-ingress-bytes-15min(117),
        tca-vpws-ingress-bytes-1hour(118),
        tca-vpws-ingress-bytes-1day(119),
        tca-vpws-egress-packets-15min(120),
        tca-vpws-egress-packets-1hour(121),
        tca-vpws-egress-packets-1day(122),
        tca-vpws-egress-bytes-15min(123),
        tca-vpws-egress-bytes-1hour(124),
        tca-vpws-egress-bytes-1day(125),
        tca-vpls-ingress-packets-15min(126),
        tca-vpls-ingress-packets-1hour(127),
        tca-vpls-ingress-packets-1day(128),
        tca-vpls-ingress-bytes-15min(129),
        tca-vpls-ingress-bytes-1hour(130),
        tca-vpls-ingress-bytes-1day(131),
        tca-vpls-egress-packets-15min(132),
        tca-vpls-egress-packets-1hour(133),
        tca-vpls-egress-packets-1day(134),
        tca-vpls-egress-bytes-15min(135),
        tca-vpls-egress-bytes-1hour(136),
        tca-vpls-egress-bytes-1day(137)
    }
    MAX-ACCESS      read-only
    STATUS          current
    DESCRIPTION
        "Unit name."
    ::= { alarmLogEntry 2 }

alarmLogObject         OBJECT-TYPE
    SYNTAX          OCTET STRING
    MAX-ACCESS      read-only
    STATUS          current
    DESCRIPTION
        "The object of the alarm."
    ::= { alarmLogEntry 3 }

alarmLogSeverity         OBJECT-TYPE
    SYNTAX          INTEGER
    {
        warning(0),
        minor(1),
        major(2),
        critical(3)
    }
    MAX-ACCESS      read-only
    STATUS          current
    DESCRIPTION
        "Severity of the alarm."
    ::= { alarmLogEntry 4 }

alarmLogServiceAffect         OBJECT-TYPE
    SYNTAX          INTEGER
    {
        service-affected(0),
        not-service-affected(1)
    }
    MAX-ACCESS      read-only
    STATUS          current
    DESCRIPTION
        "Whether this alarm affects service."
    ::= { alarmLogEntry 5 }

alarmLogAddInfo         OBJECT-TYPE
    SYNTAX          OCTET STRING
    MAX-ACCESS      read-only
    STATUS          current
    DESCRIPTION
        "Additional information of the alarm."
    ::= { alarmLogEntry 6 }

alarmLogOccurTime         OBJECT-TYPE
    SYNTAX          DateAndTime
    MAX-ACCESS      read-only
    STATUS          current
    DESCRIPTION
        "Time of the occurrence of the alarm."
    ::= { alarmLogEntry 7 }

alarmHistoryLogTable     OBJECT-TYPE
    SYNTAX          SEQUENCE OF AlarmHistoryLogEntry
    MAX-ACCESS      not-accessible
    STATUS          current
    DESCRIPTION
        "A table that contains all current alarms."
    ::= { alarm 3 }

alarmHistoryLogEntry     OBJECT-TYPE
    SYNTAX          AlarmHistoryLogEntry
    MAX-ACCESS      not-accessible
    STATUS          current
    DESCRIPTION
        "A list of temperature information of all units."
    INDEX     { alarmHistoryLogIndex  }
    ::= { alarmHistoryLogTable 1 }

AlarmHistoryLogEntry    ::=
    SEQUENCE
    {
       alarmHistoryLogIndex       Integer32,
       alarmHistoryLogSeq        Integer32,
       alarmHistoryLogType     INTEGER,
       alarmHistoryLogObject    OCTET STRING,
       alarmHistoryLogSeverity   INTEGER,
       alarmHistoryLogServiceAffect INTEGER,
       alarmHistoryLogAddInfo      OCTET STRING,
       alarmHistoryLogOccurTime    DateAndTime,
       alarmHistoryLogReleaseTime  DateAndTime
    }

alarmHistoryLogIndex         OBJECT-TYPE
    SYNTAX          Integer32
    MAX-ACCESS      not-accessible
    STATUS          current
    DESCRIPTION
        "An index of history alarms."
    ::= { alarmHistoryLogEntry 1 }

alarmHistoryLogSeq         OBJECT-TYPE
    SYNTAX          Integer32
    MAX-ACCESS      read-only
    STATUS          current
    DESCRIPTION
        "Sequence number of the history alarm."
    ::= { alarmHistoryLogEntry 2 }

alarmHistoryLogType         OBJECT-TYPE
    SYNTAX          INTEGER
    {
        unit-out(0),
        sfp-out(1),
        link-down(2),
        vpws-down(3),
        vpls-down(4),
        lsp-down(5),
        mspw-down(6),
        mem-usage-high(7),
        mpls-tp-oam-loc(8),
        mpls-tp-oam-unexp-rmepid(9),
        mpls-tp-oam-unexp-interval(10),
        mpls-tp-oam-unexp-megid(11),
        mpls-tp-oam-unexp-level(12),
        mpls-tp-oam-rdi(13),
        mpls-tp-oam-rdi-tx(14),
        mpls-tp-oam-ais-defect(15),
        mpls-tp-oam-event-full(16),
        mpls-tp-oam-1dm-full(17),
        mpls-tp-oam-wait-1st-ccm(18),
        mpls-tp-oam-ais-rx(19),
        mpls-tp-oam-ais-tx(20),
        tca-unit-temperature-min-15min(21),
        tca-unit-temperature-min-1hour(22),
        tca-unit-temperature-min-1day(23),
        tca-unit-temperature-max-15min(24),
        tca-unit-temperature-max-1hour(25),
        tca-unit-temperature-max-1day(26),
        tca-sfp-rx-power-min-15min(27),
        tca-sfp-rx-power-min-1hour(28),
        tca-sfp-rx-power-min-1day(29),
        tca-sfp-rx-power-max-15min(30),
        tca-sfp-rx-power-max-1hour(31),
        tca-sfp-rx-power-max-1day(32),
        tca-sfp-tx-power-min-15min(33),
        tca-sfp-tx-power-min-1hour(34),
        tca-sfp-tx-power-min-1day(35),
        tca-sfp-tx-power-max-15min(36),
        tca-sfp-tx-power-max-1hourn(37),
        tca-sfp-tx-power-max-1day(38),
        tca-if-dropped-events-15min(39),
        tca-if-dropped-events-1hour(40),
        tca-if-dropped-events-1day(41),
        tca-if-input-packets-15min(42),
        tca-if-input-packets-1hour(43),
        tca-if-input-packets-1day(44),
        tca-if-input-bytes-15min(45),
        tca-if-input-bytes-1hour(46),
        tca-if-input-bytes-1day(47),
        tca-if-input-broadcasts-15min(48),
        tca-if-input-broadcasts-1hour(49),
        tca-if-input-broadcasts-1day(50),
        tca-if-input-multicasts-15min(51),
        tca-if-input-multicasts-1hour(52),
        tca-if-input-multicasts-1day(53),
        tca-if-crc-errors-15min(54),
        tca-if-crc-errors-1hour(55),
        tca-if-crc-errors-1day(56),
        tca-if-collisions-15min(57),
        tca-if-collisions-1hour(58),
        tca-if-collisions-1day(59),
        tca-if-undersized-packets-15min(60),
        tca-if-undersized-packets-1hour(61),
        tca-if-undersized-packets-1day(62),
        tca-if-oversized-packets-15min(63),
        tca-if-oversized-packets-1hour(64),
        tca-if-oversized-packets-1day(65),
        tca-if-fragments-15min(66),
        tca-if-fragments-1hour(67),
        tca-if-fragments-1day(68),
        tca-if-jabbers-15min(69),
        tca-if-jabbers-1hour(70),
        tca-if-jabbers-1day(71),
        tca-if-packet-64-15min(72),
        tca-if-packet-64-1hour(73),
        tca-if-packet-64-1day(74),
        tca-if-packet-65-127-15min(75),
        tca-if-packet-65-127-1hour(76),
        tca-if-packet-65-127-1day(77),
        tca-if-packet-128-255-15min(78),
        tca-if-packet-128-255-1hour(79),
        tca-if-packet-128-255-1day(80),
        tca-if-packet-256-511-15min(81),
        tca-if-packet-256-511-1hour(82),
        tca-if-packet-256-511-1day(83),
        tca-if-packet-512-1023-15min(84),
        tca-if-packet-512-1023-1hour(85),
        tca-if-packet-512-1023-1day(86),
        tca-if-packet-1024-15min(87),
        tca-if-packet-1024-1hour(88),
        tca-if-packet-1024-1day(89),
        tca-if-output-packets-15min(90),
        tca-if-output-packets-1hour(91),
        tca-if-output-packets-1day(92),
        tca-if-output-bytes-15min(93),
        tca-if-output-bytes-1hour(94),
        tca-if-output-bytes-1day(95),
        tca-lsp-pe-out-packets-15min(96),
        tca-lsp-pe-out-packets-1hour(97),
        tca-lsp-pe-out-packets-1day(98),
        tca-lsp-pe-out-bytes-15min(99),
        tca-lsp-pe-out-bytes-1hour(100),
        tca-lsp-pe-out-bytes-1day(101),
        tca-lsp-p-east-in-packets-15min(102),
        tca-lsp-p-east-in-packets-1hour(103),
        tca-lsp-p-east-in-packets-1day(104),
        tca-lsp-p-east-in-bytes-15min(105),
        tca-lsp-p-east-in-bytes-1hour(106),
        tca-lsp-p-east-in-bytes-1day(107),
        tca-lsp-p-west-in-packets-15min(108),
        tca-lsp-p-west-in-packets-1hour(109),
        tca-lsp-p-west-in-packets-1day(110),
        tca-lsp-p-west-in-bytes-15min(111),
        tca-lsp-p-west-in-bytes-1hour(112),
        tca-lsp-p-west-in-bytes-1day(113),
        tca-vpws-ingress-packets-15min(114),
        tca-vpws-ingress-packets-1hour(115),
        tca-vpws-ingress-packets-1day(116),
        tca-vpws-ingress-bytes-15min(117),
        tca-vpws-ingress-bytes-1hour(118),
        tca-vpws-ingress-bytes-1day(119),
        tca-vpws-egress-packets-15min(120),
        tca-vpws-egress-packets-1hour(121),
        tca-vpws-egress-packets-1day(122),
        tca-vpws-egress-bytes-15min(123),
        tca-vpws-egress-bytes-1hour(124),
        tca-vpws-egress-bytes-1day(125),
        tca-vpls-ingress-packets-15min(126),
        tca-vpls-ingress-packets-1hour(127),
        tca-vpls-ingress-packets-1day(128),
        tca-vpls-ingress-bytes-15min(129),
        tca-vpls-ingress-bytes-1hour(130),
        tca-vpls-ingress-bytes-1day(131),
        tca-vpls-egress-packets-15min(132),
        tca-vpls-egress-packets-1hour(133),
        tca-vpls-egress-packets-1day(134),
        tca-vpls-egress-bytes-15min(135),
        tca-vpls-egress-bytes-1hour(136),
        tca-vpls-egress-bytes-1day(137)
    }
    MAX-ACCESS      read-only
    STATUS          current
    DESCRIPTION
        "Unit name."
    ::= { alarmHistoryLogEntry 3 }

alarmHistoryLogObject         OBJECT-TYPE
    SYNTAX          OCTET STRING
    MAX-ACCESS      read-only
    STATUS          current
    DESCRIPTION
        "The object of the alarm."
    ::= { alarmHistoryLogEntry 4 }

alarmHistoryLogSeverity         OBJECT-TYPE
    SYNTAX          INTEGER
    {
        warning(0),
        minor(1),
        major(2),
        critical(3)
    }
    MAX-ACCESS      read-only
    STATUS          current
    DESCRIPTION
        "Severity of the alarm."
    ::= { alarmHistoryLogEntry 5 }

alarmHistoryLogServiceAffect         OBJECT-TYPE
    SYNTAX          INTEGER
    {
        service-affected(0),
        not-service-affected(1)
    }
    MAX-ACCESS      read-only
    STATUS          current
    DESCRIPTION
        "Whether this alarm affects service."
    ::= { alarmHistoryLogEntry 6 }

alarmHistoryLogAddInfo         OBJECT-TYPE
    SYNTAX          OCTET STRING
    MAX-ACCESS      read-only
    STATUS          current
    DESCRIPTION
        "Additional information of the alarm."
    ::= { alarmHistoryLogEntry 7 }

alarmHistoryLogOccurTime         OBJECT-TYPE
    SYNTAX          DateAndTime
    MAX-ACCESS      read-only
    STATUS          current
    DESCRIPTION
        "Time of the occurrence of the alarm."
    ::= { alarmHistoryLogEntry 8 }

alarmHistoryLogReleaseTime         OBJECT-TYPE
    SYNTAX          DateAndTime
    MAX-ACCESS      read-only
    STATUS          current
    DESCRIPTION
        "Time of the occurrence of the alarm."
    ::= { alarmHistoryLogEntry 9 }

alarmSwitchAlarm         OBJECT-TYPE
    SYNTAX          INTEGER
    {
        enable(1),
        disable(2)
    }
    MAX-ACCESS      read-write
    STATUS          current
    DESCRIPTION
        "Enable all alarm event traps.disable(2) enable(1)"
    DEFVAL         { enable }
    ::= { alarm 4 }

alarmSwitchTca         OBJECT-TYPE
    SYNTAX          INTEGER
    {
        enable(1),
        disable(2)
    }
    MAX-ACCESS      read-write
    STATUS          current
    DESCRIPTION
        "Enable all tca event traps.disable(2) enable(1)"
    DEFVAL         { enable }
    ::= { alarm 5 }

alarmTrap        OBJECT IDENTIFIER ::= { alarm 100 }

aAlarmEventNotify    NOTIFICATION-TYPE
        OBJECTS     {
                      alarmHistoryLogSeq,
                      alarmHistoryLogType,
                      alarmHistoryLogObject,
                      alarmHistoryLogSeverity,
                      alarmHistoryLogServiceAffect,
                      alarmHistoryLogAddInfo,
                      alarmHistoryLogOccurTime,
                      alarmHistoryLogReleaseTime
                    }
        STATUS      current
        DESCRIPTION
            "This trap will be generated when system fault is detected or released.
            ie. unit-out, tca, etc."
        ::= {alarmTrap 1}

-- Sub Module: rsvpTe
-- rsvpTe: inteface
rsvpTeIfTable                     OBJECT-TYPE
 SYNTAX          SEQUENCE OF RsvpTeIfEntry
 MAX-ACCESS      not-accessible
 STATUS          current
 DESCRIPTION
  "Configure mpls-te on an interface."
 ::= { rsvpTe 1 }

rsvpTeIfEntry                     OBJECT-TYPE
    SYNTAX          RsvpTeIfEntry
    MAX-ACCESS      not-accessible
    STATUS          current
    DESCRIPTION
     "Entry of rsvpTeIfTable."
    INDEX   { ifIndex }
    ::= { rsvpTeIfTable 1 }

RsvpTeIfEntry ::=
 SEQUENCE
 {
  rsvpTeIfEnable
   INTEGER,
  rsvpTeIfHelloInterval
   Integer32,
  rsvpTeIfHelloReceipt
   INTEGER,
  rsvpTeIfHelloTimeout
   Integer32,
  rsvpTeIfKeepMultiplier
   Integer32,
  rsvpTeIfRefreshTime
   Integer32,
  rsvpTeAckWaitTime
   Integer32,
  rsvpTeMessageAck
   INTEGER,
  rsvpTeRefreshReduction
   INTEGER
 }

rsvpTeIfEnable                    OBJECT-TYPE
    SYNTAX          INTEGER {enable(1), disable(2)}
    MAX-ACCESS      read-write
    STATUS          current
    DESCRIPTION
     "Enable or disable RSVP on this interface"
    DEFVAL { disable }
    ::= { rsvpTeIfEntry 1 }

rsvpTeIfHelloInterval             OBJECT-TYPE
    SYNTAX          Integer32 (1..65535)
    MAX-ACCESS      read-write
    STATUS          current
    DESCRIPTION
     "Configure interval between successive Hello packets to neighbor on this interface"
    DEFVAL { 2 }
    ::= { rsvpTeIfEntry 2 }

rsvpTeIfHelloReceipt              OBJECT-TYPE
    SYNTAX          INTEGER {enable(1), disable(2)}
    MAX-ACCESS      read-write
    STATUS          current
    DESCRIPTION
     "Enable or disable the exchange of Hello messages on this interface"
    DEFVAL { disable }
    ::= { rsvpTeIfEntry 3 }

rsvpTeIfHelloTimeout              OBJECT-TYPE
    SYNTAX          Integer32 (1..65535)
    MAX-ACCESS      read-write
    STATUS          current
    DESCRIPTION
     "Configure Timeout for clearing up all sessions shared with a neighbor on this interface"
    DEFVAL { 7 }
    ::= { rsvpTeIfEntry 4 }

rsvpTeIfKeepMultiplier            OBJECT-TYPE
    SYNTAX          Integer32 (0..255)
    MAX-ACCESS      read-write
    STATUS          current
    DESCRIPTION
     " Configure the constant to be used for calculating a valid lifetime on this interface"
    DEFVAL { 3 }
    ::= { rsvpTeIfEntry 5 }

rsvpTeIfRefreshTime               OBJECT-TYPE
    SYNTAX          Integer32 (1..65535)
    MAX-ACCESS      read-write
    STATUS          current
    DESCRIPTION
     " Configure the path interval being used on this interface"
    DEFVAL { 30 }
    ::= { rsvpTeIfEntry 6 }

rsvpTeAckWaitTime                 OBJECT-TYPE
    SYNTAX          Integer32 (1..65535)
    MAX-ACCESS      read-write
    STATUS          current
    DESCRIPTION
     "Configure acknowledgement wait timeout on this interface"
    DEFVAL { 1 }
    ::= { rsvpTeIfEntry 7 }

rsvpTeMessageAck                  OBJECT-TYPE
    SYNTAX          INTEGER {enable(1), disable(2)}
    MAX-ACCESS      read-write
    STATUS          current
    DESCRIPTION
     "Enable or disable Message Acknowledgement on this interface"
    DEFVAL { disable }
    ::= { rsvpTeIfEntry 8  }

rsvpTeRefreshReduction            OBJECT-TYPE
    SYNTAX          INTEGER {enable(1), disable(2)}
    MAX-ACCESS      read-write
    STATUS          current
    DESCRIPTION
     "Enable refresh reduction for this interface"
    DEFVAL { enable }
    ::= { rsvpTeIfEntry 9 }


-- rsvpTe: router rsvp
rsvpTeGlobal OBJECT IDENTIFIER
    ::= { rsvpTe 2 }

rsvpTeGlobalEnable               OBJECT-TYPE
    SYNTAX          INTEGER {enable(1), disable(2)}
    MAX-ACCESS      read-write
    STATUS          current
    DESCRIPTION
     "Enable or disable the Resource Reservation Protocol (RSVP) Globally."
    DEFVAL { disable }
    ::= { rsvpTeGlobal 1}

rsvpTeGlobalExplicitNull          OBJECT-TYPE
    SYNTAX          INTEGER {explicitNull(1), noExplicitNull(2)}
    MAX-ACCESS      read-write
    STATUS          current
    DESCRIPTION
     "Configure the state of send Explicit NULL Label"
    DEFVAL { noExplicitNull }
    ::= { rsvpTeGlobal 2 }

rsvpTeGlobalHelloInterval         OBJECT-TYPE
    SYNTAX          Integer32 (1..65535)
    MAX-ACCESS      read-write
    STATUS          current
    DESCRIPTION
     "Configure the interval between successive Hello packets to neighbor"
    DEFVAL { 2 }
    ::= { rsvpTeGlobal 3 }

rsvpTeGlobalHelloTimeout          OBJECT-TYPE
    SYNTAX          Integer32 (1..65535)
    MAX-ACCESS      read-write
    STATUS          current
    DESCRIPTION
     "Configure the timeout for clearing up all sessions shared with a neighbor"
    DEFVAL { 7 }
    ::= { rsvpTeGlobal 4 }

rsvpTeGlobalKeepMultiplier        OBJECT-TYPE
    SYNTAX          Integer32 (1..255)
    MAX-ACCESS      read-write
    STATUS          current
    DESCRIPTION
     "Configure the constant to be used for calculating a valid lifetime"
    DEFVAL { 3 }
    ::= { rsvpTeGlobal 5 }

rsvpTeGlobalNeighborTable         OBJECT-TYPE
    SYNTAX          SEQUENCE OF RsvpTeGlobalNeighborEntry
    MAX-ACCESS      not-accessible
    STATUS          current
    DESCRIPTION
     "Identify a directly connected ipv4 neighbor"
    ::= { rsvpTeGlobal 6 }

rsvpTeGlobalNeighborEntry         OBJECT-TYPE
    SYNTAX          RsvpTeGlobalNeighborEntry
    MAX-ACCESS      not-accessible
    STATUS          current
    DESCRIPTION
     "Entry of rsvpTeGlobalNeighborTable"
    INDEX   { rsvpTeGlobalNeighborAddr }
    ::= { rsvpTeGlobalNeighborTable 1 }

RsvpTeGlobalNeighborEntry ::=
 SEQUENCE
    {
        rsvpTeGlobalNeighborAddr
            IpAddress,
        rsvpTeGlobalNeighborRowStatus
            RowStatus,
  rsvpTeGlobalNeighborUpStrmLSP
   Integer32,
  rsvpTeGlobalNeighborDnStrmLSP
   Integer32,
  rsvpTeGlobalNeighborRefReduc
   INTEGER,
  rsvpTeGlobalNeighborSrefreshIn
   Integer32,
  rsvpTeGlobalNeighborSrefreshType
   INTEGER,
  rsvpTeGlobalNeighborHelloStat
   INTEGER
    }

rsvpTeGlobalNeighborAddr          OBJECT-TYPE
    SYNTAX          IpAddress
    MAX-ACCESS      not-accessible
    STATUS          current
    DESCRIPTION
     "Configure the IPv4 address of the neighbor"
    ::= { rsvpTeGlobalNeighborEntry 1 }

rsvpTeGlobalNeighborRowStatus     OBJECT-TYPE
    SYNTAX          RowStatus
    MAX-ACCESS      read-create
    STATUS          current
    DESCRIPTION
     "Status of the rsvpTeGlobalNeighborEntry row.
     1 means Active
        4 means CreateAndGo
        6 means Destroy."
    ::= { rsvpTeGlobalNeighborEntry 2 }

rsvpTeGlobalNeighborUpStrmLSP      OBJECT-TYPE
    SYNTAX          Integer32
    MAX-ACCESS      read-only
    STATUS          current
    DESCRIPTION
     "Count of the up stream LSP."
    ::= { rsvpTeGlobalNeighborEntry 3 }

rsvpTeGlobalNeighborDnStrmLSP      OBJECT-TYPE
    SYNTAX          Integer32
    MAX-ACCESS      read-only
    STATUS          current
    DESCRIPTION
     "Count of the down stream LSP."
    ::= { rsvpTeGlobalNeighborEntry 4 }

rsvpTeGlobalNeighborRefReduc      OBJECT-TYPE
    SYNTAX          INTEGER {enable(1), disable(2)}
    MAX-ACCESS      read-only
    STATUS          current
    DESCRIPTION
     "The RR(Refresh Reduction) configuration of the rsvp neighbor."
    ::= { rsvpTeGlobalNeighborEntry 5 }

rsvpTeGlobalNeighborSrefreshIn   OBJECT-TYPE
    SYNTAX          Integer32
    MAX-ACCESS      read-only
    STATUS          current
    DESCRIPTION
     "The refresh timer of the rsvp neighbor."
    ::= { rsvpTeGlobalNeighborEntry 6 }

rsvpTeGlobalNeighborSrefreshType  OBJECT-TYPE
    SYNTAX          INTEGER {explicit(1), implicit(2)}
    MAX-ACCESS      read-only
    STATUS          current
    DESCRIPTION
     "The refresh type of the rsvp neighbor."
    ::= { rsvpTeGlobalNeighborEntry 7 }

rsvpTeGlobalNeighborHelloStat     OBJECT-TYPE
    SYNTAX          INTEGER {up(1), lost(2)}
    MAX-ACCESS      read-only
    STATUS          current
    DESCRIPTION
     "The status of hello keep-alive message."
    ::= { rsvpTeGlobalNeighborEntry 8 }

rsvpTeGlobalLoopDetection         OBJECT-TYPE
    SYNTAX          INTEGER {enable(1), disable(2)}
    MAX-ACCESS      read-write
    STATUS          current
    DESCRIPTION
     "Enable or disable the loop detection"
    DEFVAL { disable }
    ::= { rsvpTeGlobal 7 }

rsvpTeGlobalRefreshTime           OBJECT-TYPE
    SYNTAX          Integer32 (1..65535)
    MAX-ACCESS      read-write
    STATUS          current
    DESCRIPTION
     "Configure RSVP refresh interval timer"
    DEFVAL { 30 }
    ::= { rsvpTeGlobal 8 }

rsvpTeGlobalReoptimizeTime        OBJECT-TYPE
    SYNTAX          Integer32 (0..655535)
    MAX-ACCESS      read-write
    STATUS          current
    DESCRIPTION
     "Configure the Reoptimize timer"
    DEFVAL { 3600 }
    ::= { rsvpTeGlobal 9 }

rsvpTeGlobalVersion              OBJECT-TYPE
    SYNTAX          Integer32 (1..2)
    MAX-ACCESS      read-only
    STATUS          current
    DESCRIPTION
     "Protocal version of rsvp."
    ::= { rsvpTeGlobal 10 }

rsvpTeGlobalProcessUpTime        OBJECT-TYPE
    SYNTAX          OCTET STRING (SIZE(1..65535))
    MAX-ACCESS      read-only
    STATUS          current
    DESCRIPTION
     "Process up time of rsvp."
    ::= { rsvpTeGlobal 11 }

-- rsvpTe: rsvp trunk
rsvpTeTrunkTable                  OBJECT-TYPE
    SYNTAX          SEQUENCE OF RsvpTeTrunkEntry
    MAX-ACCESS      not-accessible
    STATUS          current
    DESCRIPTION
     "Table of rsvp trunk."
    ::= { rsvpTe 3 }

rsvpTeTrunkEntry                  OBJECT-TYPE
    SYNTAX          RsvpTeTrunkEntry
    MAX-ACCESS      not-accessible
    STATUS          current
    DESCRIPTION     "Entry of rsvpTeTrunkTable"
    INDEX   { rsvpTeTrunkName }
    ::= { rsvpTeTrunkTable 1 }

RsvpTeTrunkEntry    ::=
    SEQUENCE
    {
  rsvpTeTrunkName
            OCTET STRING,
        rsvpTeTrunkRowStatus
            RowStatus,
        rsvpTeTrunkExtTunnelId
            IpAddress,
        rsvpTeTrunkPrimaryFilter
            INTEGER,
        rsvpTeTrunkSecondaryFilter
            INTEGER,
        rsvpTeTrunkSource
            IpAddress,
        rsvpTeTrunkPrimaryHoldPriority
            Integer32,
        rsvpTeTrunkSecondaryHoldPriority
            Integer32,
        rsvpTeTrunkPrimaryHopLimit
            Integer32,
        rsvpTeTrunkSecondaryHopLimit
            Integer32,
        rsvpTeTrunkPrimaryCspf
            INTEGER,
        rsvpTeTrunkSecondaryCspf
            INTEGER,
        rsvpTeTrunkLspMetricType
            Integer32,
        rsvpTeTrunkLspMetricValue
            Integer32,
        rsvpTeTrunkPrimaryRecord
            INTEGER,
        rsvpTeTrunkSecondaryRecord
            INTEGER,
        rsvpTeTrunkPrimaryPathName
            OCTET STRING,
        rsvpTeTrunkSecondaryPathName
            OCTET STRING,
        rsvpTeTrunkPrimaryRetryTimer
            Integer32,
        rsvpTeTrunkSecondaryRetryTimer
            Integer32,
        rsvpTeTrunkPrimarySetupPriority
            Integer32,
        rsvpTeTrunkSecondarySetupPriority
            Integer32,
        rsvpTeTrunkdestination
            IpAddress,
        rsvpTeTrunkLSPCount
            Integer32
    }

rsvpTeTrunkName                   OBJECT-TYPE
    SYNTAX          OCTET STRING(SIZE(0..255))
    MAX-ACCESS      not-accessible
    STATUS          current
    DESCRIPTION
     "Name of the RSVP trunk"
    ::= { rsvpTeTrunkEntry 1 }

rsvpTeTrunkRowStatus              OBJECT-TYPE
    SYNTAX          RowStatus
    MAX-ACCESS      read-create
    STATUS          current
    DESCRIPTION     "Status of the rsvpTeTrunkEntry row
     1 means Active
        4 means CreateAndGo
        6 means Destroy."
    ::= { rsvpTeTrunkEntry 2 }

rsvpTeTrunkExtTunnelId            OBJECT-TYPE
    SYNTAX          IpAddress
    MAX-ACCESS      read-write
    STATUS          current
    DESCRIPTION
     "Specify an extended tunnel identifier for this trunk."
    ::= { rsvpTeTrunkEntry 3 }

rsvpTeTrunkPrimaryFilter          OBJECT-TYPE
    SYNTAX          INTEGER {fixed(1), shared-explicit(2)}
    MAX-ACCESS      read-write
    STATUS          current
    DESCRIPTION
     "Specify a filter to be used for this LSP."
    DEFVAL { shared-explicit }
    ::= { rsvpTeTrunkEntry 4 }

rsvpTeTrunkSecondaryFilter        OBJECT-TYPE
    SYNTAX          INTEGER {fixed(1), shared-explicit(2)}
    MAX-ACCESS      read-write
    STATUS          current
    DESCRIPTION
     "Specify a filter to be used for this LSP."
    ::= { rsvpTeTrunkEntry 5 }

rsvpTeTrunkSource                 OBJECT-TYPE
    SYNTAX          IpAddress
    MAX-ACCESS      read-write
    STATUS          current
    DESCRIPTION
     "Specify the IPv4 tunnel ingress."
    ::= { rsvpTeTrunkEntry 6 }

rsvpTeTrunkPrimaryHoldPriority    OBJECT-TYPE
    SYNTAX          Integer32 (0..7)
    MAX-ACCESS      read-write
    STATUS          current
    DESCRIPTION
     "Configure a hold priority for this LSP."
    DEFVAL { 0 }
    ::= { rsvpTeTrunkEntry 7 }

rsvpTeTrunkSecondaryHoldPriority  OBJECT-TYPE
    SYNTAX          Integer32 (0..7)
    MAX-ACCESS      read-write
    STATUS          current
    DESCRIPTION
     "Configure a hold priority for this LSP."
    ::= { rsvpTeTrunkEntry 8 }

rsvpTeTrunkPrimaryHopLimit        OBJECT-TYPE
    SYNTAX          Integer32 (1..255)
    MAX-ACCESS      read-write
    STATUS          current
    DESCRIPTION
     "Specify a hop limit for this LSP."
    DEFVAL { 65 }
    ::= { rsvpTeTrunkEntry 9 }

rsvpTeTrunkSecondaryHopLimit      OBJECT-TYPE
    SYNTAX          Integer32 (1..255)
    MAX-ACCESS      read-write
    STATUS          current
    DESCRIPTION
     "Specify a hop limit for this LSP."
    DEFVAL { 65 }
    ::= { rsvpTeTrunkEntry 10 }

rsvpTeTrunkPrimaryCspf            OBJECT-TYPE
    SYNTAX          INTEGER {enable(1), disable(2)}
    MAX-ACCESS      read-write
    STATUS          current
    DESCRIPTION
     "Use CSPF for ERO calculation."
    DEFVAL { disable }
    ::= { rsvpTeTrunkEntry 11 }

rsvpTeTrunkSecondaryCspf          OBJECT-TYPE
    SYNTAX          INTEGER {enable(1), disable(2)}
    MAX-ACCESS      read-write
    STATUS          current
    DESCRIPTION
     "Use CSPF for ERO calculation."
 DEFVAL { disable }
 ::= { rsvpTeTrunkEntry 12 }

rsvpTeTrunkPrimaryRecord          OBJECT-TYPE
    SYNTAX          INTEGER {enable(1), disable(2)}
    MAX-ACCESS      read-write
    STATUS          current
    DESCRIPTION
     "Record route taken by PATH message in order to reach tunnel egress."
    DEFVAL { disable }
    ::= { rsvpTeTrunkEntry 13 }

rsvpTeTrunkSecondaryRecord        OBJECT-TYPE
    SYNTAX          INTEGER {enable(1), disable(2)}
    MAX-ACCESS      read-write
    STATUS          current
    DESCRIPTION
     "Record route taken by PATH message in order to reach tunnel egress."
    DEFVAL { disable }
    ::= { rsvpTeTrunkEntry 14 }

rsvpTeTrunkPrimaryPathName        OBJECT-TYPE
    SYNTAX          OCTET STRING(SIZE(0..255))
    MAX-ACCESS      read-write
    STATUS          current
    DESCRIPTION
     "Specify an RSVP Path to be used."
    ::= { rsvpTeTrunkEntry 15 }

rsvpTeTrunkSecondaryPathName      OBJECT-TYPE
    SYNTAX          OCTET STRING(SIZE(0..255))
    MAX-ACCESS      read-write
    STATUS          current
    DESCRIPTION
     "Specify an RSVP Path to be used."
    ::= { rsvpTeTrunkEntry 16 }

rsvpTeTrunkPrimaryRetryTimer      OBJECT-TYPE
    SYNTAX          Integer32 (1..600)
    MAX-ACCESS      read-write
    STATUS          current
    DESCRIPTION
     "Specify a retry interval for this LSP."
    DEFVAL { 30 }
    ::= { rsvpTeTrunkEntry 17 }

rsvpTeTrunkSecondaryRetryTimer    OBJECT-TYPE
    SYNTAX          Integer32 (1..600)
    MAX-ACCESS      read-write
    STATUS          current
    DESCRIPTION
     "Specify a retry interval for this LSP."
    DEFVAL { 30 }
    ::= { rsvpTeTrunkEntry 18 }

rsvpTeTrunkPrimarySetupPriority   OBJECT-TYPE
    SYNTAX          Integer32 (0..7)
    MAX-ACCESS      read-write
    STATUS          current
    DESCRIPTION
     "Configure a setup priority for this LSP."
    DEFVAL { 0 }
    ::= { rsvpTeTrunkEntry 19 }

rsvpTeTrunkSecondarySetupPriority OBJECT-TYPE
    SYNTAX          Integer32 (0..7)
    MAX-ACCESS      read-write
    STATUS          current
    DESCRIPTION
     "Configure a setup priority for this LSP."
    ::= { rsvpTeTrunkEntry 20}

rsvpTeTrunkdestination            OBJECT-TYPE
    SYNTAX          IpAddress
    MAX-ACCESS      read-write
    STATUS          current
    DESCRIPTION
     "Specify the IPv4 tunnel egress."
    ::= { rsvpTeTrunkEntry 21}

rsvpTeTrunkLSPCount    OBJECT-TYPE
    SYNTAX          Integer32
    MAX-ACCESS      read-only
    STATUS          current
    DESCRIPTION
     "Total LSP count of the rsvp trunk."
    ::= { rsvpTeTrunkEntry 22 }

-- rsvpTe: rsvp trunk - map route
rsvpTeTrunkMapRouteTable          OBJECT-TYPE
    SYNTAX          SEQUENCE OF RsvpTeTrunkMapRouteEntry
    MAX-ACCESS      not-accessible
    STATUS          current
    DESCRIPTION
     "Table of Map route entries in trunk."
    ::= { rsvpTe 4}

rsvpTeTrunkMapRouteEntry          OBJECT-TYPE
    SYNTAX          RsvpTeTrunkMapRouteEntry
    MAX-ACCESS      not-accessible
    STATUS          current
    DESCRIPTION
     "Entry of map route table"
    INDEX   { rsvpTeTrunkName ,  rsvpTeTrunkMapRouteIpAddr, rsvpTeTrunkMapRouteIpMaskLength}
    ::= { rsvpTeTrunkMapRouteTable 1}

RsvpTeTrunkMapRouteEntry    ::=
    SEQUENCE
    {
        rsvpTeTrunkMapRouteIpAddr
            IpAddress,
        rsvpTeTrunkMapRouteIpMaskLength
            Integer32,
        rsvpTeTrunkMapRouteRowStatus
            RowStatus
    }

rsvpTeTrunkMapRouteIpAddr         OBJECT-TYPE
    SYNTAX          IpAddress
    MAX-ACCESS      not-accessible
    STATUS          current
    DESCRIPTION
     "Configure the prefix to be mapped."
    ::= { rsvpTeTrunkMapRouteEntry 1}

rsvpTeTrunkMapRouteIpMaskLength   OBJECT-TYPE
    SYNTAX          Integer32 (0.. 32)
    MAX-ACCESS      not-accessible
    STATUS          current
    DESCRIPTION
     "Configure the prefix length to be mapped."
    ::= { rsvpTeTrunkMapRouteEntry 2}

rsvpTeTrunkMapRouteRowStatus      OBJECT-TYPE
    SYNTAX          RowStatus
    MAX-ACCESS      read-create
    STATUS          current
    DESCRIPTION     "Status of the rsvpTeTrunkMapRouteEntry row
     1 means Active
        4 means CreateAndGo
        6 means Destroy."
    ::= { rsvpTeTrunkMapRouteEntry 3}


-- rsvpTe: rsvp path
rsvpTePathTable                   OBJECT-TYPE
    SYNTAX          SEQUENCE OF RsvpTePathEntry
    MAX-ACCESS      not-accessible
    STATUS          current
    DESCRIPTION
     "Table of rsvp path entries."
    ::= { rsvpTe 5 }

rsvpTePathEntry                    OBJECT-TYPE
    SYNTAX          RsvpTePathEntry
    MAX-ACCESS      not-accessible
    STATUS          current
    DESCRIPTION
     "Entry of rsvp path table."
    INDEX   { rsvpTePathName }
    ::= { rsvpTePathTable 1 }

RsvpTePathEntry    ::=
    SEQUENCE
    {
        rsvpTePathName
            OCTET STRING,
        rsvpTePathRowStatus
            RowStatus
    }

rsvpTePathName                    OBJECT-TYPE
    SYNTAX          OCTET STRING
    MAX-ACCESS      not-accessible
    STATUS          current
    DESCRIPTION
     "The name of rsvp path."
    ::= { rsvpTePathEntry 1 }

rsvpTePathRowStatus               OBJECT-TYPE
    SYNTAX          RowStatus
    MAX-ACCESS      read-create
    STATUS          current
    DESCRIPTION     "Status of the rsvpTePathEntry row
     1 means Active
        4 means CreateAndGo
        6 means Destroy."
    ::=  { rsvpTePathEntry 2 }


-- rsvpTe: rsvp path node
rsvpTePathHopTable                   OBJECT-TYPE
    SYNTAX          SEQUENCE OF RsvpTePathHopEntry
    MAX-ACCESS      not-accessible
    STATUS          current
    DESCRIPTION
     "Table of rsvp path hop entries."
    ::= { rsvpTe 6 }

rsvpTePathHopEntry                    OBJECT-TYPE
    SYNTAX          RsvpTePathHopEntry
    MAX-ACCESS      not-accessible
    STATUS          current
    DESCRIPTION
     "Entry of rsvp path hop table."
    INDEX   { rsvpTePathName, rsvpTePathHopAddrID }
    ::= { rsvpTePathHopTable 1 }

RsvpTePathHopEntry    ::=
    SEQUENCE
    {
        rsvpTePathHopAddrID
            Integer32,
        rsvpTePathHopAddrType
            INTEGER,
        rsvpTePathHopAddr
            IpAddress,
        rsvpTePathHopRowStatus
            RowStatus
    }

rsvpTePathHopAddrID                  OBJECT-TYPE
    SYNTAX          Integer32 (0..65535)
    MAX-ACCESS      not-accessible
    STATUS          current
    DESCRIPTION
     "Index of a node in rsvp path. It should be unique under same path name."
    ::= { rsvpTePathHopEntry 1 }

rsvpTePathHopAddrType                OBJECT-TYPE
    SYNTAX          INTEGER {loose(1), strict(2)}
    MAX-ACCESS      read-create
    STATUS          current
    DESCRIPTION
     "The type of a node in rsvp path."
    ::= { rsvpTePathHopEntry 2 }

rsvpTePathHopAddr                    OBJECT-TYPE
    SYNTAX          IpAddress
    MAX-ACCESS      read-create
    STATUS          current
    DESCRIPTION
     "Configure IPv4 Address of Hop."
    ::= { rsvpTePathHopEntry 3 }

rsvpTePathHopRowStatus               OBJECT-TYPE
    SYNTAX          RowStatus
    MAX-ACCESS      read-create
    STATUS          current
    DESCRIPTION     "Status of the rsvpTePathEntry row
     1 means Active
        4 means CreateAndGo
        6 means Destroy."
    ::=  { rsvpTePathHopEntry 4 }


-- rsvpTe: show rsvp
rsvpTeSummary  OBJECT IDENTIFIER
    ::= { rsvpTe 7}

rsvpTeSummarySessionTatolCount     OBJECT-TYPE
    SYNTAX          Integer32
    MAX-ACCESS      read-only
    STATUS          current
    DESCRIPTION
     "Total count of the rsvp session."
    ::= { rsvpTeSummary 1 }

rsvpTeSummarySessionUpCount       OBJECT-TYPE
    SYNTAX          Integer32
    MAX-ACCESS      read-only
    STATUS          current
    DESCRIPTION
     "Total count of the rsvp session which status is up."
    ::= { rsvpTeSummary 2 }

rsvpTeSummarySessionDownCount     OBJECT-TYPE
    SYNTAX          Integer32
    MAX-ACCESS      read-only
    STATUS          current
    DESCRIPTION
     "Total count of the rsvp session which status is down."
    ::= { rsvpTeSummary 3 }


rsvpTeSummarySessionTable         OBJECT-TYPE
 SYNTAX          SEQUENCE OF RsvpTeSummarySessionEntry
 MAX-ACCESS      not-accessible
 STATUS          current
 DESCRIPTION
  "Table of rsvp session."
 ::= { rsvpTeSummary 4 }

rsvpTeSummarySessionEntry        OBJECT-TYPE
 SYNTAX          RsvpTeSummarySessionEntry
 MAX-ACCESS      not-accessible
 STATUS          current
 DESCRIPTION
  "Entry of rsvpTeSummarySessionTable"
 INDEX   { rsvpTeSummarySessionLSPId, rsvpTeSummarySessionSource, rsvpTeSummarySessionDestination, rsvpTeSummarySessionTunnelId, rsvpTeSummarySessionExtTunnelId }
 ::= { rsvpTeSummarySessionTable 1 }

RsvpTeSummarySessionEntry    ::=
 SEQUENCE
 {
  rsvpTeSummarySessionLSPId
   Integer32,
  rsvpTeSummarySessionSource
      IpAddress,
  rsvpTeSummarySessionDestination
   IpAddress,
  rsvpTeSummarySessionTunnelId
   Integer32,
  rsvpTeSummarySessionExtTunnelId
   IpAddress,
  rsvpTeSummarySessionTrunkName
   OCTET STRING,
  rsvpTeSummarySessionState
   INTEGER,
  rsvpTeSummarySessionIsPrimary
   INTEGER,
  rsvpTeSummarySessionReserve
   INTEGER,
  rsvpTeSummarySessionRefCount
   Integer32,
  rsvpTeSummarySessionLabelIn
   Integer32,
  rsvpTeSummarySessionLabelOut
   Integer32,
  rsvpTeSummarySessionType
   INTEGER,
  rsvpTeSummarySessionFSMState
   INTEGER,
  rsvpTeSummarySessionSetupPriority
   Integer32,
  rsvpTeSummarySessionHoldPriority
   Integer32,
  rsvpTeSummarySessionCspfUsage
   INTEGER,
  rsvpTeSummarySessionLSPMetric
   Integer32,
  rsvpTeSummarySessionLSPProtection
   INTEGER,
  rsvpTeSummarySessionUpStreamAddr
   IpAddress,
  rsvpTeSummarySessionUpStreamIfIndex
   Integer32,
  rsvpTeSummarySessionDownStreamAddr
   IpAddress,
        rsvpTeSummarySessionDownStreamIfIndex
         Integer32,
        rsvpTeSummarySessionPathRefreshSec
         Integer32,
        rsvpTeSummarySessionPathRefreshDue
         Integer32,
        rsvpTeSummarySessionPathRREnable
         INTEGER,
        rsvpTeSummarySessionLifeTime
         Integer32,
        rsvpTeSummarySessionDueTime
         Integer32,
     rsvpTeSummarySessionStyle
         INTEGER,
     rsvpTeSummarySessionTrafficType
         INTEGER,
     rsvpTeSummarySessionMTU
         Integer32,
     rsvpTeSummarySessionLastErrorCode
         OCTET STRING,
     rsvpTeSummarySessionLastErrorValue
         OCTET STRING,
     rsvpTeSummarySessionLastErrorNode
         IpAddress,
     rsvpTeSummarySessionTrunkType
         INTEGER
 }

rsvpTeSummarySessionLSPId                         OBJECT-TYPE
    SYNTAX          Integer32
    MAX-ACCESS      not-accessible
    STATUS          current
    DESCRIPTION
     "Lsp id of the rsvp session. "
    ::= { rsvpTeSummarySessionEntry 1 }

rsvpTeSummarySessionSource                        OBJECT-TYPE
    SYNTAX          IpAddress
    MAX-ACCESS      not-accessible
    STATUS          current
    DESCRIPTION
     "Source address of the rsvp session."
    ::= { rsvpTeSummarySessionEntry 2 }

rsvpTeSummarySessionDestination                   OBJECT-TYPE
    SYNTAX          IpAddress
    MAX-ACCESS      not-accessible
    STATUS          current
    DESCRIPTION
     "Destination address of the rsvp session."
    ::= { rsvpTeSummarySessionEntry 3 }

rsvpTeSummarySessionTunnelId                      OBJECT-TYPE
    SYNTAX          Integer32
    MAX-ACCESS      not-accessible
    STATUS          current
    DESCRIPTION
     "Tunnel id of the rsvp session. "
    ::= { rsvpTeSummarySessionEntry 4 }

rsvpTeSummarySessionExtTunnelId                   OBJECT-TYPE
    SYNTAX          IpAddress
    MAX-ACCESS      not-accessible
    STATUS          current
    DESCRIPTION
     "Ext-Tunnel id of the rsvp session. "
    ::= { rsvpTeSummarySessionEntry 5 }

rsvpTeSummarySessionTrunkName                     OBJECT-TYPE
    SYNTAX          OCTET STRING
    MAX-ACCESS      read-only
    STATUS          current
    DESCRIPTION
     "Name of the rsvp trunk"
    ::= { rsvpTeSummarySessionEntry 6 }

rsvpTeSummarySessionState                         OBJECT-TYPE
    SYNTAX          INTEGER {up(1), down(2)}
    MAX-ACCESS      read-only
    STATUS          current
    DESCRIPTION
     "state of the rsvp session."
    ::= { rsvpTeSummarySessionEntry 7 }

rsvpTeSummarySessionIsPrimary                     OBJECT-TYPE
    SYNTAX          INTEGER {primary(1), secondary(2)}
    MAX-ACCESS      read-only
    STATUS          current
    DESCRIPTION
     "If the rsvp session is primary or secondary."
    ::= { rsvpTeSummarySessionEntry 8 }

rsvpTeSummarySessionReserve                       OBJECT-TYPE
    SYNTAX          INTEGER {enable(1), disable(2)}
    MAX-ACCESS      read-only
    STATUS          current
    DESCRIPTION
     "If resource reserve is enabled for this session."
    ::= { rsvpTeSummarySessionEntry 9 }

rsvpTeSummarySessionRefCount                      OBJECT-TYPE
    SYNTAX          Integer32
    MAX-ACCESS      read-only
    STATUS          current
    DESCRIPTION
     "Reference count of the rsvp session."
    ::= { rsvpTeSummarySessionEntry 10 }

rsvpTeSummarySessionLabelIn                       OBJECT-TYPE
    SYNTAX          Integer32
    MAX-ACCESS      read-only
    STATUS          current
    DESCRIPTION
     "In lable of the rsvp session."
    ::= { rsvpTeSummarySessionEntry 11 }

rsvpTeSummarySessionLabelOut                      OBJECT-TYPE
    SYNTAX          Integer32
    MAX-ACCESS      read-only
    STATUS          current
    DESCRIPTION
     "Out lable of the rsvp session."
    ::= { rsvpTeSummarySessionEntry 12 }

rsvpTeSummarySessionType                          OBJECT-TYPE
    SYNTAX          INTEGER {ingress(1), transmit(2), egress(3)}
    MAX-ACCESS      read-only
    STATUS          current
    DESCRIPTION
     "Type of the rsvp session"
    ::= { rsvpTeSummarySessionEntry 13 }

rsvpTeSummarySessionFSMState                      OBJECT-TYPE
    SYNTAX          INTEGER {idle(0), gmplsLabelValidateSent(1), qosResvSentforReverseDir(2), nexthopRequestSent(3), waitingforRESVmessage(4), labelRequestSent(5), mplsMessageSent(6), operational(7), usingBackup(8)}
    MAX-ACCESS      read-only
    STATUS          current
    DESCRIPTION
     "FSM state of the rsvp session"
    ::= { rsvpTeSummarySessionEntry 14 }

rsvpTeSummarySessionSetupPriority                 OBJECT-TYPE
    SYNTAX          Integer32 (0..7)
    MAX-ACCESS      read-only
    STATUS          current
    DESCRIPTION
     "Setup priority of the rsvp session"
    ::= { rsvpTeSummarySessionEntry 15 }

rsvpTeSummarySessionHoldPriority                  OBJECT-TYPE
    SYNTAX          Integer32 (0..7)
    MAX-ACCESS      read-only
    STATUS          current
    DESCRIPTION
     "Hold priority of the rsvp session"
    ::= { rsvpTeSummarySessionEntry 16 }

rsvpTeSummarySessionCspfUsage                     OBJECT-TYPE
    SYNTAX          INTEGER {enable(1), disable(2)}
    MAX-ACCESS      read-only
    STATUS          current
    DESCRIPTION
     "If CSPF is enabled for this session. "
    ::= { rsvpTeSummarySessionEntry 17 }

rsvpTeSummarySessionLSPMetric                     OBJECT-TYPE
    SYNTAX          Integer32
    MAX-ACCESS      read-only
    STATUS          current
    DESCRIPTION
     "LSP Metric of the rsvp session. "
    ::= { rsvpTeSummarySessionEntry 18 }

rsvpTeSummarySessionLSPProtection                 OBJECT-TYPE
    SYNTAX          INTEGER {oneToOne(1), facility(2), none(3)}
    MAX-ACCESS      read-only
    STATUS          current
    DESCRIPTION
     "LSP Protection type of the rsvp session. "
    ::= { rsvpTeSummarySessionEntry 19 }

rsvpTeSummarySessionUpStreamAddr                  OBJECT-TYPE
    SYNTAX          IpAddress
    MAX-ACCESS      read-only
    STATUS          current
    DESCRIPTION
     "Upstream Ip Address of the rsvp session. "
    ::= { rsvpTeSummarySessionEntry 20 }

rsvpTeSummarySessionUpStreamIfIndex               OBJECT-TYPE
    SYNTAX          Integer32
    MAX-ACCESS      read-only
    STATUS          current
    DESCRIPTION
     "Upstream interface index of the rsvp session. "
    ::= { rsvpTeSummarySessionEntry 21 }

rsvpTeSummarySessionDownStreamAddr                OBJECT-TYPE
    SYNTAX          IpAddress
    MAX-ACCESS      read-only
    STATUS          current
    DESCRIPTION
     "DownStream Ip Address of the rsvp session. "
    ::= { rsvpTeSummarySessionEntry 22 }

rsvpTeSummarySessionDownStreamIfIndex             OBJECT-TYPE
    SYNTAX          Integer32
    MAX-ACCESS      read-only
    STATUS          current
    DESCRIPTION
     "Downstream interface index of the rsvp session. "
    ::= { rsvpTeSummarySessionEntry 23 }

rsvpTeSummarySessionPathRefreshSec                OBJECT-TYPE
    SYNTAX          Integer32
    MAX-ACCESS      read-only
    STATUS          current
    DESCRIPTION
     "The refresh time of the rsvp path in session. "
    ::= { rsvpTeSummarySessionEntry 24 }

rsvpTeSummarySessionPathRefreshDue                OBJECT-TYPE
    SYNTAX          Integer32
    MAX-ACCESS      read-only
    STATUS          current
    DESCRIPTION
     "The due time of the rsvp path in session. "
    ::= { rsvpTeSummarySessionEntry 25 }

rsvpTeSummarySessionPathRREnable                 OBJECT-TYPE
    SYNTAX          INTEGER {enable(1), disable(2)}
    MAX-ACCESS      read-only
    STATUS          current
    DESCRIPTION
     "If refresh reduction is enabled for this rsvp session. "
    ::= { rsvpTeSummarySessionEntry 26 }

rsvpTeSummarySessionLifeTime                     OBJECT-TYPE
    SYNTAX          Integer32
    MAX-ACCESS      read-only
    STATUS          current
    DESCRIPTION
     "The life time for this rsvp session. "
    ::= { rsvpTeSummarySessionEntry 27 }

rsvpTeSummarySessionDueTime                      OBJECT-TYPE
    SYNTAX          Integer32
    MAX-ACCESS      read-only
    STATUS          current
    DESCRIPTION
     "The due time for this rsvp session. "
    ::= { rsvpTeSummarySessionEntry 28 }

rsvpTeSummarySessionStyle                        OBJECT-TYPE
    SYNTAX          INTEGER {fixedFilter(1), sharedExplicitFilter(2) }
    MAX-ACCESS      read-only
    STATUS          current
    DESCRIPTION
     "The style this rsvp session. "
    ::= { rsvpTeSummarySessionEntry 29 }

rsvpTeSummarySessionTrafficType                  OBJECT-TYPE
    SYNTAX          INTEGER {guaranteed(1), controlledLoad(2) }
    MAX-ACCESS      read-only
    STATUS          current
    DESCRIPTION
     "The traffic type this rsvp session. "
    ::= { rsvpTeSummarySessionEntry 30 }

rsvpTeSummarySessionMTU                          OBJECT-TYPE
    SYNTAX          Integer32
    MAX-ACCESS      read-only
    STATUS          current
    DESCRIPTION
     "The MTU this rsvp session. "
    ::= { rsvpTeSummarySessionEntry 31 }

rsvpTeSummarySessionLastErrorCode                OBJECT-TYPE
    SYNTAX          OCTET STRING
    MAX-ACCESS      read-only
    STATUS          current
    DESCRIPTION
     "The last error code this rsvp session. "
    ::= { rsvpTeSummarySessionEntry 32 }

rsvpTeSummarySessionLastErrorValue               OBJECT-TYPE
    SYNTAX          OCTET STRING
    MAX-ACCESS      read-only
    STATUS          current
    DESCRIPTION
     "The last error value this rsvp session. "
    ::= { rsvpTeSummarySessionEntry 33 }

rsvpTeSummarySessionLastErrorNode               OBJECT-TYPE
    SYNTAX          IpAddress
    MAX-ACCESS      read-only
    STATUS          current
    DESCRIPTION
     "The last error value this rsvp session. "
    ::= { rsvpTeSummarySessionEntry 34 }

rsvpTeSummarySessionTrunkType                   OBJECT-TYPE
    SYNTAX          INTEGER {gmpls(1), mpls(2) }
    MAX-ACCESS      read-only
    STATUS          current
    DESCRIPTION
     "The last error value this rsvp session. "
    ::= { rsvpTeSummarySessionEntry 35 }

rsvpTeSummarySessionExplicitRouteTable          OBJECT-TYPE
 SYNTAX          SEQUENCE OF RsvpTeSummarySessionExplicitRouteEntry
 MAX-ACCESS      not-accessible
 STATUS          current
 DESCRIPTION
  "Table of Explicit route in rsvp session."
 ::= { rsvpTeSummary 5 }

rsvpTeSummarySessionExplicitRouteEntry         OBJECT-TYPE
 SYNTAX          RsvpTeSummarySessionExplicitRouteEntry
 MAX-ACCESS      not-accessible
 STATUS          current
 DESCRIPTION
  "Entry of rsvpTeSummarySessionExplicitRouteTable"
 INDEX   {rsvpTeSummarySessionDestination, rsvpTeSummarySessionSource, rsvpTeSummarySessionTunnelId, rsvpTeSummarySessionLSPId,  rsvpTeSummarySessionExtTunnelId, rsvpTeSummarySessionExplicitRouteAddrId}
 ::= { rsvpTeSummarySessionExplicitRouteTable 1 }

RsvpTeSummarySessionExplicitRouteEntry    ::=
 SEQUENCE
 {
  rsvpTeSummarySessionExplicitRouteAddrId
   Integer32,
  rsvpTeSummarySessionExplicitRouteAddr
   IpAddress,
  rsvpTeSummarySessionExplicitRouteMaskLen
   Integer32,
  rsvpTeSummarySessionExplicitRouteType
   INTEGER
 }

rsvpTeSummarySessionExplicitRouteAddrId        OBJECT-TYPE
    SYNTAX          Integer32
    MAX-ACCESS      read-only
    STATUS          current
    DESCRIPTION
     "The id of an explicit route entry. "
    ::= { rsvpTeSummarySessionExplicitRouteEntry 1 }

rsvpTeSummarySessionExplicitRouteAddr          OBJECT-TYPE
    SYNTAX          IpAddress
    MAX-ACCESS      read-only
    STATUS          current
    DESCRIPTION
     "The ipv4 address of an explicit route entry. "
    ::= { rsvpTeSummarySessionExplicitRouteEntry 2 }

rsvpTeSummarySessionExplicitRouteMaskLen       OBJECT-TYPE
    SYNTAX          Integer32
    MAX-ACCESS      read-only
    STATUS          current
    DESCRIPTION
     "The ipv4 mask length of an explicit route entry. "
    ::= { rsvpTeSummarySessionExplicitRouteEntry 3 }

rsvpTeSummarySessionExplicitRouteType             OBJECT-TYPE
    SYNTAX          INTEGER {strict(1), loose(2) }
    MAX-ACCESS      read-only
    STATUS          current
    DESCRIPTION
     "The type of an explicit route entry. "
    ::= { rsvpTeSummarySessionExplicitRouteEntry 4 }

rsvpTeSummarySessionRecvRouteTable          OBJECT-TYPE
 SYNTAX          SEQUENCE OF RsvpTeSummarySessionRecvRouteEntry
 MAX-ACCESS      not-accessible
 STATUS          current
 DESCRIPTION
  "Table of Recv route in rsvp session."
 ::= { rsvpTeSummary 6 }

rsvpTeSummarySessionRecvRouteEntry         OBJECT-TYPE
 SYNTAX          RsvpTeSummarySessionRecvRouteEntry
 MAX-ACCESS      not-accessible
 STATUS          current
 DESCRIPTION
  "Entry of rsvpTeSummarySessionRecvRouteTable"
 INDEX   { rsvpTeSummarySessionLSPId, rsvpTeSummarySessionSource, rsvpTeSummarySessionDestination, rsvpTeSummarySessionTunnelId, rsvpTeSummarySessionExtTunnelId, rsvpTeSummarySessionRecvRouteAddrId }
 ::= { rsvpTeSummarySessionRecvRouteTable 1 }

RsvpTeSummarySessionRecvRouteEntry    ::=
 SEQUENCE
 {
  rsvpTeSummarySessionRecvRouteAddrId
   Integer32,
  rsvpTeSummarySessionRecvRouteAddr
   IpAddress,
  rsvpTeSummarySessionRecvRouteMaskLen
   Integer32,
  rsvpTeSummarySessionRecvRouteType
   INTEGER
 }

rsvpTeSummarySessionRecvRouteAddrId        OBJECT-TYPE
    SYNTAX          Integer32
    MAX-ACCESS      read-only
    STATUS          current
    DESCRIPTION
     "The ipv4 address of an Recv route entry. "
    ::= { rsvpTeSummarySessionRecvRouteEntry 1 }

rsvpTeSummarySessionRecvRouteAddr          OBJECT-TYPE
    SYNTAX          IpAddress
    MAX-ACCESS      read-only
    STATUS          current
    DESCRIPTION
     "The ipv4 address of an Recv route entry. "
    ::= { rsvpTeSummarySessionRecvRouteEntry 2 }

rsvpTeSummarySessionRecvRouteMaskLen       OBJECT-TYPE
    SYNTAX          Integer32
    MAX-ACCESS      read-only
    STATUS          current
    DESCRIPTION
     "The ipv4 mask length of an Recv route entry. "
    ::= { rsvpTeSummarySessionRecvRouteEntry 3 }

rsvpTeSummarySessionRecvRouteType             OBJECT-TYPE
    SYNTAX          INTEGER {strict(1), loose(2) }
    MAX-ACCESS      read-only
    STATUS          current
    DESCRIPTION
     "The type of an Recv route entry. "
    ::= { rsvpTeSummarySessionRecvRouteEntry 4 }

rsvpTeSummarySessionRecordRouteTable          OBJECT-TYPE
 SYNTAX          SEQUENCE OF RsvpTeSummarySessionRecordRouteEntry
 MAX-ACCESS      not-accessible
 STATUS          current
 DESCRIPTION
  "Table of Record route in rsvp session."
 ::= { rsvpTeSummary 7 }

rsvpTeSummarySessionRecordRouteEntry         OBJECT-TYPE
 SYNTAX          RsvpTeSummarySessionRecordRouteEntry
 MAX-ACCESS      not-accessible
 STATUS          current
 DESCRIPTION
  "Entry of rsvpTeSummarySessionRecordRouteTable"
 INDEX   { rsvpTeSummarySessionLSPId, rsvpTeSummarySessionSource, rsvpTeSummarySessionDestination, rsvpTeSummarySessionTunnelId, rsvpTeSummarySessionExtTunnelId, rsvpTeSummarySessionRecordRouteAddrId }
 ::= { rsvpTeSummarySessionRecordRouteTable 1 }

RsvpTeSummarySessionRecordRouteEntry    ::=
 SEQUENCE
 {
  rsvpTeSummarySessionRecordRouteAddrId
   Integer32,
  rsvpTeSummarySessionRecordRouteAddr
   OCTET STRING
 }

rsvpTeSummarySessionRecordRouteAddrId       OBJECT-TYPE
    SYNTAX          Integer32
    MAX-ACCESS      read-only
    STATUS          current
    DESCRIPTION
     "The id of an Record route entry. "
    ::= { rsvpTeSummarySessionRecordRouteEntry 1 }

rsvpTeSummarySessionRecordRouteAddr          OBJECT-TYPE
    SYNTAX          OCTET STRING
    MAX-ACCESS      read-only
    STATUS          current
    DESCRIPTION
     "The ipv4 address of an Record route entry. "
    ::= { rsvpTeSummarySessionRecordRouteEntry 2 }

rsvpTeSummaryStatistics  OBJECT IDENTIFIER
    ::= { rsvpTeSummary 8}

rsvpTeSummaryPathSent                        OBJECT-TYPE
    SYNTAX          Integer32
    MAX-ACCESS      read-only
    STATUS          current
    DESCRIPTION
     "The total count of the rsvp path packet sent from this system. "
    ::= { rsvpTeSummaryStatistics 1 }

rsvpTeSummaryPathRecv                        OBJECT-TYPE
    SYNTAX          Integer32
    MAX-ACCESS      read-only
    STATUS          current
    DESCRIPTION
     "The total count of the rsvp path packet recieved by this system. "
    ::= { rsvpTeSummaryStatistics 2 }

rsvpTeSummaryPathErrSent                        OBJECT-TYPE
    SYNTAX          Integer32
    MAX-ACCESS      read-only
    STATUS          current
    DESCRIPTION
     "The total count of the rsvp path-err packet sent from this system. "
    ::= { rsvpTeSummaryStatistics 3 }

rsvpTeSummaryPathErrRecv                        OBJECT-TYPE
    SYNTAX          Integer32
    MAX-ACCESS      read-only
    STATUS          current
    DESCRIPTION
     "The total count of the rsvp path-err packet recieved by this system. "
    ::= { rsvpTeSummaryStatistics 4 }

rsvpTeSummaryPathTearSent                        OBJECT-TYPE
    SYNTAX          Integer32
    MAX-ACCESS      read-only
    STATUS          current
    DESCRIPTION
     "The total count of the rsvp path-tear packet sent from this system. "
    ::= { rsvpTeSummaryStatistics 5 }

rsvpTeSummaryPathTearRecv                        OBJECT-TYPE
    SYNTAX          Integer32
    MAX-ACCESS      read-only
    STATUS          current
    DESCRIPTION
     "The total count of the rsvp path-tear packet recieved by this system. "
    ::= { rsvpTeSummaryStatistics 6 }

rsvpTeSummaryResvFFSent                         OBJECT-TYPE
    SYNTAX          Integer32
    MAX-ACCESS      read-only
    STATUS          current
    DESCRIPTION
     "The total count of the rsvp Resv-FF packet sent from this system. "
    ::= { rsvpTeSummaryStatistics 7 }

rsvpTeSummaryResvFFRecv                         OBJECT-TYPE
    SYNTAX          Integer32
    MAX-ACCESS      read-only
    STATUS          current
    DESCRIPTION
     "The total count of the rsvp Resv-FF packet recieved by this system. "
    ::= { rsvpTeSummaryStatistics 8 }

rsvpTeSummaryResvWFSent                         OBJECT-TYPE
    SYNTAX          Integer32
    MAX-ACCESS      read-only
    STATUS          current
    DESCRIPTION
     "The total count of the rsvp Resv-WF packet sent from this system. "
    ::= { rsvpTeSummaryStatistics 9 }

rsvpTeSummaryResvWFRecv                         OBJECT-TYPE
    SYNTAX          Integer32
    MAX-ACCESS      read-only
    STATUS          current
    DESCRIPTION
     "The total count of the rsvp Resv-WF packet recieved by this system. "
    ::= { rsvpTeSummaryStatistics 10 }

rsvpTeSummaryResvSESent                         OBJECT-TYPE
    SYNTAX          Integer32
    MAX-ACCESS      read-only
    STATUS          current
    DESCRIPTION
     "The total count of the rsvp Resv-SE packet sent from this system. "
    ::= { rsvpTeSummaryStatistics 11 }

rsvpTeSummaryResvSERecv                         OBJECT-TYPE
    SYNTAX          Integer32
    MAX-ACCESS      read-only
    STATUS          current
    DESCRIPTION
     "The total count of the rsvp Resv-SE packet recieved by this system. "
    ::= { rsvpTeSummaryStatistics 12 }

rsvpTeSummaryResvErrSent                         OBJECT-TYPE
    SYNTAX          Integer32
    MAX-ACCESS      read-only
    STATUS          current
    DESCRIPTION
     "The total count of the rsvp Resv-Err packet sent from this system. "
    ::= { rsvpTeSummaryStatistics 13 }

rsvpTeSummaryResvErrRecv                         OBJECT-TYPE
    SYNTAX          Integer32
    MAX-ACCESS      read-only
    STATUS          current
    DESCRIPTION
     "The total count of the rsvp Resv-Err packet recieved by this system. "
    ::= { rsvpTeSummaryStatistics 14 }

rsvpTeSummaryResvTearSent                         OBJECT-TYPE
    SYNTAX          Integer32
    MAX-ACCESS      read-only
    STATUS          current
    DESCRIPTION
     "The total count of the rsvp Resv-Tear packet sent from this system. "
    ::= { rsvpTeSummaryStatistics 15 }

rsvpTeSummaryResvTearRecv                         OBJECT-TYPE
    SYNTAX          Integer32
    MAX-ACCESS      read-only
    STATUS          current
    DESCRIPTION
     "The total count of the rsvp Resv-Tear packet recieved by this system. "
    ::= { rsvpTeSummaryStatistics 16 }

rsvpTeSummaryResvConfSent                         OBJECT-TYPE
    SYNTAX          Integer32
    MAX-ACCESS      read-only
    STATUS          current
    DESCRIPTION
     "The total count of the rsvp Resv-Conf packet sent from this system. "
    ::= { rsvpTeSummaryStatistics 17 }

rsvpTeSummaryResvConfRecv                         OBJECT-TYPE
    SYNTAX          Integer32
    MAX-ACCESS      read-only
    STATUS          current
    DESCRIPTION
     "The total count of the rsvp Resv-Conf packet recieved by this system. "
    ::= { rsvpTeSummaryStatistics 18 }

rsvpTeSummaryHelloSent                           OBJECT-TYPE
    SYNTAX          Integer32
    MAX-ACCESS      read-only
    STATUS          current
    DESCRIPTION
     "The total count of the rsvp Hello packet sent from this system. "
    ::= { rsvpTeSummaryStatistics 19 }

rsvpTeSummaryHelloRecv
OBJECT-TYPE
    SYNTAX          Integer32
    MAX-ACCESS      read-only
    STATUS          current
    DESCRIPTION
     "The total count of the rsvp Hello packet recieved by this system. "
    ::= { rsvpTeSummaryStatistics 20 }

rsvpTeSummaryBundleSent                          OBJECT-TYPE
    SYNTAX          Integer32
    MAX-ACCESS      read-only
    STATUS          current
    DESCRIPTION
     "The total count of the rsvp Bundle packet sent from this system. "
    ::= { rsvpTeSummaryStatistics 21 }

rsvpTeSummaryBundleRecv                          OBJECT-TYPE
    SYNTAX          Integer32
    MAX-ACCESS      read-only
    STATUS          current
    DESCRIPTION
     "The total count of the rsvp Bundle packet recieved by this system. "
    ::= { rsvpTeSummaryStatistics 22 }

rsvpTeSummaryAckSent                             OBJECT-TYPE
    SYNTAX          Integer32
    MAX-ACCESS      read-only
    STATUS          current
    DESCRIPTION
     "The total count of the rsvp ack packet sent from this system. "
    ::= { rsvpTeSummaryStatistics 23 }

rsvpTeSummaryAckRecv                            OBJECT-TYPE
    SYNTAX          Integer32
    MAX-ACCESS      read-only
    STATUS          current
    DESCRIPTION
     "The total count of the rsvp ack packet recieved by this system. "
    ::= { rsvpTeSummaryStatistics 24 }

rsvpTeSummarySrefreshSent                       OBJECT-TYPE
    SYNTAX          Integer32
    MAX-ACCESS      read-only
    STATUS          current
    DESCRIPTION
     "The total count of the rsvp srefresh packet sent from this system. "
    ::= { rsvpTeSummaryStatistics 25 }

rsvpTeSummarySrefreshRecv                       OBJECT-TYPE
    SYNTAX          Integer32
    MAX-ACCESS      read-only
    STATUS          current
    DESCRIPTION
     "The total count of the rsvp srefresh packet recieved by this system. "
    ::= { rsvpTeSummaryStatistics 26 }



    
voiceVlanEnableVlan  OBJECT-TYPE
    SYNTAX          Integer32 (0|2..4094)
    MAX-ACCESS      read-write
    STATUS          current
    DESCRIPTION
        "Specify voice VLAN from 2 to 4094. 0 means voice vlan is disabled."
    DEFVAL          { 0 }
    ::= { voiceVlan 1 }

voiceVlanEnableSecurity  OBJECT-TYPE
    SYNTAX          TruthValue
    MAX-ACCESS      read-write
    STATUS          current
    DESCRIPTION
        "Specify voice VLAN security mode,1 will enable it,2 will disable it."
    ::= { voiceVlan 2 }

voiceVlanCOS  OBJECT-TYPE
    SYNTAX          Integer32(0..7)
    MAX-ACCESS      read-write
    STATUS          current
    DESCRIPTION
        "Set the COS of voice vlan."
    DEFVAL          { 5 }
    ::= { voiceVlan 3 }

voiceVlanEnableInterfaceTable OBJECT-TYPE
    SYNTAX          SEQUENCE OF VoiceVlanEnableInterfaceEntry
    MAX-ACCESS      not-accessible
    STATUS          current
    DESCRIPTION
        "The voice vlan enable interface table."
    ::= { voiceVlan 4 }

voiceVlanEnableInterfaceEntry OBJECT-TYPE
    SYNTAX          VoiceVlanEnableInterfaceEntry
    MAX-ACCESS      not-accessible
    STATUS          current
    DESCRIPTION
        "The voice vlan enable interface table entry."
    INDEX    { ifIndex }
    ::= { voiceVlanEnableInterfaceTable 1 }

VoiceVlanEnableInterfaceEntry     ::=
    SEQUENCE {
        voiceVlanEnableInterfaceStatus
            TruthValue
    }

voiceVlanEnableInterfaceStatus  OBJECT-TYPE
    SYNTAX          TruthValue
    MAX-ACCESS      read-write
    STATUS          current
    DESCRIPTION
        "Enable voice vlan on port,1 will enable it,2 will disable it."
    ::= { voiceVlanEnableInterfaceEntry 1 }

voiceVlanOuiEntryTable OBJECT-TYPE
    SYNTAX          SEQUENCE OF VoiceVlanOuiEntryEntry
    MAX-ACCESS      not-accessible
    STATUS          current
    DESCRIPTION
        "Table description."
    ::= { voiceVlan 5 }

voiceVlanOuiEntryEntry OBJECT-TYPE
    SYNTAX          VoiceVlanOuiEntryEntry
    MAX-ACCESS      not-accessible
    STATUS          current
    DESCRIPTION
        "Entry description."
    INDEX    { voiceVlanOuiEntryId }
    ::= { voiceVlanOuiEntryTable 1 }

VoiceVlanOuiEntryEntry     ::=
    SEQUENCE {
        voiceVlanOuiEntryId
            Integer32,
        voiceVlanOuiEntryMac
            MacAddress,
        voiceVlanOuiEntryMask
            MacAddress,
        voiceVlanOuiEntryDescription
            OCTET STRING,
        voiceVlanOuiEntryRowstatus
            RowStatus
    }

voiceVlanOuiEntryId  OBJECT-TYPE
    SYNTAX          Integer32
    MAX-ACCESS      not-accessible
    STATUS          current
    DESCRIPTION
        "OUI_id Desc."
    ::= { voiceVlanOuiEntryEntry 1 }

voiceVlanOuiEntryMac  OBJECT-TYPE
    SYNTAX          MacAddress
    MAX-ACCESS      read-create
    STATUS          current
    DESCRIPTION
        "MAC Desc."
    ::= { voiceVlanOuiEntryEntry 2 }

voiceVlanOuiEntryMask  OBJECT-TYPE
    SYNTAX          MacAddress
    MAX-ACCESS      read-create
    STATUS          current
    DESCRIPTION
        "MASK Desc."
    ::= { voiceVlanOuiEntryEntry 3 }

voiceVlanOuiEntryDescription  OBJECT-TYPE
    SYNTAX          OCTET STRING  (SIZE (1..63))
    MAX-ACCESS      read-create
    STATUS          current
    DESCRIPTION
        "description description."
    ::= { voiceVlanOuiEntryEntry 4 }

voiceVlanOuiEntryRowstatus  OBJECT-TYPE
    SYNTAX          RowStatus
    MAX-ACCESS      read-create
    STATUS          current
    DESCRIPTION
        "The status of the conceptual row. Now only realize CreateAndGo(4)
        and Destroy(6) and Active(1)."
    ::= { voiceVlanOuiEntryEntry 5 }

iviRouteTable OBJECT-TYPE
    SYNTAX          SEQUENCE OF IviRouteEntry
    MAX-ACCESS      not-accessible
    STATUS          current
    DESCRIPTION
        "The table for IVI route."
    ::= { ivi 1 }

iviRouteEntry OBJECT-TYPE
    SYNTAX          IviRouteEntry
    MAX-ACCESS      not-accessible
    STATUS          current
    DESCRIPTION
        "The entry of IVI route."
    INDEX    { iviRouteIndex }
    ::= { iviRouteTable 1 }
    
IviRouteEntry     ::= 
    SEQUENCE {
        iviRouteIndex
            Integer32,
        iviRouteIpv6address
            OCTET STRING,
        iviRouteIpv6addressMask
            Integer32,
        iviRouteIpv4address
            IpAddress,
        iviRouteIpv4addressMask
            Integer32,
        iviRouteRowStatus
            RowStatus
    }

iviRouteIndex  OBJECT-TYPE
    SYNTAX          Integer32 (1..32)
    MAX-ACCESS      not-accessible
    STATUS          current
    DESCRIPTION
        "IVI entry index."
    DEFVAL          { 0 }
    ::= { iviRouteEntry 1 }

iviRouteIpv6address  OBJECT-TYPE
    SYNTAX          OCTET STRING  (SIZE (16..16))
    MAX-ACCESS      read-create
    STATUS          current
    DESCRIPTION
        "The ipv6 address of IVI entry."
    ::= { iviRouteEntry 2 }

iviRouteIpv6addressMask  OBJECT-TYPE
    SYNTAX          Integer32 (8..96)
    MAX-ACCESS      read-create
    STATUS          current
    DESCRIPTION
        "The ipv6 prefix length."
    DEFVAL          { 0 }
    ::= { iviRouteEntry 3 }

iviRouteIpv4address  OBJECT-TYPE
    SYNTAX          IpAddress
    MAX-ACCESS      read-create
    STATUS          current
    DESCRIPTION
        "The ipv4 address of IVI entry"
    ::= { iviRouteEntry 4 }

iviRouteIpv4addressMask  OBJECT-TYPE
    SYNTAX          Integer32 (1..32)
    MAX-ACCESS      read-create
    STATUS          current
    DESCRIPTION
        "The ipv4 prefix length."
    DEFVAL          { 0 }
    ::= { iviRouteEntry 5 }

iviRouteRowStatus  OBJECT-TYPE
    SYNTAX          RowStatus
    MAX-ACCESS      read-create
    STATUS          current
    DESCRIPTION
        "The status of the conceptual row. Now only realize CreateAndGo(4)
        and Destroy(6) and Active(1)."
    ::= { iviRouteEntry 6 }


iviInterfaceTable OBJECT-TYPE
    SYNTAX          SEQUENCE OF IviInterfaceEntry
    MAX-ACCESS      not-accessible
    STATUS          current
    DESCRIPTION
        "The table for IVI enable status."
    ::= { ivi 2 }

iviInterfaceEntry OBJECT-TYPE
    SYNTAX          IviInterfaceEntry
    MAX-ACCESS      not-accessible
    STATUS          current
    DESCRIPTION
        "The entry of IVI enable status."
    INDEX    { ifIndex }
    ::= { iviInterfaceTable 1 }
    
IviInterfaceEntry     ::= 
    SEQUENCE {
        iviInterfaceStatus
            TruthValue
    }

iviInterfaceStatus  OBJECT-TYPE
    SYNTAX          TruthValue
    MAX-ACCESS      read-write
    STATUS          current
    DESCRIPTION
        "IVI status on the interface."
    ::= { iviInterfaceEntry 1 }

-- Sub Module: L2 protocol
--
--  L2 protocol tunnel Enable
--    
    l2ProtocolTunnelEnable OBJECT-TYPE
        SYNTAX INTEGER
        {
            enable(1), 
            disable(2)
        }
        MAX-ACCESS read-only
        STATUS current
        DESCRIPTION
            "Enable/disable L2ProtocolTunnel."
        ::= { l2protocol 1 }   

--
--  L2 protocol tunnel destnation Mac set
--

    l2ProtocolTunnelDestMac OBJECT-TYPE
        SYNTAX  MacAddress 
        MAX-ACCESS read-only
        STATUS current
        DESCRIPTION "Tunnel's destination MAC address, could be 0100.0CCD.CDD0-D2 or 010F.E200.0003.
        The default dest MAC address is 0100.0CCD.CDD0."
        ::= { l2protocol 2 }

    l2ProtocolTunnelCOS OBJECT-TYPE
        SYNTAX Integer32        (0..7)
        MAX-ACCESS read-only
        STATUS current
        DESCRIPTION
            "This node is used to configure layer2 protocol default COS values."
        DEFVAL { 0 } 
        ::= { l2protocol 3 }        
--
--  L2 protocol Mac set
--

    l2ProtocolMacTable OBJECT-TYPE
        SYNTAX  SEQUENCE OF L2ProtocolMacEntry
        MAX-ACCESS not-accessible
        STATUS   current
        DESCRIPTION "The information of the destination MAC 0180.c2xx.xxxx."
        ::= { l2protocol 5 }
            
    l2ProtocolMacEntry OBJECT-TYPE
        SYNTAX  L2ProtocolMacEntry
        MAX-ACCESS not-accessible
        STATUS current
        DESCRIPTION "The entry of the destination MAC table."
        INDEX   { l2ProtocolMacIndex }
        ::= { l2ProtocolMacTable 1 }        
    
    L2ProtocolMacEntry   ::=
    SEQUENCE {
        l2ProtocolMacIndex      Integer32,
        l2ProtocolMac           MacAddress,
        l2ProtocolMacMask       MacAddress,
        l2ProtocolMacRowstatus  RowStatus
        }    

    l2ProtocolMacIndex OBJECT-TYPE
        SYNTAX  Integer32         (0..3)
        MAX-ACCESS not-accessible
        STATUS current
        DESCRIPTION "The index of the mac entry. The value of index plus 1 equals the value in cli."
        ::= { l2ProtocolMacEntry 1 }

    l2ProtocolMac OBJECT-TYPE
        SYNTAX  MacAddress 
        MAX-ACCESS read-only
        STATUS current
        DESCRIPTION "L2 protocol MAC address, should be 0180.C200.0000-0180.C2FF.FFFF."
        ::= { l2ProtocolMacEntry 2 }

    l2ProtocolMacMask OBJECT-TYPE
        SYNTAX  MacAddress 
        MAX-ACCESS read-only
        STATUS current
        DESCRIPTION "L2 protocol MAC mask, should be FFFF.FF00.0000-FFFF.FFFF.FFFF."
        ::= { l2ProtocolMacEntry 3 }

    l2ProtocolMacRowstatus OBJECT-TYPE
        SYNTAX RowStatus
        MAX-ACCESS read-only
        STATUS current
        DESCRIPTION
            "The status of this conceptual row. Now only realize CreateAndGo and Destroy and Active."
        ::= { l2ProtocolMacEntry 4 }   

--
--  L2 protocol tunnel Mac set
--

    l2ProtocolTunnelMacTable OBJECT-TYPE
        SYNTAX  SEQUENCE OF L2ProtocolTunnelMacEntry
        MAX-ACCESS not-accessible
        STATUS   current
        DESCRIPTION "The information of mac tunnel enable or not."
        ::= { l2protocol 6 }
            
    l2ProtocolTunnelMacEntry OBJECT-TYPE
        SYNTAX  L2ProtocolTunnelMacEntry
        MAX-ACCESS not-accessible
        STATUS current
        DESCRIPTION "The information of mac tunnel enable or not."
        INDEX   { interfaceIndex, l2ProtocolMacIndex}
        ::= { l2ProtocolTunnelMacTable 1 }        
    
    L2ProtocolTunnelMacEntry   ::=
    SEQUENCE {
        l2ProtocolTunnelMacType        INTEGER,
        l2ProtocolTunnelMacEvcName     OCTET STRING,
        l2ProtocolTunnelMacRowstatus   RowStatus
        }    
    
    l2ProtocolTunnelMacType OBJECT-TYPE
        SYNTAX INTEGER
        {
            peer(0), 
            tunnel(1),
            discard(2)
        }
        MAX-ACCESS read-only
        STATUS current
        DESCRIPTION "The type of l2 protocol action.
        0 peer.
        1 tunnel.
        2 discard."
        DEFVAL { peer }
        ::= { l2ProtocolTunnelMacEntry 1 }
        
    l2ProtocolTunnelMacEvcName OBJECT-TYPE
        SYNTAX  OCTET STRING (SIZE (1..16))
        MAX-ACCESS read-only
        STATUS current
        DESCRIPTION "The name of the evc entry."
        ::= { l2ProtocolTunnelMacEntry 2 }
        
    l2ProtocolTunnelMacRowstatus OBJECT-TYPE
        SYNTAX RowStatus
        MAX-ACCESS read-only
        STATUS current
        DESCRIPTION
            "The status of this conceptual row. Now only realize CreateAndGo and Destroy and Active.
             In this node when Destroy the entry the default type peer will be used."
        ::= { l2ProtocolTunnelMacEntry 3 }    
        
--
--  L2 protocol tunnel dot1x set
--

    l2ProtocolTunnelDot1xTable OBJECT-TYPE
        SYNTAX  SEQUENCE OF L2ProtocolTunnelDot1xEntry
        MAX-ACCESS not-accessible
        STATUS   current
        DESCRIPTION "The information of Dot1x tunnel enable or not."
        ::= { l2protocol 7 }
            
    l2ProtocolTunnelDot1xEntry OBJECT-TYPE
        SYNTAX  L2ProtocolTunnelDot1xEntry
        MAX-ACCESS not-accessible
        STATUS current
        DESCRIPTION "The information of Dot1x tunnel enable or not."
        INDEX   { interfaceIndex}
        ::= { l2ProtocolTunnelDot1xTable 1 }        
    
    L2ProtocolTunnelDot1xEntry   ::=
    SEQUENCE {
        l2ProtocolTunnelDot1xType        INTEGER,
        l2ProtocolTunnelDot1xEvcName     OCTET STRING,
        l2ProtocolTunnelDot1xRowstatus   RowStatus
        }    
    
    l2ProtocolTunnelDot1xType OBJECT-TYPE
        SYNTAX INTEGER
        {
            peer(0), 
            tunnel(1),
            discard(2)
        }
        MAX-ACCESS read-only
        STATUS current
        DESCRIPTION "The type of l2 protocol action.
        0 peer.
        1 tunnel.
        2 discard."
        DEFVAL { peer }
        ::= { l2ProtocolTunnelDot1xEntry 1 }
        
    l2ProtocolTunnelDot1xEvcName OBJECT-TYPE
        SYNTAX OCTET STRING (SIZE (1..16))
        MAX-ACCESS read-only
        STATUS current
        DESCRIPTION "The name of the evc entry."
        ::= { l2ProtocolTunnelDot1xEntry 2 }
        
    l2ProtocolTunnelDot1xRowstatus OBJECT-TYPE
        SYNTAX RowStatus
        MAX-ACCESS read-only
        STATUS current
        DESCRIPTION
            "The status of this conceptual row. Now only realize CreateAndGo and Destroy and Active.
            In this node when Destroy the entry the default type peer will be used."
        ::= { l2ProtocolTunnelDot1xEntry 3 }            

--
--  L2 protocol tunnel Slow Proto set
--

    l2ProtocolTunnelSlowProtoTable OBJECT-TYPE
        SYNTAX  SEQUENCE OF L2ProtocolTunnelSlowProtoEntry
        MAX-ACCESS not-accessible
        STATUS   current
        DESCRIPTION "The information of slow protocol tunnel enable or not."
        ::= { l2protocol 8 }
            
    l2ProtocolTunnelSlowProtoEntry OBJECT-TYPE
        SYNTAX  L2ProtocolTunnelSlowProtoEntry
        MAX-ACCESS not-accessible
        STATUS current
        DESCRIPTION "The information of slow proto tunnel enable or not."
        INDEX   { interfaceIndex}
        ::= { l2ProtocolTunnelSlowProtoTable 1 }        
    
    L2ProtocolTunnelSlowProtoEntry   ::=
    SEQUENCE {
        l2ProtocolTunnelSlowProtoType        INTEGER,
        l2ProtocolTunnelSlowProtoEvcName    OCTET STRING,
        l2ProtocolTunnelSlowProtoRowstatus   RowStatus
        }    
    
    l2ProtocolTunnelSlowProtoType OBJECT-TYPE
        SYNTAX INTEGER
        {
            peer(0), 
            tunnel(1),
            discard(2)
        }
        MAX-ACCESS read-only
        STATUS current
        DESCRIPTION "The type of l2 protocol action.
        0 peer.
        1 tunnel.
        2 discard."
        DEFVAL { peer }
        ::= { l2ProtocolTunnelSlowProtoEntry 1 }
        
    l2ProtocolTunnelSlowProtoEvcName OBJECT-TYPE
        SYNTAX  OCTET STRING (SIZE (1..16))
        MAX-ACCESS read-only
        STATUS current
        DESCRIPTION "The name of the evc entry."
        ::= { l2ProtocolTunnelSlowProtoEntry 2 }
        
    l2ProtocolTunnelSlowProtoRowstatus OBJECT-TYPE
        SYNTAX RowStatus
        MAX-ACCESS read-only
        STATUS current
        DESCRIPTION
            "The status of this conceptual row. Now only realize CreateAndGo and Destroy and Active.
            In this node when Destroy the entry the default type peer will be used."
        ::= { l2ProtocolTunnelSlowProtoEntry 3 }    

--
--  L2 protocol tunnel Stp set
--

    l2ProtocolTunnelStpTable OBJECT-TYPE
        SYNTAX  SEQUENCE OF L2ProtocolTunnelStpEntry
        MAX-ACCESS not-accessible
        STATUS   current
        DESCRIPTION "The information of Stp tunnel enable or not."
        ::= { l2protocol 9 }
            
    l2ProtocolTunnelStpEntry OBJECT-TYPE
        SYNTAX  L2ProtocolTunnelStpEntry
        MAX-ACCESS not-accessible
        STATUS current
        DESCRIPTION "The information of Stp tunnel enable or not."
        INDEX   { interfaceIndex}
        ::= { l2ProtocolTunnelStpTable 1 }        
    
    L2ProtocolTunnelStpEntry   ::=
    SEQUENCE {
        l2ProtocolTunnelStpType        INTEGER,
        l2ProtocolTunnelStpEvcName     OCTET STRING,
        l2ProtocolTunnelStpRowstatus   RowStatus
        }    
    
    l2ProtocolTunnelStpType OBJECT-TYPE
        SYNTAX INTEGER
        {
            peer(0), 
            tunnel(1),
            discard(2)
        }
        MAX-ACCESS read-only
        STATUS current
        DESCRIPTION "The type of l2 protocol action.
        0 peer.
        1 tunnel.
        2 discard."
        DEFVAL { peer }
        ::= { l2ProtocolTunnelStpEntry 1 }
        
    l2ProtocolTunnelStpEvcName OBJECT-TYPE
        SYNTAX  OCTET STRING (SIZE (1..16))
        MAX-ACCESS read-only
        STATUS current
        DESCRIPTION "The name of the evc entry."
        ::= { l2ProtocolTunnelStpEntry 2 }
        
    l2ProtocolTunnelStpRowstatus OBJECT-TYPE
        SYNTAX RowStatus
        MAX-ACCESS read-only
        STATUS current
        DESCRIPTION
            "The status of this conceptual row. Now only realize CreateAndGo and Destroy and Active.
            In this node when Destroy the entry the default type peer will be used."
        ::= { l2ProtocolTunnelStpEntry 3 }    
        
--
--  L2 protocol tunnel Cfm set
--

    l2ProtocolTunnelCfmTable OBJECT-TYPE
        SYNTAX  SEQUENCE OF L2ProtocolTunnelCfmEntry
        MAX-ACCESS not-accessible
        STATUS   current
        DESCRIPTION "The information of Cfm tunnel enable or not."
        ::= { l2protocol 10 }
            
    l2ProtocolTunnelCfmEntry OBJECT-TYPE
        SYNTAX  L2ProtocolTunnelCfmEntry
        MAX-ACCESS not-accessible
        STATUS current
        DESCRIPTION "The information of Cfm tunnel enable or not."
        INDEX   { interfaceIndex}
        ::= { l2ProtocolTunnelCfmTable 1 }        
    
    L2ProtocolTunnelCfmEntry   ::=
    SEQUENCE {
        l2ProtocolTunnelCfmType        INTEGER,
        l2ProtocolTunnelCfmEvcName     OCTET STRING,
        l2ProtocolTunnelCfmRowstatus   RowStatus
        }    
    
    l2ProtocolTunnelCfmType OBJECT-TYPE
        SYNTAX INTEGER
        {
            peer(0), 
            tunnel(1),
            discard(2)
        }
        MAX-ACCESS read-only
        STATUS current
        DESCRIPTION "The type of l2 protocol action.
        0 peer.
        1 tunnel.
        2 discard."
        DEFVAL { peer }
        ::= { l2ProtocolTunnelCfmEntry 1 }
        
    l2ProtocolTunnelCfmEvcName OBJECT-TYPE
        SYNTAX  OCTET STRING (SIZE (1..16))
        MAX-ACCESS read-only
        STATUS current
        DESCRIPTION "The name of the evc entry."
        ::= { l2ProtocolTunnelCfmEntry 2 }
        
    l2ProtocolTunnelCfmRowstatus OBJECT-TYPE
        SYNTAX RowStatus
        MAX-ACCESS read-only
        STATUS current
        DESCRIPTION
            "The status of this conceptual row. Now only realize CreateAndGo and Destroy and Active.
            In this node when Destroy the entry the default type peer will be used."
        ::= { l2ProtocolTunnelCfmEntry 3 }  

--
--  L2 protocol tunnel uplink enable
--

    l2ProtocolTunnelUplinkTable OBJECT-TYPE
        SYNTAX  SEQUENCE OF L2ProtocolTunnelUplinkEntry
        MAX-ACCESS not-accessible
        STATUS   current
        DESCRIPTION "The information of uplink enable or not."
        ::= { l2protocol 11 }
            
    l2ProtocolTunnelUplinkEntry OBJECT-TYPE
        SYNTAX  L2ProtocolTunnelUplinkEntry
        MAX-ACCESS not-accessible
        STATUS current
        DESCRIPTION "The information of uplink enable or not."
        INDEX   { interfaceIndex}
        ::= { l2ProtocolTunnelUplinkTable 1 }        
    
    L2ProtocolTunnelUplinkEntry   ::=
    SEQUENCE {
        l2ProtocolTunnelUplinkEnable    INTEGER,
        l2ProtocolTunnelUplinkRowstatus   RowStatus
        }    
    
    l2ProtocolTunnelUplinkEnable OBJECT-TYPE
        SYNTAX INTEGER
        {
            enable(1), 
            disable(2)
        }
        MAX-ACCESS read-only
        STATUS current
        DESCRIPTION "l2protocol uplink enable or not."
        DEFVAL { disable }
        ::= { l2ProtocolTunnelUplinkEntry 1 }
        
    l2ProtocolTunnelUplinkRowstatus OBJECT-TYPE
        SYNTAX RowStatus
        MAX-ACCESS read-only
        STATUS current
        DESCRIPTION
            "The status of this conceptual row. Now only realize CreateAndGo and Destroy and Active.
            In this node when Destroy the entry the default type peer will be used."
        ::= { l2ProtocolTunnelUplinkEntry 2 }        
        
--
--  L2 protocol Full-Mac set
--

    l2ProtocolFullMacTable OBJECT-TYPE
        SYNTAX  SEQUENCE OF L2ProtocolFullMacEntry
        MAX-ACCESS not-accessible
        STATUS   current
        DESCRIPTION "The infomation of the all destination MAC."
        ::= { l2protocol 12 }
            
    l2ProtocolFullMacEntry OBJECT-TYPE
        SYNTAX  L2ProtocolFullMacEntry
        MAX-ACCESS not-accessible
        STATUS current
        DESCRIPTION "The entry of the destination MAC table."
        INDEX   { l2ProtocolFullMacIndex }
        ::= { l2ProtocolFullMacTable 1 }        
    
    L2ProtocolFullMacEntry   ::=
    SEQUENCE {
        l2ProtocolFullMacIndex      Integer32,
        l2ProtocolFullMac           MacAddress,
        l2ProtocolFullMacRowstatus  RowStatus
        }

    l2ProtocolFullMacIndex OBJECT-TYPE
        SYNTAX  Integer32         (0)
        MAX-ACCESS not-accessible
        STATUS current
        DESCRIPTION "The index of the full-mac entry. The value is 0 always"
        ::= { l2ProtocolFullMacEntry 1 }

    l2ProtocolFullMac OBJECT-TYPE
        SYNTAX  MacAddress 
        MAX-ACCESS read-only
        STATUS current
        DESCRIPTION "L2 protocol MAC address, including all MAC addresses."
        ::= { l2ProtocolFullMacEntry 2 }

    l2ProtocolFullMacRowstatus OBJECT-TYPE
        SYNTAX RowStatus
        MAX-ACCESS read-only
        STATUS current
        DESCRIPTION
            "The status of this conceptual row.Now only realize CreateAndGo and Destroy and Active."
        ::= { l2ProtocolFullMacEntry 3 }   

--
--  L2 protocol tunnel Full-Mac set
--

    l2ProtocolTunnelFullMacTable OBJECT-TYPE
        SYNTAX  SEQUENCE OF L2ProtocolTunnelFullMacEntry
        MAX-ACCESS not-accessible
        STATUS   current
        DESCRIPTION "The infomation of full-mac tunnel enable or not."
        ::= { l2protocol 13 }
            
    l2ProtocolTunnelFullMacEntry OBJECT-TYPE
        SYNTAX  L2ProtocolTunnelFullMacEntry
        MAX-ACCESS not-accessible
        STATUS current
        DESCRIPTION "The infomation of full-mac tunnel enable or not."
        INDEX   { interfaceIndex }
        ::= { l2ProtocolTunnelFullMacTable 1 }        
    
    L2ProtocolTunnelFullMacEntry   ::=
    SEQUENCE {
        l2ProtocolTunnelFullMacType        INTEGER,
        l2ProtocolTunnelFullMacEvcName     OCTET STRING,
        l2ProtocolTunnelFullMacRowstatus   RowStatus
        }    
    
    l2ProtocolTunnelFullMacType OBJECT-TYPE
        SYNTAX INTEGER
        {
            peer(0), 
            tunnel(1),
            discard(2)
        }
        MAX-ACCESS read-only
        STATUS current
        DESCRIPTION "The type of l2 protocol action.
        0 peer.
        1 tunnel.
        2 discard."
        DEFVAL { peer }
        ::= { l2ProtocolTunnelFullMacEntry 1 }
        
    l2ProtocolTunnelFullMacEvcName OBJECT-TYPE
        SYNTAX  OCTET STRING (SIZE (1..16))
        MAX-ACCESS read-only
        STATUS current
        DESCRIPTION "The name of the evc entry."
        ::= { l2ProtocolTunnelFullMacEntry 2 }
        
    l2ProtocolTunnelFullMacRowstatus OBJECT-TYPE
        SYNTAX RowStatus
        MAX-ACCESS read-only
        STATUS current
        DESCRIPTION
            "The status of this conceptual row.Now only realize CreateAndGo and Destroy and Active.
             In this node when Destroy the entry the default type peer will be used."
        ::= { l2ProtocolTunnelFullMacEntry 3 }    


-- Sub Module: loopback detect   OBJECT IDENTIFIER ::= { centec 105 }

loopbackDetectIfTable   OBJECT-TYPE
    SYNTAX  SEQUENCE OF LoopbackDetectIfEntry
    MAX-ACCESS not-accessible
    STATUS   current
    DESCRIPTION 
    "Configure loopback detection on an interface."
    ::= { loopbackDetect 1 }
 
loopbackDetectIfEntry OBJECT-TYPE
    SYNTAX  LoopbackDetectIfEntry
    MAX-ACCESS not-accessible
    STATUS current
    DESCRIPTION 
    "Entry of loopbackDetectIfTable."
    INDEX   { loopbackDetectIfIndex }
    ::= { loopbackDetectIfTable 1 }

LoopbackDetectIfEntry   ::=
    SEQUENCE {
        loopbackDetectIfIndex              Integer32,
        loopbackDetectEnable               INTEGER,
        loopbackDetectAction               INTEGER,
        loopbackDetectStatus               INTEGER
        }

loopbackDetectIfIndex         OBJECT-TYPE
    SYNTAX          Integer32 (1..65535)
    MAX-ACCESS      not-accessible
    STATUS          current
    DESCRIPTION     "Interface index."
    ::= { loopbackDetectIfEntry 1 }
 
loopbackDetectEnable OBJECT-TYPE
    SYNTAX  INTEGER {enable(1), disable(2)}
    MAX-ACCESS read-write
    STATUS current
    DESCRIPTION 
    "Enable the loopback detect on a port.The meanings of the values are:
       enable(1);disable(2)."  
    DEFVAL { disable }
    ::= { loopbackDetectIfEntry 2 }

loopbackDetectAction OBJECT-TYPE
    SYNTAX  INTEGER {shutdown(1), trap(2)}
    MAX-ACCESS read-write
    STATUS current
    DESCRIPTION 
    "Set the action of the loopback detection.The meanings of the values are:
       shutdown(1);trap(2)."  
    DEFVAL { trap }
    ::= { loopbackDetectIfEntry 3 }

loopbackDetectStatus OBJECT-TYPE
    SYNTAX  INTEGER {trap(1), shutdown(2), normal(3)}
    MAX-ACCESS read-only
    STATUS current
    DESCRIPTION 
    "Get the status of the loopback detection.The meanings of the values are:
       trap(1);shutdown(2);normal(3)."  
    DEFVAL { normal }
    ::= { loopbackDetectIfEntry 4 }

loopbackDetectPktInterval OBJECT-TYPE
        SYNTAX Integer32        (1..300)
        MAX-ACCESS read-write
        STATUS current
        DESCRIPTION
            "This node is used to configure loopback detection packet interval."
        DEFVAL { 5 } 
        ::= { loopbackDetect 2 }

loopbackDetectTrap        OBJECT IDENTIFIER ::= { loopbackDetect 1000 }

loopbackDetectStatusNotify    NOTIFICATION-TYPE
        OBJECTS     { loopbackDetectIfIndex, loopbackDetectStatus }
        STATUS      current
        DESCRIPTION
            "This trap will be generated when loopback status changed on an interface."
        ::= {loopbackDetectTrap 1}

END
